RFC1155-SMI DEFINITIONS ::= BEGIN

EXPORTS -- EVERYTHING
        internet, directory, mgmt,
        experimental, private, enterprises,
        OBJECT-TYPE, ObjectName, ObjectSyntax, SimpleSyntax,
        ApplicationSyntax, NetworkAddress, IpAddress,
        Counter, Gauge, TimeTicks, Opaque;

 -- the path to the root

 internet      OBJECT IDENTIFIER ::= { iso org(3) dod(6) 1 }

 directory     OBJECT IDENTIFIER ::= { internet 1 }

 mgmt          OBJECT IDENTIFIER ::= { internet 2 }

 experimental  OBJECT IDENTIFIER ::= { internet 3 }

 private       OBJECT IDENTIFIER ::= { internet 4 }
 enterprises   OBJECT IDENTIFIER ::= { private 1 }

 -- definition of object types

 OBJECT-TYPE MACRO ::=
 BEGIN
     TYPE NOTATION ::= "SYNTAX" type (TYPE ObjectSyntax)
                        "ACCESS" Access
                        "STATUS" Status
     VALUE NOTATION ::= value (VALUE ObjectName)

     Access ::= "read-only"
                     | "read-write"
                     | "write-only"
                     | "not-accessible"
     Status ::= "mandatory"
                     | "optional"
                     | "obsolete"
 END

 ObjectName ::=
     OBJECT IDENTIFIER

 ObjectSyntax ::=
     CHOICE {
         simple
             SimpleSyntax,
         application-wide
             ApplicationSyntax
     }

 SimpleSyntax ::=
     CHOICE {
         number
             INTEGER,
         string
             OCTET STRING,
         object
             OBJECT IDENTIFIER,
         empty
             NULL
     }

 ApplicationSyntax ::=
     CHOICE {
         address
             NetworkAddress,
         counter
             Counter,
         gauge
             Gauge,
         ticks
             TimeTicks,
         arbitrary
             Opaque
     }

 NetworkAddress ::=
     CHOICE {
         internet
             IpAddress
     }

 IpAddress ::=
     [APPLICATION 0]
         IMPLICIT OCTET STRING (SIZE (4))

 Counter ::=
     [APPLICATION 1]
         IMPLICIT INTEGER (0..4294967295)

 Gauge ::=
     [APPLICATION 2]
         IMPLICIT INTEGER (0..4294967295)

 TimeTicks ::=
     [APPLICATION 3]
         IMPLICIT INTEGER (0..4294967295)

 Opaque ::=
     [APPLICATION 4]
         IMPLICIT OCTET STRING

END
