IANA-ENERGY-RELATION-MIB DEFINITIONS ::= BEGIN
         IMPORTS
           MODULE-IDENTITY, mib-2
               FROM SNMPv2-SMI
           TEXTUAL-CONVENTION
               FROM SNMPv2-TC;

         ianaEnergyRelationMIB MODULE-IDENTITY
           LAST-UPDATED "201502090000Z"  -- February 9, 2015
           ORGANIZATION "IANA"
           CONTACT-INFO "
                         Internet Assigned Numbers Authority
                         Postal: ICANN
                         12025 Waterfront Dr., Suite 300
                         Los Angeles, CA 90094
                         United States
                         Tel: +1-310-301-5800
                         EMail: iana@iana.org"

           DESCRIPTION
            "Copyright (c) 2015 IETF Trust and the persons identified as
             authors of the code.  All rights reserved.

             Redistribution and use in source and binary forms, with or
             without modification, is permitted pursuant to, and subject
             to the license terms contained in, the Simplified BSD
             License set forth in Section 4.c of the IETF Trust's Legal
             Provisions Relating to IETF Documents
             (http://trustee.ietf.org/license-info).

             This MIB module defines a TEXTUAL-CONVENTION that
             describes the relationships between Energy Objects.

             The initial version of this MIB module was published in
             RFC 7461; for full legal notices see the RFC itself."

           REVISION     "201502090000Z"  -- February 9, 2015
           DESCRIPTION  "Initial version of this MIB as published in
                         RFC 7461."
           ::= { mib-2 232 }

         -- Textual Conventions

   IANAEnergyRelationship ::= TEXTUAL-CONVENTION
       STATUS            current
       DESCRIPTION
              "An enumerated value specifying the type of
               relationship between an Energy Object A, on

               which the relationship is specified, with the
               Energy Object B, identified by the UUID.

               The enumeration 'poweredBy' is applicable if
               Energy Object A is poweredBy Energy Object B.

               The enumeration 'powering' is applicable if
               Energy Object A is powering Energy Object B.

               The enumeration 'meteredBy' is applicable if
               Energy Object A is meteredBy Energy Object B.

               The enumeration 'metering' is applicable if
               Energy Object A is metering Energy Object B.

               The enumeration 'aggregatedBy' is applicable if
               Energy Object A is aggregatedBy Energy Object B.

               The enumeration 'aggregating' is applicable if
               Energy Object A is aggregating Energy Object B."

       SYNTAX      INTEGER  {
                    poweredBy(1),   --  power relationship
                    powering(2),
                    meteredBy(3),   --  meter relationship
                    metering(4),
                    aggregatedBy(5), -- aggregation relationship
                    aggregating(6)
                    }

   END
