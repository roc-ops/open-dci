CLAB-WIFI-MIB DEFINITIONS ::= BEGIN

IMPORTS 
    MODULE-IDENTITY, 
    OBJECT-TYPE, 
    NOTIFICATION-TYPE,
    Unsigned32,
    Integer32,
    Counter32,
    Counter64
                       FROM SNMPv2-SMI 
    OBJECT-GROUP, 
    MODULE-COMPLIANCE,
    NOTIFICATION-GROUP 
                       FROM SNMPv2-CONF 
    SnmpAdminString 
                       FROM SNMP-FRAMEWORK-MIB
    MacAddress,
    DateAndTime,
    TruthValue,
    RowStatus,
    TEXTUAL-CONVENTION
                       FROM SNMPv2-TC    
    InetAddressType,
    InetAddress,
    InetPortNumber
                       FROM INET-ADDRESS-MIB
    InterfaceIndex 
                       FROM IF-MIB
                       
    clabProjWireless 
                       FROM CLAB-DEF-MIB;

    clabWIFIMib MODULE-IDENTITY

    LAST-UPDATED  "201603300000Z" -- March 30, 2016
  
    ORGANIZATION "Cable Television Laboratories, Inc." 
    CONTACT-INFO 
            "Broadband Network Services
             Cable Television Laboratories, Inc.
             858 Coal Creek Circle,
             Louisville, CO 80027, USA 
             Phone: +1 303-661-9100
             Email: mibs@cablelabs.com"
     DESCRIPTION 
            "This MIB module contains the management objects
             for the Wi-Fi interface.
             
             Copyright 1999-2016 Cable Television Laboratories, Inc.
             All rights reserved." 
     REVISION "201603300000Z" -- March 30, 2016
     DESCRIPTION 
            "Updated per ECN WiFi-MGMT-N-16.0034-1. Changes:
             1. Deprecated clabWIFIAccessPointPasspointVenueNamesTable,
                clabWIFIAccessPointPasspointNAIRealmsTable and
                clabWIFIAccessPointPasspointOSUTable.
             2. Created clabWIFIAccessPointPasspoint2VenueNamesTable,
                clabWIFIAccessPointPasspoint2NAIRealmsTable,
                clabWIFIAccessPointPasspoint2NAIRealmsEapMethodsTable,
                clabWIFIAccessPointPasspoint2NAIRealmsEapMethodsAuthTable,
                clabWIFIAccessPointPasspoint2OSUTable,
                clabWIFIAccessPointPasspoint2OSUProviderNamesTable,
                clabWIFIAccessPointPasspoint2OSUProviderIconsTable and
                clabWIFIAccessPointPasspoint2OSUProviderServiceDescTable." 
     REVISION "201512020000Z" -- December 2, 2015
     DESCRIPTION 
            "Revised Version includes ECN
             WiFi-MGMT-N-15.0030-1 " 
     REVISION "201403110000Z" -- March 11, 2014
     DESCRIPTION 
            "Revised Version includes ECN
             WiFi-MGMT-N-14.0017-2
             and published as part of WR-SP-WiFi-MGMT-I04-140311" 
     REVISION "201201060000Z" -- Jan 6, 2012
     DESCRIPTION 
            "Revised Version includes ECN
             WiFi-MGMT-N-11.0006-5
             and published as part of WR-SP-WiFi-MGMT-I03-120216" 
     REVISION "201009270000Z" -- Sept 27, 2010
     DESCRIPTION 
            "Revised Version includes ECN
             WiFi-MGMT-N-11.0002-4
             and published as part of WR-SP-WiFi-MGMT-I02-101006" 
     REVISION "201007290000Z" -- July 29, 2010
     DESCRIPTION
             "Initial version, published as part of the CableLabs
             Wi-Fi Provisioning Framework Specification
             WR-SP-WiFi-MGMT-I01-100729
             Copyright 2010 Cable Television Laboratories, Inc.
             All rights reserved."   
             
    ::= { clabProjWireless 1 }
  
-- Textual Conventions
PktErrorRateType ::= TEXTUAL-CONVENTION
			DISPLAY-HINT 	"d-9"
			STATUS current
			DESCRIPTION 
				"This data type represents a packet error rate in
				 units of 10^-5 or a resolution of 0.000000001 
				 precision."
			SYNTAX Integer32

-- Object Definitions
clabWIFINotifications OBJECT IDENTIFIER ::= { clabWIFIMib 0 }
clabWIFIObjects OBJECT IDENTIFIER ::= { clabWIFIMib 1 }

clabWIFIWiFi OBJECT IDENTIFIER ::= {clabWIFIObjects 1 }

clabWIFIWiFiRadioNumberOfEntries    OBJECT-TYPE
    SYNTAX      Unsigned32 
    MAX-ACCESS  read-only
    STATUS      current
    DESCRIPTION
        "This object is defined in TR-181 Device.WiFi.RadioNumberOfEntries."
    REFERENCE
        "TR-181 Device Data Model for TR-069."
    ::= {clabWIFIWiFi 1 }

clabWIFIWiFiSSIDNumberOfEntries    OBJECT-TYPE
    SYNTAX      Unsigned32 
    MAX-ACCESS  read-only
    STATUS      current
    DESCRIPTION
        "This object is defined in TR-181 Device.WiFi.SSIDNumberOfEntries."
    REFERENCE
        "TR-181 Device Data Model for TR-069."
    ::= {clabWIFIWiFi 2 }

clabWIFIWiFiAccessPointNumberOfEntries    OBJECT-TYPE
    SYNTAX      Unsigned32 
    MAX-ACCESS  read-only
    STATUS      current
    DESCRIPTION
        "This object is defined in TR-181 Device.WiFi.AccessPointNumberOfEntries."
    REFERENCE
        "TR-181 Device Data Model for TR-069."
    ::= {clabWIFIWiFi 3 }

clabWIFIWiFiEndPointNumberOfEntries    OBJECT-TYPE
    SYNTAX      Unsigned32 
    MAX-ACCESS  read-only
    STATUS      current
    DESCRIPTION
        "This object is defined in TR-181 Device.WiFi.EndPointNumberOfEntries."
    REFERENCE
        "TR-181 Device Data Model for TR-069."
    ::= {clabWIFIWiFi 4 }

clabWIFISSIDSteeringEnabled    OBJECT-TYPE
    SYNTAX      TruthValue 
    MAX-ACCESS  read-write
    STATUS      current
    DESCRIPTION
        "This object is defined as a CableLabs TR-181 extension to
         Device.WiFi.  It enables support to steer a user device to 
         a Private SSID when available."
    ::= {clabWIFIWiFi 5 }

clabWIFICommitSettings    OBJECT-TYPE
    SYNTAX      TruthValue 
    MAX-ACCESS  read-write
    STATUS      current
    DESCRIPTION
        "This attribute when set to 'true' flushes the WiFi settings in
         non-volatile memory and reinitialize the WiFi system with the 
         new set of values without reboot. This attribute reports a value 
         'false' when WiFi attributes have been changed but the changes 
         are not active (i.e. not flushed in non-volatile and not part 
         of the active configuration). Systems that support immediate 
         commit upon any attribute change will report this attribute as 
         'true' always, and silently accepts sets to 'true'."
    ::= {clabWIFIWiFi 6 }

clabWIFIRadioTable OBJECT-TYPE
    SYNTAX      SEQUENCE OF ClabWIFIRadioEntry
    MAX-ACCESS  not-accessible
    STATUS      current
    DESCRIPTION
        "This object is defined in TR-181 Device.WiFi.Radio"
    REFERENCE
        "TR-181 Device Data Model for TR-069."
    ::= {clabWIFIObjects 2 }

clabWIFIRadioEntry    OBJECT-TYPE
    SYNTAX      ClabWIFIRadioEntry
    MAX-ACCESS  not-accessible
    STATUS      current
    DESCRIPTION
        "The Conceptual row of clabWIFIRadioTable."
    INDEX {
            clabWIFIRadioId
          }
    ::= {clabWIFIRadioTable 1 }

ClabWIFIRadioEntry ::= SEQUENCE {
    clabWIFIRadioId
                 InterfaceIndex,
    clabWIFIRadioEnable
                 TruthValue,
    clabWIFIRadioStatus
                 INTEGER,
    clabWIFIRadioAlias
                 SnmpAdminString,
    clabWIFIRadioName
                 SnmpAdminString,
    clabWIFIRadioLastChange
                 Unsigned32,
    clabWIFIRadioLowerLayers
                 SnmpAdminString,
    clabWIFIRadioUpstream
                 TruthValue,
    clabWIFIRadioMaxBitRate
                 Unsigned32,
    clabWIFIRadioSupportedFrequencyBands
                 SnmpAdminString,
    clabWIFIRadioOperatingFrequencyBand
                 INTEGER,
    clabWIFIRadioSupportedStandards
                 SnmpAdminString,
    clabWIFIRadioOperatingStandards
                 INTEGER,
    clabWIFIRadioPossibleChannels
                 SnmpAdminString,
    clabWIFIRadioChannelsInUse
                 SnmpAdminString,
    clabWIFIRadioChannel
                 Unsigned32,
    clabWIFIRadioAutoChannelSupported
                 TruthValue,
    clabWIFIRadioAutoChannelEnable
                 TruthValue,
    clabWIFIRadioAutoChannelRefreshPeriod
                 Unsigned32,
    clabWIFIRadioOperatingChannelBandwidth
                 INTEGER,
    clabWIFIRadioExtensionChannel
                 INTEGER,
    clabWIFIRadioGuardInterval
                 INTEGER,
    clabWIFIRadioMCS
                 Integer32,
    clabWIFIRadioTransmitPowerSupported
                 SnmpAdminString,
    clabWIFIRadioTransmitPower
                 Unsigned32,
    clabWIFIRadioIEEE80211hSupported
                 TruthValue,
    clabWIFIRadioIEEE80211hEnabled
                 TruthValue,
    clabWIFIRadioRegulatoryDomain
                 SnmpAdminString,
    clabWIFIRadioNonContiguousChannel
                 Unsigned32,
    clabWIFIRadioCarrierSenseThresholdInUse
                 Integer32,
    clabWIFIRadioCarrierSenseThresholdRange
                 Integer32,
    clabWIFIRadioStatsChanUtilization
                 Unsigned32,
    clabWIFIRadioRtsCtsExchange
                 Integer32,
    clabWIFIRadioFrameAggregationLevel
                 Unsigned32,
    clabWIFIRadioThroughput
                 Unsigned32,
    clabWIFIRadioPktErrorRateSTA
                 PktErrorRateType,
    clabWIFIRadioRetryLimit
                 Unsigned32,
    clabWIFIRadioCCARequest
                 OCTET STRING,
    clabWIFIRadioRPIHistogramRequest
                 OCTET STRING,
    clabWIFIRadioFragmentationThreshold
                 Unsigned32,
    clabWIFIRadioRTSThreshold
                 Unsigned32,
    clabWIFIRadioLongRetryLimit
                 Unsigned32,
    clabWIFIRadioBeaconPeriod
                 Unsigned32,
    clabWIFIRadioDTIMPeriod
                 Unsigned32,
    clabWIFIRadioPacketAggregationEnable
                 TruthValue,
    clabWIFIRadioBasicDataTransmitRates
                 SnmpAdminString,
    clabWIFIRadioOperationalDataTransmitRates
                 SnmpAdminString,
    clabWIFIRadioSupportedDataTransmitRates
                 SnmpAdminString,
    clabWIFIRadioCarrierSenseThresholdRangeMin
                 Integer32,
    clabWIFIRadioCarrierSenseThresholdRangeMax
                 Integer32,
    clabWIFIRadioCCAReport
                 OCTET STRING,
    clabWIFIRadioRPIHistogramReport
                 OCTET STRING,
    clabWIFIRadioPreambleType
                 INTEGER
    }
clabWIFIRadioId    OBJECT-TYPE
    SYNTAX      InterfaceIndex 
    MAX-ACCESS  not-accessible
    STATUS      current
    DESCRIPTION
        "The key for a unique instance of this object. 
        This value corresponds to the Interface Index 
        (i.e., ifIndex in SMIv2). "
    ::= {clabWIFIRadioEntry 1 }

clabWIFIRadioEnable    OBJECT-TYPE
    SYNTAX      TruthValue 
    MAX-ACCESS  read-write
    STATUS      current
    DESCRIPTION
        "This object is defined in TR-181 Device.WiFi.Radio.{i}.Enable"
    REFERENCE
        "TR-181 Device Data Model for TR-069."
    ::= {clabWIFIRadioEntry 2 }

clabWIFIRadioStatus    OBJECT-TYPE
    SYNTAX      INTEGER  {
                           up(1),
                           down(2),
                           unknown(4),
                           dormant(5),
                           notPresent(6),
                           lowerLayerDown(7),
                           error(8)
                         }
    MAX-ACCESS  read-only
    STATUS      current
    DESCRIPTION
        "This object is defined in TR-181 Device.WiFi.Radio.{i}.Status."
    REFERENCE
        "TR-181 Device Data Model for TR-069."
    ::= {clabWIFIRadioEntry 3 }

clabWIFIRadioAlias    OBJECT-TYPE
    SYNTAX      SnmpAdminString (SIZE(0..64))
    MAX-ACCESS  read-write
    STATUS      current
    DESCRIPTION
        "This object is defined in TR-181 Device.WiFi.Radio.{i}.Alias."
    REFERENCE
        "TR-181 Device Data Model for TR-069."
    ::= {clabWIFIRadioEntry 4 }

clabWIFIRadioName    OBJECT-TYPE
    SYNTAX      SnmpAdminString (SIZE(0..64))
    MAX-ACCESS  read-only
    STATUS      current
    DESCRIPTION
        "This object is defined in TR-181 Device.WiFi.Radio.{i}.Name."
    REFERENCE
        "TR-181 Device Data Model for TR-069."
    ::= {clabWIFIRadioEntry 5 }

clabWIFIRadioLastChange    OBJECT-TYPE
    SYNTAX      Unsigned32 
    UNITS       "seconds"
    MAX-ACCESS  read-only
    STATUS      current
    DESCRIPTION
        "This object is defined in TR-181 Device.WiFi.Radio.{i}.LastChange."
    REFERENCE
        "TR-181 Device Data Model for TR-069."
    ::= {clabWIFIRadioEntry 6 }

clabWIFIRadioLowerLayers    OBJECT-TYPE
    SYNTAX      SnmpAdminString (SIZE(0..1024))
    MAX-ACCESS  read-write
    STATUS      current
    DESCRIPTION
        "This object is defined in TR-181 Device.WiFi.Radio.{i}.LowerLayers."
    REFERENCE
        "TR-181 Device Data Model for TR-069."
    ::= {clabWIFIRadioEntry 7 }

clabWIFIRadioUpstream    OBJECT-TYPE
    SYNTAX      TruthValue 
    MAX-ACCESS  read-only
    STATUS      current
    DESCRIPTION
        "This object is defined in TR-181 Device.WiFi.Radio.{i}.Upstream"
    REFERENCE
        "TR-181 Device Data Model for TR-069."
    ::= {clabWIFIRadioEntry 8 }

clabWIFIRadioMaxBitRate    OBJECT-TYPE
    SYNTAX      Unsigned32 
    UNITS       "Mbps"
    MAX-ACCESS  read-only
    STATUS      current
    DESCRIPTION
        "This object is defined in TR-181 Device.WiFi.Radio.{i}.MaxBitRate."
    REFERENCE
        "TR-181 Device Data Model for TR-069."
    ::= {clabWIFIRadioEntry 9 }

clabWIFIRadioSupportedFrequencyBands    OBJECT-TYPE
    SYNTAX      SnmpAdminString
    MAX-ACCESS  read-only
    STATUS      current
    DESCRIPTION
        "This object is defined in TR-181 Device.WiFi.RadioSupportedFrequencyBands."
    REFERENCE
        "TR-181 Device Data Model for TR-069."
    ::= {clabWIFIRadioEntry 10 }

clabWIFIRadioOperatingFrequencyBand    OBJECT-TYPE
    SYNTAX      INTEGER  {
                           n2dot4Ghz(1),
                           n5Ghz(2)
                         }
    MAX-ACCESS  read-write
    STATUS      current
    DESCRIPTION
        "This object is defined in TR-181 Device.WiFi.Radio.{i}.OperatingFrequencyBand"
    REFERENCE
        "TR-181 Device Data Model for TR-069."
    ::= {clabWIFIRadioEntry 11 }

clabWIFIRadioSupportedStandards    OBJECT-TYPE
    SYNTAX      SnmpAdminString
    MAX-ACCESS  read-only
    STATUS      current
    DESCRIPTION
        "This object is defined in TR-181 Device.WiFi.Radio.{i}.SupportedStandards"
    REFERENCE
        "TR-181 Device Data Model for TR-069."
    ::= {clabWIFIRadioEntry 12 }

clabWIFIRadioOperatingStandards    OBJECT-TYPE
    SYNTAX      INTEGER  {
                           a(1),
                           b(2),
                           g(3),
                           n(5),
                           ac(6)
                         }
    MAX-ACCESS  read-write
    STATUS      current
    DESCRIPTION
        "This object is modified from TR-181 Device.WiFi.Radio.{i}.OperatingStandards"
    REFERENCE
        "TR-181 Device Data Model for TR-069."
    ::= {clabWIFIRadioEntry 13 }

clabWIFIRadioPossibleChannels    OBJECT-TYPE
    SYNTAX      SnmpAdminString (SIZE(0..1024))
    MAX-ACCESS  read-only
    STATUS      current
    DESCRIPTION
        "This object is defined in TR-181 Device.WiFi.Radio.{i}.PossibleChannels"
    REFERENCE
        "TR-181 Device Data Model for TR-069."
    ::= {clabWIFIRadioEntry 14 }

clabWIFIRadioChannelsInUse    OBJECT-TYPE
    SYNTAX      SnmpAdminString (SIZE(0..1024))
    MAX-ACCESS  read-only
    STATUS      current
    DESCRIPTION
        "This object is defined in TR-181 Device.WiFi.Radio.{i}.ChannelsInUse"
    REFERENCE
        "TR-181 Device Data Model for TR-069."
    ::= {clabWIFIRadioEntry 15 }

clabWIFIRadioChannel    OBJECT-TYPE
    SYNTAX      Unsigned32 (1..255)
    MAX-ACCESS  read-write
    STATUS      current
    DESCRIPTION
        "This object is defined in TR-181 Device.WiFi.Radio.{i}.Channel.
         For 80MHz, 160MHz and 80+80MHz RF channels of 802.11ac, this 
         object indicates the Primary Channel of the RF channel."
    REFERENCE
        "TR-181 Device Data Model for TR-069."
    ::= {clabWIFIRadioEntry 16 }

clabWIFIRadioAutoChannelSupported    OBJECT-TYPE
    SYNTAX      TruthValue 
    MAX-ACCESS  read-only
    STATUS      current
    DESCRIPTION
        "This object is defined in TR-181 Device.WiFi.Radio.{i}.AutoChannelSupported"
    REFERENCE
        "TR-181 Device Data Model for TR-069."
    ::= {clabWIFIRadioEntry 17 }

clabWIFIRadioAutoChannelEnable    OBJECT-TYPE
    SYNTAX      TruthValue 
    MAX-ACCESS  read-write
    STATUS      current
    DESCRIPTION
        "This object is defined in TR-181 Device.WiFi.Radio.{i}.AutoChannelEnable"
    REFERENCE
        "TR-181 Device Data Model for TR-069."
    ::= {clabWIFIRadioEntry 18 }

clabWIFIRadioAutoChannelRefreshPeriod    OBJECT-TYPE
    SYNTAX      Unsigned32 
    UNITS       "seconds"
    MAX-ACCESS  read-write
    STATUS      current
    DESCRIPTION
        "This object is defined in TR-181 Device.WiFi.Radio.{i}.AutoChannelRefreshPeriod"
    REFERENCE
        "TR-181 Device Data Model for TR-069."
    ::= {clabWIFIRadioEntry 19 }

clabWIFIRadioOperatingChannelBandwidth    OBJECT-TYPE
    SYNTAX      INTEGER  {
                           n20MHz(1),
                           n40MHz(2),
                           ac80MHz(3),
                           ac160MHz(4),
                           ac80plus80MHz(5),
                           auto(6)
                         }
    MAX-ACCESS  read-write
    STATUS      current
    DESCRIPTION
        "This object is modified from TR-181 Device.WiFi.Radio.{i}.OperatingChannelBandwidth"
    REFERENCE
        "TR-181 Device Data Model for TR-069."
    DEFVAL      { auto }
    ::= {clabWIFIRadioEntry 20 }

clabWIFIRadioExtensionChannel    OBJECT-TYPE
    SYNTAX      INTEGER  {
                           aboveControlChannel(1),
                           belowControlChannel(2),
                           auto(3)
                         } 
    MAX-ACCESS  read-write
    STATUS      current
    DESCRIPTION
        "This object is defined in TR-181 Device.WiFi.Radio.{i}.ExtensionChannel"
    REFERENCE
        "TR-181 Device Data Model for TR-069."
    DEFVAL      { auto }
    ::= {clabWIFIRadioEntry 21 }

clabWIFIRadioGuardInterval    OBJECT-TYPE
    SYNTAX      INTEGER  {
                           n400nsec(1),
                           n800nsec(2),
                           auto(3)
                         }  
    MAX-ACCESS  read-write
    STATUS      current
    DESCRIPTION
        "This object is defined in TR-181 Device.WiFi.Radio.{i}.RadioGuardInterval"
    REFERENCE
        "TR-181 Device Data Model for TR-069."
    DEFVAL      { auto }
    ::= {clabWIFIRadioEntry 22 }

clabWIFIRadioMCS    OBJECT-TYPE
    SYNTAX      Integer32 (-1..31)
    MAX-ACCESS  read-write
    STATUS      current
    DESCRIPTION
        "This object is defined in TR-181 Device.WiFi.Radio.{i}.RadioMCS "
    REFERENCE
        "TR-181 Device Data Model for TR-069."
    ::= {clabWIFIRadioEntry 23 }

clabWIFIRadioTransmitPowerSupported    OBJECT-TYPE
    SYNTAX      SnmpAdminString (SIZE(0..64))
    MAX-ACCESS  read-only
    STATUS      current
    DESCRIPTION
        "This object is defined in TR-181 Device.WiFi.Radio.{i}.TransmitPowerSupported"
    REFERENCE
        "TR-181 Device Data Model for TR-069."
    ::= {clabWIFIRadioEntry 24 }

clabWIFIRadioTransmitPower    OBJECT-TYPE
    SYNTAX      Unsigned32 (1..100)
    UNITS       "percentage"
    MAX-ACCESS  read-write
    STATUS      current
    DESCRIPTION
        "This object is defined in TR-181 Device.WiFi.Radio.{i}.TransmitPower"
    REFERENCE
        "TR-181 Device Data Model for TR-069."
    ::= {clabWIFIRadioEntry 25 }

clabWIFIRadioIEEE80211hSupported    OBJECT-TYPE
    SYNTAX      TruthValue 
    MAX-ACCESS  read-only
    STATUS      current
    DESCRIPTION
        "This object is defined in TR-181 Device.WiFi.Radio.{i}.IEEE80211hSupported"
    REFERENCE
        "TR-181 Device Data Model for TR-069."
    ::= {clabWIFIRadioEntry 26 }

clabWIFIRadioIEEE80211hEnabled    OBJECT-TYPE
    SYNTAX      TruthValue 
    MAX-ACCESS  read-write
    STATUS      current
    DESCRIPTION
        "This object is defined in TR-181 Device.WiFi.Radio.{i}.IEEE80211hEnabled"
    REFERENCE
        "TR-181 Device Data Model for TR-069."
    ::= {clabWIFIRadioEntry 27 }

clabWIFIRadioRegulatoryDomain    OBJECT-TYPE
    SYNTAX      SnmpAdminString 
    MAX-ACCESS  read-write
    STATUS      current
    DESCRIPTION
        "This object is defined in TR-181 Device.WiFi.Radio.{i}.RegulatoryDomain"
    REFERENCE
        "TR-181 Device Data Model for TR-069."
    ::= {clabWIFIRadioEntry 28 }

clabWIFIRadioNonContiguousChannel    OBJECT-TYPE
    SYNTAX      Unsigned32 (1..255) 
    MAX-ACCESS  read-write
    STATUS      current
    DESCRIPTION
        "This object is defined for the Noncontiguous 80+80Mhz channels
         only. It indicates the center of the second 80Mhz subchannel."
    REFERENCE
        "IEEE 802.11ac standard."
    ::= {clabWIFIRadioEntry 29 }
    
clabWIFIRadioCarrierSenseThresholdInUse    OBJECT-TYPE
    SYNTAX      Integer32
    UNITS       "dBm" 
    MAX-ACCESS  read-write
    STATUS      current
    DESCRIPTION
        "This object is the RSSI signal level at which CS/CCA detects a 
         busy condition. This attribute enables APs to increase minimum 
         sensitivity to avoid detecting busy condition from 
         multiple/weak Wi-Fi sources in dense Wi-Fi environments."
    ::= {clabWIFIRadioEntry 30 }

clabWIFIRadioCarrierSenseThresholdRange    OBJECT-TYPE
    SYNTAX      Integer32
    UNITS       "dBm" 
    MAX-ACCESS  read-only
    STATUS      deprecated
    DESCRIPTION
        "This object indicates the Carrier Sense ranges supported by
         the radio."
    ::= {clabWIFIRadioEntry 31 }

clabWIFIRadioStatsChanUtilization    OBJECT-TYPE
    SYNTAX      Unsigned32
    MAX-ACCESS  read-only
    STATUS      deprecated
    DESCRIPTION
        "This object indicates the fraction of the time AP senses a busy
         channel or transmits frames. This object provides visibility
         into channel capacity."
    ::= {clabWIFIRadioEntry 32 }

clabWIFIRadioRtsCtsExchange    OBJECT-TYPE
    SYNTAX      Integer32
    UNITS       "bytes"
    MAX-ACCESS  read-write
    STATUS      current
    DESCRIPTION
        "This object allows configuring the RTS/CTS parameters."
    ::= {clabWIFIRadioEntry 33 }

clabWIFIRadioFrameAggregationLevel    OBJECT-TYPE
    SYNTAX      Unsigned32
    UNITS       "frames"
    MAX-ACCESS  read-write
    STATUS      deprecated
    DESCRIPTION
        "This object allows configuring the frame aggregation level 
         depending on how dense the network is. For example, if the 
         network is not congested, then a large number of frames can 
         be aggregated and sent."
    ::= {clabWIFIRadioEntry 34 }

clabWIFIRadioThroughput    OBJECT-TYPE
    SYNTAX      Unsigned32
    UNITS       "Mbps" 
    MAX-ACCESS  read-only
    STATUS      deprecated
    DESCRIPTION
        "This object indicates the throughput expressed in Mbps."
    ::= {clabWIFIRadioEntry 35 }

clabWIFIRadioPktErrorRateSTA    OBJECT-TYPE
    SYNTAX      PktErrorRateType
    MAX-ACCESS  read-only
    STATUS      deprecated
    DESCRIPTION
        "This object indicates the traffic quality (e.g., HTTP, TCP) 
         of an STA."
    ::= {clabWIFIRadioEntry 36 }

clabWIFIRadioRetryLimit    OBJECT-TYPE
    SYNTAX      Unsigned32 (0..7)
    MAX-ACCESS  read-only
    STATUS      current
    DESCRIPTION
        "This object is defined in TR-181 Device.WiFi.Radio.{i}.RetryLimit."
    ::= {clabWIFIRadioEntry 37 }

clabWIFIRadioCCARequest      OBJECT-TYPE
    SYNTAX      OCTET STRING (SIZE(11))
    MAX-ACCESS  read-only
    STATUS      current
    DESCRIPTION
        "This object is defined in TR-181 Device.WiFi.Radio.{i}.CCARequest."
    ::= {clabWIFIRadioEntry 38 }

clabWIFIRadioRPIHistogramRequest   OBJECT-TYPE
    SYNTAX      OCTET STRING (SIZE(11))
    MAX-ACCESS  read-only
    STATUS      current
    DESCRIPTION
        "This object is defined in TR-181 Device.WiFi.Radio.{i}.RPIHistogramRequest."
    ::= {clabWIFIRadioEntry 39 }

clabWIFIRadioFragmentationThreshold    OBJECT-TYPE
    SYNTAX      Unsigned32
    MAX-ACCESS  read-only
    STATUS      current
    DESCRIPTION
        "This object is defined in TR-181   
         Device.WiFi.Radio.{i}.FragmentationThreshold."
    ::= {clabWIFIRadioEntry 40 }

clabWIFIRadioRTSThreshold    OBJECT-TYPE
    SYNTAX      Unsigned32
    MAX-ACCESS  read-only
    STATUS      current
    DESCRIPTION
        "This object is defined in TR-181 Device.WiFi.Radio.{i}.RTSThreshold."
    ::= {clabWIFIRadioEntry 41 }

clabWIFIRadioLongRetryLimit    OBJECT-TYPE
    SYNTAX      Unsigned32
    MAX-ACCESS  read-only
    STATUS      current
    DESCRIPTION
        "This object is defined in TR-181 Device.WiFi.Radio.{i}.RetryLimit."
    ::= {clabWIFIRadioEntry 42 }

clabWIFIRadioBeaconPeriod    OBJECT-TYPE
    SYNTAX      Unsigned32
    MAX-ACCESS  read-only
    STATUS      current
    DESCRIPTION
        "This object is defined in TR-181 Device.WiFi.Radio.{i}.BeaconPeriod."
    ::= {clabWIFIRadioEntry 43 }

clabWIFIRadioDTIMPeriod    OBJECT-TYPE
    SYNTAX      Unsigned32
    MAX-ACCESS  read-only
    STATUS      current
    DESCRIPTION
        "This object is defined in TR-181 Device.WiFi.Radio.{i}.DTIMPeriod."
    ::= {clabWIFIRadioEntry 44 }

clabWIFIRadioPacketAggregationEnable    OBJECT-TYPE
    SYNTAX      TruthValue
    MAX-ACCESS  read-only
    STATUS      current
    DESCRIPTION
        "This object is defined in TR-181 Device.WiFi.Radio.{i}.
         PacketAggregationEnable."
    ::= {clabWIFIRadioEntry 45 }

clabWIFIRadioBasicDataTransmitRates    OBJECT-TYPE
    SYNTAX      SnmpAdminString
    MAX-ACCESS  read-only
    STATUS      current
    DESCRIPTION
        "This object is defined in TR-181 
         Device.WiFi.Radio.{i}.BasicDataTransmitRates."
    ::= {clabWIFIRadioEntry 46 }

clabWIFIRadioOperationalDataTransmitRates    OBJECT-TYPE
    SYNTAX      SnmpAdminString
    MAX-ACCESS  read-only
    STATUS      current
    DESCRIPTION
        "This object is defined in TR-181 
         Device.WiFi.Radio.{i}.OperationalDataTransmitRates."
    ::= {clabWIFIRadioEntry 47 }

clabWIFIRadioSupportedDataTransmitRates    OBJECT-TYPE
    SYNTAX      SnmpAdminString
    MAX-ACCESS  read-only
    STATUS      current
    DESCRIPTION
        "This object is defined in TR-181 Device.WiFi.Radio.{i}.
         SupportedDataTransmitRates."
    ::= {clabWIFIRadioEntry 48 }

clabWIFIRadioCarrierSenseThresholdRangeMin    OBJECT-TYPE
    SYNTAX      Integer32
    UNITS       "dBm" 
    MAX-ACCESS  read-only
    STATUS      current
    DESCRIPTION
        "Indicates the minimum Carrier Sense threshold level supported by the radio."
    ::= {clabWIFIRadioEntry 49 }

clabWIFIRadioCarrierSenseThresholdRangeMax    OBJECT-TYPE
    SYNTAX      Integer32
    UNITS       "dBm" 
    MAX-ACCESS  read-only
    STATUS      current
    DESCRIPTION
        "Indicates the maximum Carrier Sense threshold level supported by the radio."
    ::= {clabWIFIRadioEntry 50 }

clabWIFIRadioCCAReport      OBJECT-TYPE
    SYNTAX      OCTET STRING (SIZE(12))
    MAX-ACCESS  read-only
    STATUS      current
    DESCRIPTION
        "This object is defined in TR-181 Device.WiFi.Radio.{i}.CCAReport."
    ::= {clabWIFIRadioEntry 51 }

clabWIFIRadioRPIHistogramReport   OBJECT-TYPE
    SYNTAX      OCTET STRING (SIZE(19))
    MAX-ACCESS  read-only
    STATUS      current
    DESCRIPTION
        "This object is defined in TR-181 Device.WiFi.Radio.{i}.RPIHistogramReport."
    ::= {clabWIFIRadioEntry 52 }

clabWIFIRadioPreambleType    OBJECT-TYPE
    SYNTAX      INTEGER  {
    			    short(1),
			    long(2),
			    auto(3)
			 }
    MAX-ACCESS  read-only
    STATUS      current
    DESCRIPTION
        "This object is defined in TR-181 Device.WiFi.Radio.{i}.
         PreambleType."
    ::= {clabWIFIRadioEntry 53 }

clabWIFIRadioStatsTable OBJECT-TYPE
    SYNTAX      SEQUENCE OF ClabWIFIRadioStatsEntry
    MAX-ACCESS  not-accessible
    STATUS      current
    DESCRIPTION
        "This object is defined in TR-181 Device.WiFi.Radio.{i}.Stats."
    REFERENCE
        "TR-181 Device Data Model for TR-069."
    ::= {clabWIFIObjects 3 }

clabWIFIRadioStatsEntry    OBJECT-TYPE
    SYNTAX      ClabWIFIRadioStatsEntry
    MAX-ACCESS  not-accessible
    STATUS      current
    DESCRIPTION
        "The Conceptual row of clabWIFIRadioStatsTable."
    REFERENCE
        "TR-181 Issue 2"
    INDEX {
            clabWIFIRadioId
          }
    ::= {clabWIFIRadioStatsTable 1 }

ClabWIFIRadioStatsEntry ::= SEQUENCE {
    clabWIFIRadioStatsBytesSent
                 Counter64,
    clabWIFIRadioStatsBytesReceived
                 Counter64,
    clabWIFIRadioStatsPacketsSent
                 Counter64,
    clabWIFIRadioStatsPacketsReceived
                 Counter64,
    clabWIFIRadioStatsErrorsSent
                 Counter32,
    clabWIFIRadioStatsErrorsReceived
                 Counter32,
    clabWIFIRadioStatsDiscardPacketsSent
                 Counter32,
    clabWIFIRadioStatsDiscardPacketsReceived
                 Counter32,
    clabWIFIRadioStatsPLCPErrorCount
                 Counter32, 
    clabWIFIRadioStatsFCSErrorCount
                 Counter32, 
    clabWIFIRadioStatsInvalidMACCount
                 Counter32, 
    clabWIFIRadioStatsPacketsOtherReceived
                 Counter32,
    clabWIFIRadioStatsNoise
                 Integer32,
    clabWIFIRadioStatsFramesRetransmissionsSent 
                 Counter64, 
    clabWIFIRadioStatsFramesDuplicatedReceived  
                 Counter64,
    clabWIFIRadioStatsChannelUtilization
                 Unsigned32     
      }

clabWIFIRadioStatsBytesSent    OBJECT-TYPE
    SYNTAX      Counter64 
    MAX-ACCESS  read-only
    STATUS      current
    DESCRIPTION
        "This object is defined in TR-181 Device.WiFi.Radio.{i}.Stats.BytesSent."
    REFERENCE
        "TR-181 Device Data Model for TR-069."
    ::= {clabWIFIRadioStatsEntry 1 }

clabWIFIRadioStatsBytesReceived    OBJECT-TYPE
    SYNTAX      Counter64 
    MAX-ACCESS  read-only
    STATUS      current
    DESCRIPTION
        "This object is defined in TR-181 Device.WiFi.Radio.{i}.Stats.BytesReceived."
    REFERENCE
        "TR-181 Device Data Model for TR-069."
    ::= {clabWIFIRadioStatsEntry 2 }

clabWIFIRadioStatsPacketsSent    OBJECT-TYPE
    SYNTAX      Counter64 
    MAX-ACCESS  read-only
    STATUS      current
    DESCRIPTION
        "This object is defined in TR-181 Device.WiFi.Radio.{i}.Stats.PacketsSent."
    REFERENCE
        "TR-181 Device Data Model for TR-069."
    ::= {clabWIFIRadioStatsEntry 3 }

clabWIFIRadioStatsPacketsReceived    OBJECT-TYPE
    SYNTAX      Counter64 
    MAX-ACCESS  read-only
    STATUS      current
    DESCRIPTION
        "This object is defined in TR-181 Device.WiFi.Radio.{i}.Stats.PacketsReceived."
    REFERENCE
        "TR-181 Device Data Model for TR-069."
    ::= {clabWIFIRadioStatsEntry 4 }

clabWIFIRadioStatsErrorsSent    OBJECT-TYPE
    SYNTAX      Counter32 
    MAX-ACCESS  read-only
    STATUS      current
    DESCRIPTION
        "This object is defined in TR-181 Device.WiFi.Radio.{i}.Stats.ErrorsSent."
    REFERENCE
        "TR-181 Device Data Model for TR-069."
    ::= {clabWIFIRadioStatsEntry 5 }

clabWIFIRadioStatsErrorsReceived    OBJECT-TYPE
    SYNTAX      Counter32 
    MAX-ACCESS  read-only
    STATUS      current
    DESCRIPTION
        "This object is defined in TR-181 Device.WiFi.Radio.{i}.Stats.ErrorsReceived."
    REFERENCE
        "TR-181 Device Data Model for TR-069."
    ::= {clabWIFIRadioStatsEntry 6 }

clabWIFIRadioStatsDiscardPacketsSent    OBJECT-TYPE
    SYNTAX      Counter32 
    MAX-ACCESS  read-only
    STATUS      current
    DESCRIPTION
        "This object is defined in TR-181 Device.WiFi.Radio.{i}.Stats.DiscardPacketsSent."
    REFERENCE
        "TR-181 Device Data Model for TR-069."
    ::= {clabWIFIRadioStatsEntry 7 }

clabWIFIRadioStatsDiscardPacketsReceived    OBJECT-TYPE
    SYNTAX      Counter32 
    MAX-ACCESS  read-only
    STATUS      current
    DESCRIPTION
        "This object is defined in TR-181 Device.WiFi.Radio.{i}.Stats.DiscardPacketsReceived."
    REFERENCE
        "TR-181 Device Data Model for TR-069."
    ::= {clabWIFIRadioStatsEntry 8 }

clabWIFIRadioStatsPLCPErrorCount   OBJECT-TYPE
    SYNTAX      Counter32 
    MAX-ACCESS  read-only
    STATUS      current
    DESCRIPTION
        "This object is defined in TR-181 Device.WiFi.Radio.{i}.
        Stats.PLCPErrorCount."
    REFERENCE
        "TR-181 Device Data Model for TR-069."
    ::= {clabWIFIRadioStatsEntry 9 }

clabWIFIRadioStatsFCSErrorCount   OBJECT-TYPE
    SYNTAX      Counter32 
    MAX-ACCESS  read-only
    STATUS      current
    DESCRIPTION
        "This object is defined in TR-181 Device.WiFi.Radio.{i}.
        Stats.FCSErrorCount."
    REFERENCE
        "TR-181 Device Data Model for TR-069."
    ::= {clabWIFIRadioStatsEntry 10 }

clabWIFIRadioStatsInvalidMACCount   OBJECT-TYPE
    SYNTAX      Counter32 
    MAX-ACCESS  read-only
    STATUS      current
    DESCRIPTION
        "This object is defined in TR-181 Device.WiFi.Radio.{i}.
        Stats.InvalidMACCount."
    REFERENCE
        "TR-181 Device Data Model for TR-069."
    ::= {clabWIFIRadioStatsEntry 11 }

clabWIFIRadioStatsPacketsOtherReceived   OBJECT-TYPE
    SYNTAX      Counter32 
    MAX-ACCESS  read-only
    STATUS      current
    DESCRIPTION
        "This object is defined in TR-181 Device.WiFi.Radio.{i}.
        Stats.PacketsOtherReceived."
    REFERENCE
        "TR-181 Device Data Model for TR-069."
    ::= {clabWIFIRadioStatsEntry 12 }

clabWIFIRadioStatsNoise    OBJECT-TYPE
    SYNTAX      Integer32 
    UNITS       "dBm"
    MAX-ACCESS  read-only
    STATUS      current
    DESCRIPTION
        " An indicator of average noise strength received at this radio, 
          measured in dBm. This measurement of non-IEEE 802.11 noise power 
          is made by sampling the channel when virtual carrier sense 
          indicates idle and this radio is neither transmitting nor 
          receiving a frame."
    ::= { clabWIFIRadioStatsEntry 13 }

clabWIFIRadioStatsFramesRetransmissionsSent    OBJECT-TYPE
    SYNTAX      Counter64 
    UNITS       "frames"
    MAX-ACCESS  read-only
    STATUS      current
    DESCRIPTION
        " The FramesRetransmissionsSent parameter indicates the total 
          number of frames retransmitted out of the interface (marked 
          as duplicated). The value of this counter MAY be reset to
          zero when the CPE is rebooted."
    ::= { clabWIFIRadioStatsEntry 14 }

clabWIFIRadioStatsFramesDuplicatedReceived  OBJECT-TYPE
    SYNTAX      Counter64 
    UNITS       "frames"
    MAX-ACCESS  read-only
    STATUS      current
    DESCRIPTION
        " The FramesDuplicatedReceived indicated the total number of 
          duplicated frames received on this interface. The value of 
          this counter MAY be reset to zero when the CPE is rebooted."
      ::= { clabWIFIRadioStatsEntry 15 }

clabWIFIRadioStatsChannelUtilization  OBJECT-TYPE
    SYNTAX      Unsigned32 (1..100)
    UNITS       "percentage"
    MAX-ACCESS  read-only
    STATUS      current
    DESCRIPTION
        " Report WIFI Radio Stats Channel Utilization. The fraction of
          the time AP senses a busy channel or transmits frames. 
          Provides visibility into channel capacity."
    ::= { clabWIFIRadioStatsEntry 16 }

clabWIFIRadioChannelWiFiDiagnostics OBJECT IDENTIFIER
    ::= {clabWIFIObjects 22 }

clabWIFIRadioChannelWiFiDiagnosticsState OBJECT-TYPE
    SYNTAX      INTEGER {
                         none(1),
                         requested(2),
                         completed(3),
                         error(4)
                        }
    MAX-ACCESS  read-only
    STATUS      current
    DESCRIPTION
        "Indicates availability of WiFi SSID data."       
    ::= { clabWIFIRadioChannelWiFiDiagnostics 1 }
    
clabWIFIRadioChannelWiFiDiagnosticsLastRunTimestamp OBJECT-TYPE
    SYNTAX      DateAndTime
    MAX-ACCESS  read-only
    STATUS      current
    DESCRIPTION
        "Timestamp when the last diagnostic was completed."     
    ::= { clabWIFIRadioChannelWiFiDiagnostics 2 }

clabWIFIRadioChannelWiFiDiagnosticsResultNumberOfEntries OBJECT-TYPE
    SYNTAX      Unsigned32
    MAX-ACCESS  read-only
    STATUS      current
    DESCRIPTION
        "The number of entries in the clabWIFIRadioChannelWiFiDiagnosticsResultsTable."       
    ::= { clabWIFIRadioChannelWiFiDiagnostics 3 }
    
clabWIFIRadioChannelWiFiDiagnosticsResultsTable OBJECT-TYPE
    SYNTAX      SEQUENCE OF ClabWIFIRadioChannelWiFiDiagnosticsResultsEntry
    MAX-ACCESS  not-accessible
    STATUS      current
    DESCRIPTION
        "This table contains the results of a RadioChannelWiFiDiagnostics
         execution."
    ::= { clabWIFIRadioChannelWiFiDiagnostics 4 }

clabWIFIRadioChannelWiFiDiagnosticsResultsEntry   OBJECT-TYPE
    SYNTAX      ClabWIFIRadioChannelWiFiDiagnosticsResultsEntry
    MAX-ACCESS  not-accessible
    STATUS      current
    DESCRIPTION
        "The Conceptual row of ClabWIFIRadioChannelWiFiDiagnosticsResultsEntry."
    INDEX {
            clabWIFIRadioChannelWiFiDiagnosticsResultsChannel
          }
    ::= { clabWIFIRadioChannelWiFiDiagnosticsResultsTable 1 }

ClabWIFIRadioChannelWiFiDiagnosticsResultsEntry ::= SEQUENCE {
    clabWIFIRadioChannelWiFiDiagnosticsResultsChannel
                 Unsigned32,
    clabWIFIRadioChannelWiFiDiagnosticsResultsBandwidth
                 INTEGER,
    clabWIFIRadioChannelWiFiDiagnosticsResultsAvailableCapacity
                 Unsigned32,
    clabWIFIRadioChannelWiFiDiagnosticsResultsNonWiFi
                 Unsigned32,
    clabWIFIRadioChannelWiFiDiagnosticsResultsNonWiFiClasses
                 SnmpAdminString,
    clabWIFIRadioChannelWiFiDiagnosticsResultsFrequencyBand
                 INTEGER                                                 
    }
clabWIFIRadioChannelWiFiDiagnosticsResultsChannel OBJECT-TYPE
    SYNTAX      Unsigned32  
    MAX-ACCESS  not-accessible
    STATUS      current
    DESCRIPTION
        "Channel number for which the current row's statistics refers."
    ::= { clabWIFIRadioChannelWiFiDiagnosticsResultsEntry 1 }
    
clabWIFIRadioChannelWiFiDiagnosticsResultsBandwidth OBJECT-TYPE
    SYNTAX      INTEGER {
                         mhz20(1),
                         mhz40(2),
                         mhz80(3),
                         mhz160(4)
                         }
    MAX-ACCESS  read-only
    STATUS      current
    DESCRIPTION
        "Indicates the bandwidth at which the channel is operating."
    ::= { clabWIFIRadioChannelWiFiDiagnosticsResultsEntry 2 } 

clabWIFIRadioChannelWiFiDiagnosticsResultsAvailableCapacity OBJECT-TYPE
    SYNTAX      Unsigned32 (1..100)
    UNITS       "percentage" 
    MAX-ACCESS  read-only
    STATUS      current
    DESCRIPTION
        "Percentage of total channel bandwidth available for use."
    ::= { clabWIFIRadioChannelWiFiDiagnosticsResultsEntry 3 }  
        
clabWIFIRadioChannelWiFiDiagnosticsResultsNonWiFi OBJECT-TYPE
    SYNTAX      Unsigned32 (1..100)
    UNITS       "percentage" 
    MAX-ACCESS  read-only
    STATUS      current
    DESCRIPTION
        "Percentage of total channel bandwidth occupied by non-WiFi interface."
    ::= { clabWIFIRadioChannelWiFiDiagnosticsResultsEntry 4 }  
    
clabWIFIRadioChannelWiFiDiagnosticsResultsNonWiFiClasses OBJECT-TYPE
    SYNTAX      SnmpAdminString
    MAX-ACCESS  read-only
    STATUS      current
    DESCRIPTION
        "Comma-separated list of strings. Each list item is an 
         enumeration of:  
         (Microwave, Bluetooth, Radar, Zigbee, etc)."
    ::= { clabWIFIRadioChannelWiFiDiagnosticsResultsEntry 5 }

clabWIFIRadioChannelWiFiDiagnosticsResultsFrequencyBand OBJECT-TYPE
    SYNTAX      INTEGER {
                         ghz24(1),
                         ghz5(2)
                        }
    MAX-ACCESS  read-only
    STATUS      current
    DESCRIPTION
        " Indicates the frequency band at which the radio of this SSID 
          instance is operating."
    ::= { clabWIFIRadioChannelWiFiDiagnosticsResultsEntry 6 }   

clabWIFINeighboringWiFiDiagnostics OBJECT IDENTIFIER
    ::= { clabWIFIObjects 21  }

clabWIFINeighboringWiFiDiagnosticsMode OBJECT-TYPE
    SYNTAX      INTEGER {
                         manual(1),
                         interval(2),
                         stop(3)
                        }
    MAX-ACCESS  read-write
    STATUS      current
    DESCRIPTION
        "This object allows the operator to initiate a single diagnostic
         Execution (manual), set periodic diagnostic executions at specified 
         interval (interval), or stop a scheduled periodic diagnostic (stop)."
    ::= { clabWIFINeighboringWiFiDiagnostics 1 }

clabWIFINeighboringWiFiDiagnosticsInterval OBJECT-TYPE
    SYNTAX      Unsigned32 (1..1440)
    MAX-ACCESS  read-write
    STATUS      current
    DESCRIPTION
 " The interval, in seconds, between channel scans when 
   DiagnosticMode is set to 'Interval."
    ::= { clabWIFINeighboringWiFiDiagnostics 2 }

clabWIFINeighboringWiFiDiagnosticsState OBJECT-TYPE
    SYNTAX      INTEGER {
                          none(1),
                          requested(2),
                          completed(3),
                          error(4)
                        }
    MAX-ACCESS  read-write
    STATUS      current
    DESCRIPTION
     "This object is defined in TR-181 Device.WiFi.NeighboringWiFiDiagnostic.DiagnosticsState "
    REFERENCE
        "TR-181 Device Data Model for TR-069."
    ::= { clabWIFINeighboringWiFiDiagnostics 3 }

clabWIFINeighboringWiFiDiagnosticsTableClear OBJECT-TYPE
    SYNTAX      TruthValue 
    MAX-ACCESS  read-write
    STATUS      current
    DESCRIPTION
     " Clears all entries in the clabWIFINeighborWiFiDiagnosticsResultsTable.  
       The agent will always return a value of false(2) when queried. "
    ::= { clabWIFINeighboringWiFiDiagnostics 4 }

clabWIFINeighboringWiFiDiagnosticsTableMaxNumberOfEntries OBJECT-TYPE
    SYNTAX      Unsigned32 
    MAX-ACCESS  read-write
    STATUS      current
    DESCRIPTION
     " Sets a maximum number of rows in this table.  If a new row is to 
       be written that would exceed the this maximum, the device must first
       delete the oldest row in the table. "
    ::= { clabWIFINeighboringWiFiDiagnostics 5 }

clabWIFINeighboringWiFiDiagnosticsResultTable OBJECT-TYPE
    SYNTAX      SEQUENCE OF ClabWIFINeighboringWiFiDiagnosticsResultEntry
    MAX-ACCESS  not-accessible
    STATUS      current
    DESCRIPTION
        "This object is defined in TR-181
         Device.WiFi.NeighboringWiFiDiagnostic.Result."
    REFERENCE
        "TR-181 Device Data Model for TR-069."
    ::= { clabWIFINeighboringWiFiDiagnostics 6 }

clabWIFINeighboringWiFiDiagnosticsResultEntry    OBJECT-TYPE
    SYNTAX      ClabWIFINeighboringWiFiDiagnosticsResultEntry
    MAX-ACCESS  not-accessible
    STATUS      current
    DESCRIPTION
        "The Conceptual row of clabWIFINeighboringWiFiDiagnosticsResultTable."
    INDEX {
            clabWIFIRadioId,
            clabWIFINeighboringWiFiDiagnosticsResultIndex
          }
    ::= { clabWIFINeighboringWiFiDiagnosticsResultTable 1 }

ClabWIFINeighboringWiFiDiagnosticsResultEntry ::= SEQUENCE {
    clabWIFINeighboringWiFiDiagnosticsResultIndex
                 Unsigned32,
    clabWIFINeighboringWiFiSSID
                 OCTET STRING,
    clabWIFINeighboringWiFiBSSID
                 MacAddress,
    clabWIFINeighboringWiFiMode
                 INTEGER,
    clabWIFINeighboringWiFiChannel
                 Unsigned32,
    clabWIFINeighboringWiFiSignalStrength
                 Integer32,
    clabWIFINeighboringWiFiSecurityModeEnabled
                 INTEGER,
    clabWIFINeighboringWiFiEncryptionMode
                 INTEGER,
    clabWIFINeighboringWiFiOperatingFrequencyBand
                 INTEGER,
    clabWIFINeighboringWiFiSupportedStandards
                 INTEGER,
    clabWIFINeighboringWiFiOperatingStandards
                 SnmpAdminString,
    clabWIFINeighboringWiFiOperatingChannelBandwidth
                 INTEGER,
    clabWIFINeighboringWiFiBeaconPeriod
                 Unsigned32,
    clabWIFINeighboringWiFiNoise
                 Integer32,
    clabWIFINeighboringWiFiBasicDataTransferRates
                 OCTET STRING,
    clabWIFINeighboringWiFiSupportedDataTransferRates
                 OCTET STRING,
    clabWIFINeighboringWiFiDTIMPeriod
                 Unsigned32,
    clabWIFINeighboringWiFiSidebandPosition
                 INTEGER,
    clabWIFINeighboringWiFiDiagnosticsLastRunTimestamp
                 DateAndTime,
    clabWIFINeighboringWiFiDiagnosticsNonContiguousChannel
                 Unsigned32
      }

clabWIFINeighboringWiFiDiagnosticsResultIndex OBJECT-TYPE
    SYNTAX      Unsigned32  
    MAX-ACCESS  not-accessible
    STATUS      current
    DESCRIPTION
        "Secondary index used to allow multiple Diagnostics to
         Be stored."
    ::= { clabWIFINeighboringWiFiDiagnosticsResultEntry 1 }

clabWIFINeighboringWiFiSSID OBJECT-TYPE
    SYNTAX      OCTET STRING (SIZE(1..32))
    MAX-ACCESS  read-only
    STATUS      current
    DESCRIPTION
        "This object is defined in TR-181
         Device.WiFi.NeighboringWiFiDiagnostic.Result.{i}.SSID"
    REFERENCE
        "TR-181 Device Data Model for TR-069."
    ::= { clabWIFINeighboringWiFiDiagnosticsResultEntry 2 }

clabWIFINeighboringWiFiBSSID OBJECT-TYPE
    SYNTAX      MacAddress
    MAX-ACCESS  read-only
    STATUS      current
    DESCRIPTION
        "This object is defined in TR-181
         Device.WiFi.NeighboringWiFiDiagnostic.Result.{i}.BSSID"
    REFERENCE
        "TR-181 Device Data Model for TR-069."
    ::= { clabWIFINeighboringWiFiDiagnosticsResultEntry 3 }

clabWIFINeighboringWiFiMode OBJECT-TYPE
    SYNTAX      INTEGER {
                          adhoc(1),
                          infrastructure(2)
                         }
    MAX-ACCESS  read-only
    STATUS      current
    DESCRIPTION
        "This object is defined in TR-181
         Device.WiFi.NeighboringWiFiDiagnostic.Result.{i}.Mode"
    REFERENCE
        "TR-181 Device Data Model for TR-069."
    ::= { clabWIFINeighboringWiFiDiagnosticsResultEntry 4 }

clabWIFINeighboringWiFiChannel  OBJECT-TYPE
    SYNTAX      Unsigned32 (1..255)
    MAX-ACCESS  read-only
    STATUS      current
    DESCRIPTION
        "This object is defined in TR-181
         Device.WiFi.NeighboringWiFiDiagnostic.Result.{i}.Channel"
    REFERENCE
        "TR-181 Device Data Model for TR-069."
    ::= { clabWIFINeighboringWiFiDiagnosticsResultEntry 5 }

clabWIFINeighboringWiFiSignalStrength  OBJECT-TYPE
    SYNTAX      Integer32 (-200..0)
    MAX-ACCESS  read-only
    STATUS      current
    DESCRIPTION
        "This object is defined in TR-181
         Device.WiFi.NeighboringWiFiDiagnostic.Result.{i}.SignalStrength"
    REFERENCE
        "TR-181 Device Data Model for TR-069."
    ::= { clabWIFINeighboringWiFiDiagnosticsResultEntry 6 }

clabWIFINeighboringWiFiSecurityModeEnabled  OBJECT-TYPE
    SYNTAX      INTEGER {
                   none(1), 
                   wep(2),
                   wpa(3),
                   wpa2(4),
                   wpawpa2(5),
                   wpaenterprise(6),
                   wpa2enterprise(7),
                   wpawpa2enterprise(8)
                         }

    MAX-ACCESS  read-only
    STATUS      current
    DESCRIPTION
        "This object is defined in TR-181
         Device.WiFi.NeighboringWiFiDiagnostic.Result.{i}.SecurityModeEnabled"
    REFERENCE
        "TR-181 Device Data Model for TR-069."
    ::= { clabWIFINeighboringWiFiDiagnosticsResultEntry 7 }

clabWIFINeighboringWiFiEncryptionMode  OBJECT-TYPE
    SYNTAX      INTEGER {
                    tkip(1), 
                    aes(2)
                        }
    MAX-ACCESS  read-only
    STATUS      current
    DESCRIPTION
        "This object is defined in TR-181
         Device.WiFi.NeighboringWiFiDiagnostic.Result.{i}.EncryptionMode"
    REFERENCE
        "TR-181 Device Data Model for TR-069."
    ::= { clabWIFINeighboringWiFiDiagnosticsResultEntry 8 }

clabWIFINeighboringWiFiOperatingFrequencyBand  OBJECT-TYPE
    SYNTAX      INTEGER {
                      ghz24(1), 
                      ghz5(2)
                        }
    MAX-ACCESS  read-only
    STATUS      current
    DESCRIPTION
        "This object is defined in TR-181
         Device.WiFi.NeighboringWiFiDiagnostic.Result.{i}.OperatingFrequencyBand"
    REFERENCE
        "TR-181 Device Data Model for TR-069."
    ::= { clabWIFINeighboringWiFiDiagnosticsResultEntry 9 }

clabWIFINeighboringWiFiSupportedStandards  OBJECT-TYPE
    SYNTAX      INTEGER  {
                           a(1),
                           b(2),
                           g(3),
                           n(4),
                           ac(5)
                         }
    MAX-ACCESS  read-only
    STATUS      current
    DESCRIPTION
        "This object is defined in TR-181
         Device.WiFi.NeighboringWiFiDiagnostic.Result.{i}.SupportedStandards"
    REFERENCE
        "TR-181 Device Data Model for TR-069."
    ::= { clabWIFINeighboringWiFiDiagnosticsResultEntry 10 }

clabWIFINeighboringWiFiOperatingStandards  OBJECT-TYPE
    SYNTAX      SnmpAdminString 
    MAX-ACCESS  read-only
    STATUS      current
    DESCRIPTION
        "This object is defined in TR-181
         Device.WiFi.NeighboringWiFiDiagnostic.Result.{i}.OperatingStandards"
    REFERENCE
        "TR-181 Device Data Model for TR-069."
    ::= { clabWIFINeighboringWiFiDiagnosticsResultEntry 11 }

clabWIFINeighboringWiFiOperatingChannelBandwidth  OBJECT-TYPE
    SYNTAX      INTEGER  {
                           mHz20 (1),
                           mHz40(2),
                           mHz80 (3),
                           mHz160(4),
                           mHz80plus80(5),
                           auto(8)
                         }

    MAX-ACCESS  read-only
    STATUS      current
    DESCRIPTION
        "This object is defined in TR-181
         Device.WiFi.NeighboringWiFiDiagnostic.Result.{i}.OperatingChannelBandwidth"
    REFERENCE
        "TR-181 Device Data Model for TR-069."
    ::= { clabWIFINeighboringWiFiDiagnosticsResultEntry 12 }

clabWIFINeighboringWiFiBeaconPeriod  OBJECT-TYPE
    SYNTAX      Unsigned32 
    MAX-ACCESS  read-only
    STATUS      current
    DESCRIPTION
        "This object is defined in TR-181
         Device.WiFi.NeighboringWiFiDiagnostic.Result.{i}.BeaconPeriod"
    REFERENCE
        "TR-181 Device Data Model for TR-069."
    ::= { clabWIFINeighboringWiFiDiagnosticsResultEntry 13 }

clabWIFINeighboringWiFiNoise  OBJECT-TYPE
    SYNTAX      Integer32 (-200..0) 
    MAX-ACCESS  read-only
    STATUS      current
    DESCRIPTION
        "This object is defined in TR-181
         Device.WiFi.NeighboringWiFiDiagnostic.Result.{i}.Noise"
    REFERENCE
        "TR-181 Device Data Model for TR-069."
    ::= { clabWIFINeighboringWiFiDiagnosticsResultEntry 14 }

clabWIFINeighboringWiFiBasicDataTransferRates  OBJECT-TYPE
    SYNTAX      OCTET STRING (SIZE(0..256)) 
    MAX-ACCESS  read-only
    STATUS      current
    DESCRIPTION
        "This object is defined in TR-181
         Device.WiFi.NeighboringWiFiDiagnostic.Result.{i}.BasicDataTransferRates"
    REFERENCE
        "TR-181 Device Data Model for TR-069."
    ::= { clabWIFINeighboringWiFiDiagnosticsResultEntry 15 }

clabWIFINeighboringWiFiSupportedDataTransferRates  OBJECT-TYPE
    SYNTAX      OCTET STRING (SIZE(0..256)) 
    MAX-ACCESS  read-only
    STATUS      current
    DESCRIPTION
        "This object is defined in TR-181
         Device.WiFi.NeighboringWiFiDiagnostic.Result.{i}.SupportedDataTransferRates"
    REFERENCE
        "TR-181 Device Data Model for TR-069."
    ::= { clabWIFINeighboringWiFiDiagnosticsResultEntry 16 }

clabWIFINeighboringWiFiDTIMPeriod  OBJECT-TYPE
    SYNTAX      Unsigned32 
    MAX-ACCESS  read-only
    STATUS      current
    DESCRIPTION
        "This object is defined in TR-181
         Device.WiFi.NeighboringWiFiDiagnostic.Result.{i}.DTIMPeriod"
    REFERENCE
        "TR-181 Device Data Model for TR-069."
    ::= { clabWIFINeighboringWiFiDiagnosticsResultEntry 17 }

clabWIFINeighboringWiFiSidebandPosition  OBJECT-TYPE
    SYNTAX      INTEGER  {
                          upper(1),
                          lower(2)
                         }
    MAX-ACCESS  read-only
    STATUS      current
    DESCRIPTION
        " The position of the sideband in case the bandwidth of 
          the measured service set is 40 MHz."
    REFERENCE
        "TR-181 Device Data Model for TR-069."
    ::= { clabWIFINeighboringWiFiDiagnosticsResultEntry 18 }

clabWIFINeighboringWiFiDiagnosticsLastRunTimestamp OBJECT-TYPE
    SYNTAX      DateAndTime
    MAX-ACCESS  read-only
    STATUS      current
    DESCRIPTION
        " Timestamp when the channel Diagnostic was executed."
    ::= { clabWIFINeighboringWiFiDiagnosticsResultEntry 19 }

clabWIFINeighboringWiFiDiagnosticsNonContiguousChannel    OBJECT-TYPE
    SYNTAX      Unsigned32 (1..255) 
    MAX-ACCESS  read-write
    STATUS      current
    DESCRIPTION
        "This object is defined for the Noncontiguous 80+80Mhz channels
         only. It indicates the center of the second 80Mhz subchannel."
    REFERENCE
        "IEEE 802.11ac standard."
    ::= { clabWIFINeighboringWiFiDiagnosticsResultEntry 20 }

clabWIFINeighboringWiFiDiagnosticsResultNumberOfEntries OBJECT-TYPE
    SYNTAX      Unsigned32
    MAX-ACCESS  read-only
    STATUS      current
    DESCRIPTION
        "The number of entries in the clabWIFINeighboringWiFiDiagnosticsResultTable."       
    ::= { clabWIFINeighboringWiFiDiagnostics 7 }
    
clabWIFISSIDTable OBJECT-TYPE
    SYNTAX      SEQUENCE OF ClabWIFISSIDEntry
    MAX-ACCESS  not-accessible
    STATUS      current
    DESCRIPTION
        "This object is defined in TR-181 Device.WiFi.SSID{i}."
    REFERENCE
        "TR-181 Device Data Model for TR-069."
    ::= {clabWIFIObjects 4 }

clabWIFISSIDEntry    OBJECT-TYPE
    SYNTAX      ClabWIFISSIDEntry
    MAX-ACCESS  not-accessible
    STATUS      current
    DESCRIPTION
        "The Conceptual row of clabWIFISSIDTable."
    INDEX {
            clabWIFISSIDId
          }
    ::= {clabWIFISSIDTable 1 }

ClabWIFISSIDEntry ::= SEQUENCE {
    clabWIFISSIDId
                 InterfaceIndex,
    clabWIFISSIDEnable
                 TruthValue,
    clabWIFISSIDStatus
                 INTEGER,
    clabWIFISSIDAlias
                 SnmpAdminString,
    clabWIFISSIDName
                 SnmpAdminString,
    clabWIFISSIDLastChange
                 Unsigned32,
    clabWIFISSIDLowerLayers
                 SnmpAdminString,
    clabWIFISSIDBSSID
                 MacAddress,
    clabWIFISSIDMACAddress
                 MacAddress,
    clabWIFISSIDSSID
                 SnmpAdminString,
    clabWIFISSIDRowStatus
                 RowStatus,
    clabWIFISSIDFragmentationEnable
                 TruthValue,
    clabWIFISSIDPeriodicStatsNumberOfEntries 
                 Integer32
    }

clabWIFISSIDId    OBJECT-TYPE
    SYNTAX      InterfaceIndex 
    MAX-ACCESS  not-accessible
    STATUS      current
    DESCRIPTION
        "The key for a unique instance of this object. 
        This value corresponds to the Interface Index 
        (i.e., ifIndex in SMIv2). "
    ::= {clabWIFISSIDEntry 1 }

clabWIFISSIDEnable    OBJECT-TYPE
    SYNTAX      TruthValue 
    MAX-ACCESS  read-create
    STATUS      current
    DESCRIPTION
        "This object is defined in TR-181 Device.WiFi.SSID{i}.Enable."
    REFERENCE
        "TR-181 Device Data Model for TR-069."
    ::= {clabWIFISSIDEntry 2 }

clabWIFISSIDStatus    OBJECT-TYPE
    SYNTAX      INTEGER  {
                           up(1),
                           down(2),
                           unknown(4),
                           dormant(5),
                           notPresent(6),
                           lowerLayerDown(7),
                           error(8)
                         }
    MAX-ACCESS  read-only
    STATUS      current
    DESCRIPTION
        "This object is defined in TR-181 Device.WiFi.SSID{i}.Status."
    REFERENCE
        "TR-181 Device Data Model for TR-069."
    ::= {clabWIFISSIDEntry 3 }

clabWIFISSIDAlias    OBJECT-TYPE
    SYNTAX      SnmpAdminString (SIZE(0..64)) 
    MAX-ACCESS  read-create
    STATUS      current
    DESCRIPTION
        "This object is defined in TR-181 Device.WiFi.SSID{i}.Alias."
    REFERENCE
        "TR-181 Device Data Model for TR-069."
    ::= {clabWIFISSIDEntry 4 }

clabWIFISSIDName    OBJECT-TYPE
    SYNTAX      SnmpAdminString (SIZE(0..64)) 
    MAX-ACCESS  read-only
    STATUS      current
    DESCRIPTION
        "This object is defined in TR-181 Device.WiFi.SSID{i}.Name."
    REFERENCE
        "TR-181 Device Data Model for TR-069."    ::= {clabWIFISSIDEntry 5 }

clabWIFISSIDLastChange    OBJECT-TYPE
    SYNTAX      Unsigned32 
    UNITS       "seconds"
    MAX-ACCESS  read-only
    STATUS      current
    DESCRIPTION
        "This object is defined in TR-181 Device.WiFi.SSID{i}.LastChange."
    REFERENCE
        "TR-181 Device Data Model for TR-069."
    ::= {clabWIFISSIDEntry 6 }

clabWIFISSIDLowerLayers    OBJECT-TYPE
    SYNTAX      SnmpAdminString (SIZE(0..1024))
    MAX-ACCESS  read-create
    STATUS      current
    DESCRIPTION
        "This object is defined in TR-181 Device.WiFi.SSID{i}.LowerLayers."
    REFERENCE
        "TR-181 Device Data Model for TR-069."
    ::= {clabWIFISSIDEntry 7 }

clabWIFISSIDBSSID    OBJECT-TYPE
    SYNTAX      MacAddress 
    MAX-ACCESS  read-only
    STATUS      current
    DESCRIPTION
        "This object is defined in TR-181 Device.WiFi.SSID{i}.BSSID."
    REFERENCE
        "TR-181 Device Data Model for TR-069."
    ::= {clabWIFISSIDEntry 8 }

clabWIFISSIDMACAddress    OBJECT-TYPE
    SYNTAX      MacAddress 
    MAX-ACCESS  read-only
    STATUS      current
    DESCRIPTION
        "This object is defined in TR-181 Device.WiFi.SSID{i}.MACAddress."
    REFERENCE
        "TR-181 Device Data Model for TR-069."
    ::= {clabWIFISSIDEntry 9 }

clabWIFISSIDSSID    OBJECT-TYPE
    SYNTAX      SnmpAdminString (SIZE(0..32))
    MAX-ACCESS  read-create
    STATUS      current
    DESCRIPTION
        "This object is defined in TR-181 Device.WiFi.SSID{i}.SSID."
    REFERENCE
        "TR-181 Device Data Model for TR-069."
    ::= {clabWIFISSIDEntry 10 }

clabWIFISSIDRowStatus    OBJECT-TYPE
    SYNTAX      RowStatus 
    MAX-ACCESS  read-create
    STATUS      current
    DESCRIPTION
        "The status of this instance"
    ::= {clabWIFISSIDEntry 11 }

clabWIFISSIDFragmentationEnable    OBJECT-TYPE
    SYNTAX      TruthValue 
    MAX-ACCESS  read-write
    STATUS      current
    DESCRIPTION
        "This attribute when set to 'true' will indicate that 
         fragmentation is enabled for this SSID.  When set to false,
         indicates fragmentation is disabled for this SSID."
    ::= {clabWIFISSIDEntry 12 }

clabWIFISSIDPeriodicStatsNumberOfEntries    OBJECT-TYPE
    SYNTAX      Integer32 
    MAX-ACCESS  read-only
    STATUS      current
    DESCRIPTION
        "Number of entries in the SSID Periodic stats table."
    ::= {clabWIFISSIDEntry 13 }

clabWIFISSIDStatsTable OBJECT-TYPE
    SYNTAX      SEQUENCE OF ClabWIFISSIDStatsEntry
    MAX-ACCESS  not-accessible
    STATUS      current
    DESCRIPTION
        "This object is defined in TR-181 Device.WiFi.SSID{i}.Stats."
    REFERENCE
        "TR-181 Device Data Model for TR-069."
    ::= {clabWIFIObjects 5 }

clabWIFISSIDStatsEntry    OBJECT-TYPE
    SYNTAX      ClabWIFISSIDStatsEntry
    MAX-ACCESS  not-accessible
    STATUS      current
    DESCRIPTION
        "The Conceptual row of clabWIFISSIDStatsTable."
    REFERENCE
        "TR-181 Issue2"
    INDEX {
            clabWIFISSIDId
          }
    ::= {clabWIFISSIDStatsTable 1 }

ClabWIFISSIDStatsEntry ::= SEQUENCE {
    clabWIFISSIDStatsBytesSent
                 Counter64,
    clabWIFISSIDStatsBytesReceived
                 Counter64,
    clabWIFISSIDStatsPacketsSent
                 Counter64,
    clabWIFISSIDStatsPacketsReceived
                 Counter64,
    clabWIFISSIDStatsErrorsSent
                 Counter32,
    clabWIFISSIDStatsErrorsReceived
                 Counter32,
    clabWIFISSIDStatsUnicastPacketsSent
                 Counter64,
    clabWIFISSIDStatsUnicastPacketsReceived
                 Counter64,
    clabWIFISSIDStatsDiscardPacketsSent
                 Counter32,
    clabWIFISSIDStatsDiscardPacketsReceived
                 Counter32,
    clabWIFISSIDStatsMulticastPacketsSent
                 Counter64,
    clabWIFISSIDStatsMulticastPacketsReceived
                 Counter64,
    clabWIFISSIDStatsBroadcastPacketsSent
                 Counter64,
    clabWIFISSIDStatsBroadcastPacketsReceived
                 Counter64,
    clabWIFISSIDStatsUnknownProtoPacketsReceived
                 Counter32,
    clabWIFISSIDStatsRetransCount
                 Counter32,
    clabWIFISSIDStatsRetryCount
                 Counter32,
    clabWIFISSIDStatsMultipleRetryCount
                 Counter32,
    clabWIFISSIDStatsACKFailureCount
                 Counter32,
    clabWIFISSIDStatsAggregatedPacketCount
                 Counter32
    }

clabWIFISSIDStatsBytesSent    OBJECT-TYPE
    SYNTAX      Counter64 
    MAX-ACCESS  read-only
    STATUS      current
    DESCRIPTION
        "This object is defined in TR-181 Device.WiFi.SSID{i}.Stats.BytesSent."
    REFERENCE
        "TR-181 Device Data Model for TR-069."
    ::= {clabWIFISSIDStatsEntry 1 }

clabWIFISSIDStatsBytesReceived    OBJECT-TYPE
    SYNTAX      Counter64 
    MAX-ACCESS  read-only
    STATUS      current
    DESCRIPTION
        "This object is defined in TR-181 Device.WiFi.SSID{i}.Stats.BytesReceived."
    REFERENCE
        "TR-181 Device Data Model for TR-069."
    ::= {clabWIFISSIDStatsEntry 2 }

clabWIFISSIDStatsPacketsSent    OBJECT-TYPE
    SYNTAX      Counter64 
    MAX-ACCESS  read-only
    STATUS      current
    DESCRIPTION
        "This object is defined in TR-181 Device.WiFi.SSID{i}.Stats.PacketsSent."
    REFERENCE
        "TR-181 Device Data Model for TR-069."
    ::= {clabWIFISSIDStatsEntry 3 }

clabWIFISSIDStatsPacketsReceived    OBJECT-TYPE
    SYNTAX      Counter64 
    MAX-ACCESS  read-only
    STATUS      current
    DESCRIPTION
        "This object is defined in TR-181 Device.WiFi.SSID{i}.Stats.PacketsReceived."
    REFERENCE
        "TR-181 Device Data Model for TR-069."
    ::= {clabWIFISSIDStatsEntry 4 }

clabWIFISSIDStatsErrorsSent    OBJECT-TYPE
    SYNTAX      Counter32 
    MAX-ACCESS  read-only
    STATUS      current
    DESCRIPTION
        "This object is defined in TR-181 Device.WiFi.SSID{i}.Stats.ErrorsSent."
    REFERENCE
        "TR-181 Device Data Model for TR-069."
    ::= {clabWIFISSIDStatsEntry 5 }

clabWIFISSIDStatsErrorsReceived    OBJECT-TYPE
    SYNTAX      Counter32 
    MAX-ACCESS  read-only
    STATUS      current
    DESCRIPTION
        "This object is defined in TR-181 Device.WiFi.SSID{i}.Stats.ErrorsReceived."
    REFERENCE
        "TR-181 Device Data Model for TR-069."
    ::= {clabWIFISSIDStatsEntry 6 }

clabWIFISSIDStatsUnicastPacketsSent    OBJECT-TYPE
    SYNTAX      Counter64 
    MAX-ACCESS  read-only
    STATUS      current
    DESCRIPTION
        "This object is defined in TR-181 Device.WiFi.SSID{i}.Stats.UnicastPacketsSent."
    REFERENCE
        "TR-181 Device Data Model for TR-069."
    ::= {clabWIFISSIDStatsEntry 7 }

clabWIFISSIDStatsUnicastPacketsReceived    OBJECT-TYPE
    SYNTAX      Counter64 
    MAX-ACCESS  read-only
    STATUS      current
    DESCRIPTION
        "This object is defined in TR-181 Device.WiFi.SSID{i}.Stats.UnicastPacketsReceived."
    REFERENCE
        "TR-181 Device Data Model for TR-069."
    ::= {clabWIFISSIDStatsEntry 8 }

clabWIFISSIDStatsDiscardPacketsSent    OBJECT-TYPE
    SYNTAX      Counter32 
    MAX-ACCESS  read-only
    STATUS      current
    DESCRIPTION
        "This object is defined in TR-181 Device.WiFi.SSID{i}.Stats.DiscardPacketsSent."
    REFERENCE
        "TR-181 Device Data Model for TR-069."
    ::= {clabWIFISSIDStatsEntry 9 }

clabWIFISSIDStatsDiscardPacketsReceived    OBJECT-TYPE
    SYNTAX      Counter32 
    MAX-ACCESS  read-only
    STATUS      current
    DESCRIPTION
        "This object is defined in TR-181 Device.WiFi.SSID{i}.Stats.DiscardPacketsReceived."
    REFERENCE
        "TR-181 Device Data Model for TR-069."
    ::= {clabWIFISSIDStatsEntry 10 }

clabWIFISSIDStatsMulticastPacketsSent    OBJECT-TYPE
    SYNTAX      Counter64 
    MAX-ACCESS  read-only
    STATUS      current
    DESCRIPTION
        "This object is defined in TR-181 Device.WiFi.SSID{i}.Stats.MulticastPacketsSent."
    REFERENCE
        "TR-181 Device Data Model for TR-069."
    ::= {clabWIFISSIDStatsEntry 11 }

clabWIFISSIDStatsMulticastPacketsReceived    OBJECT-TYPE
    SYNTAX      Counter64 
    MAX-ACCESS  read-only
    STATUS      current
    DESCRIPTION
        "This object is defined in TR-181 Device.WiFi.SSID{i}.Stats.MulticastPacketsReceived."
    REFERENCE
        "TR-181 Device Data Model for TR-069."
    ::= {clabWIFISSIDStatsEntry 12 }

clabWIFISSIDStatsBroadcastPacketsSent    OBJECT-TYPE
    SYNTAX      Counter64 
    MAX-ACCESS  read-only
    STATUS      current
    DESCRIPTION
        "This object is defined in TR-181 Device.WiFi.SSID{i}.Stats.BroadcastPacketsSent."
    REFERENCE
        "TR-181 Device Data Model for TR-069."
    ::= {clabWIFISSIDStatsEntry 13 }

clabWIFISSIDStatsBroadcastPacketsReceived    OBJECT-TYPE
    SYNTAX      Counter64 
    MAX-ACCESS  read-only
    STATUS      current
    DESCRIPTION
        "This object is defined in TR-181 Device.WiFi.SSID{i}.Stats.BroadcastPacketsReceived."
    REFERENCE
        "TR-181 Device Data Model for TR-069."
    ::= {clabWIFISSIDStatsEntry 14 }

clabWIFISSIDStatsUnknownProtoPacketsReceived    OBJECT-TYPE
    SYNTAX      Counter32 
    MAX-ACCESS  read-only
    STATUS      current
    DESCRIPTION
        "This object is defined in TR-181 Device.WiFi.SSID{i}.Stats.UnknownProtoPacketsReceived."
    REFERENCE
        "TR-181 Device Data Model for TR-069."
    ::= {clabWIFISSIDStatsEntry 15 }

clabWIFISSIDStatsRetransCount    OBJECT-TYPE     
    SYNTAX      Counter32 
    MAX-ACCESS  read-only
    STATUS      current
    DESCRIPTION
        "This object is defined in TR-181 Device.WiFi.SSID.{i}.Stats.RetransCount."
    REFERENCE
        "TR-181 Device Data Model for TR-069."
    ::= {clabWIFISSIDStatsEntry 16 }

clabWIFISSIDStatsRetryCount    OBJECT-TYPE     
    SYNTAX      Counter32 
    MAX-ACCESS  read-only
    STATUS      current
    DESCRIPTION
        "This object is defined in TR-181 Device.WiFi.SSID.{i}.Stats.RetryCount."
    REFERENCE
        "TR-181 Device Data Model for TR-069."
    ::= {clabWIFISSIDStatsEntry 17 }

clabWIFISSIDStatsMultipleRetryCount    OBJECT-TYPE     
    SYNTAX      Counter32 
    MAX-ACCESS  read-only
    STATUS      current
    DESCRIPTION
        "This object is defined in TR-181 Device.WiFi.SSID.{i}.Stats.MutipleRetryCount."
    REFERENCE
        "TR-181 Device Data Model for TR-069."
    ::= {clabWIFISSIDStatsEntry 18 }

clabWIFISSIDStatsACKFailureCount    OBJECT-TYPE     
    SYNTAX      Counter32 
    MAX-ACCESS  read-only
    STATUS      current
    DESCRIPTION
        "This object is defined in TR-181 Device.WiFi.SSID.{i}.Stats.ACKFailureCount."
    REFERENCE
        "TR-181 Device Data Model for TR-069."
    ::= {clabWIFISSIDStatsEntry 19 }

clabWIFISSIDStatsAggregatedPacketCount    OBJECT-TYPE     
    SYNTAX      Counter32 
    MAX-ACCESS  read-only
    STATUS      current
    DESCRIPTION
        "This object is defined in TR-181 Device.WiFi.SSID.{i}.Stats.AggregatedPacketCount."
    REFERENCE
        "TR-181 Device Data Model for TR-069."
    ::= {clabWIFISSIDStatsEntry 20 }

clabWIFIAccessPointTable OBJECT-TYPE
    SYNTAX      SEQUENCE OF ClabWIFIAccessPointEntry
    MAX-ACCESS  not-accessible
    STATUS      current
    DESCRIPTION
        "This object is defined in TR-181 Device.WiFi.AccessPoint{i}."
    REFERENCE
        "TR-181 Device Data Model for TR-069."
    ::= {clabWIFIObjects 6 }

clabWIFIAccessPointEntry    OBJECT-TYPE
    SYNTAX      ClabWIFIAccessPointEntry
    MAX-ACCESS  not-accessible
    STATUS      current
    DESCRIPTION
        "The Conceptual row of clabWIFIAccessPointTable."
    INDEX {
            clabWIFIAccessPointId
          }
    ::= {clabWIFIAccessPointTable 1 }

ClabWIFIAccessPointEntry ::= SEQUENCE {
    clabWIFIAccessPointId
                 Unsigned32,
    clabWIFIAccessPointEnable
                 TruthValue,
    clabWIFIAccessPointStatus
                 INTEGER,
    clabWIFIAccessPointAlias
                 SnmpAdminString,
    clabWIFIAccessPointSSIDReference
                 Unsigned32,
    clabWIFIAccessPointSSIDAdvertisementEnabled
                 TruthValue,
    clabWIFIAccessPointRetryLimit
                 Unsigned32,
    clabWIFIAccessPointWMMCapability
                 TruthValue,
    clabWIFIAccessPointUAPSDCapability
                 TruthValue,
    clabWIFIAccessPointWMMEnable
                 TruthValue,
    clabWIFIAccessPointUAPSDEnable
                 TruthValue,
    clabWIFIAccessPointAssociatedDeviceNumberOfEntries
                 Unsigned32,
    clabWIFIAccessPointRowStatus 
                 RowStatus,
    clabWIFIAccessPointPublicAccessMode                 
                 TruthValue,
    clabWIFIAccessPointIsolationEnable
                 TruthValue,
    clabWIFIAccessPointMaxAssociatedDevices
                 Unsigned32,
    clabWIFIAccessPointPasspointSupported
                 TruthValue,
    clabWIFIAccessPointPasspointEnabled
                 TruthValue,
    clabWIFIAccessPointInterworkingCapability
                 TruthValue,
    clabWIFIAccessPointInterworkingServiceEnabled
                 TruthValue,
    clabWIFIAccessPointAccessControlFilterEnable
                 TruthValue,		  
    clabWIFIAccessPointMACAddressControlEnable
                 TruthValue,
    clabWIFIAccessPointAllowedMACAddress
                 OCTET STRING,
    clabWIFIAccessPointClientSessionNumberOfEntries
                 Unsigned32,
    clabWIFIAccessPointAssociatedDeviceCount
                 Unsigned32
    }

clabWIFIAccessPointId    OBJECT-TYPE
    SYNTAX      Unsigned32 (1..99)
    MAX-ACCESS  not-accessible
    STATUS      current
    DESCRIPTION
        "The key for a unique instance of this object."
    ::= {clabWIFIAccessPointEntry 1 }

clabWIFIAccessPointEnable    OBJECT-TYPE
    SYNTAX      TruthValue 
    MAX-ACCESS  read-create
    STATUS      current
    DESCRIPTION
        "This object is defined in TR-181 Device.WiFi.AccessPoint{i}.Enable."
    REFERENCE
        "TR-181 Device Data Model for TR-069."
    ::= {clabWIFIAccessPointEntry 2 }

clabWIFIAccessPointStatus    OBJECT-TYPE
    SYNTAX      INTEGER  {
                           disabled(1),
                           enabled(2),
                           errorMisconfigured(3),
                           error(4)
                         }
    MAX-ACCESS  read-only
    STATUS      current
    DESCRIPTION
        "This object is defined in TR-181 Device.WiFi.AccessPoint{i}.Status."
    REFERENCE
        "TR-181 Device Data Model for TR-069."
    ::= {clabWIFIAccessPointEntry 3 }

clabWIFIAccessPointAlias    OBJECT-TYPE
    SYNTAX      SnmpAdminString (SIZE(0..64))
    MAX-ACCESS  read-create
    STATUS      current
    DESCRIPTION
        "This object is defined in TR-181 Device.WiFi.AccessPoint{i}.Alias."
    REFERENCE
        "TR-181 Device Data Model for TR-069."
    ::= {clabWIFIAccessPointEntry 4 }

clabWIFIAccessPointSSIDReference    OBJECT-TYPE
    SYNTAX      Unsigned32 
    MAX-ACCESS  read-create
    STATUS      current
    DESCRIPTION
        "This object is defined in TR-181 Device.WiFi.AccessPoint{i}.Reference."
    REFERENCE
        "TR-181 Device Data Model for TR-069."
    ::= {clabWIFIAccessPointEntry 5 }

clabWIFIAccessPointSSIDAdvertisementEnabled    OBJECT-TYPE
    SYNTAX      TruthValue 
    MAX-ACCESS  read-create
    STATUS      current
    DESCRIPTION
        "This object is defined in TR-181 Device.WiFi.AccessPoint{i}.AdvertisementEnabled."
    REFERENCE
        "TR-181 Device Data Model for TR-069."
    ::= {clabWIFIAccessPointEntry 6 }

clabWIFIAccessPointRetryLimit    OBJECT-TYPE
    SYNTAX      Unsigned32 (0..7)
    MAX-ACCESS  read-create
    STATUS      deprecated
    DESCRIPTION
        "This object is defined in TR-181 Device.WiFi.AccessPoint{i}.RetryLimit."
    REFERENCE
        "TR-181 Device Data Model for TR-069."
    ::= {clabWIFIAccessPointEntry 7 }

clabWIFIAccessPointWMMCapability    OBJECT-TYPE
    SYNTAX      TruthValue 
    MAX-ACCESS  read-only
    STATUS      current
    DESCRIPTION
        "This object is defined in TR-181 Device.WiFi.AccessPoint{i}.WMMCapability."
    REFERENCE
        "TR-181 Device Data Model for TR-069."
    ::= {clabWIFIAccessPointEntry 8 }

clabWIFIAccessPointUAPSDCapability    OBJECT-TYPE
    SYNTAX      TruthValue 
    MAX-ACCESS  read-only
    STATUS      current
    DESCRIPTION
        "This object is defined in TR-181 Device.WiFi.AccessPoint{i}.UAPSDCapability."
    REFERENCE
        "TR-181 Device Data Model for TR-069."
    ::= {clabWIFIAccessPointEntry 9 }

clabWIFIAccessPointWMMEnable    OBJECT-TYPE
    SYNTAX      TruthValue 
    MAX-ACCESS  read-create
    STATUS      current
    DESCRIPTION
        "This object is defined in TR-181 Device.WiFi.AccessPoint{i}.WMMEnable."
    REFERENCE
        "TR-181 Device Data Model for TR-069."
    ::= {clabWIFIAccessPointEntry 10 }

clabWIFIAccessPointUAPSDEnable    OBJECT-TYPE
    SYNTAX      TruthValue 
    MAX-ACCESS  read-create
    STATUS      current
    DESCRIPTION
        "This object is defined in TR-181 Device.WiFi.AccessPoint{i}.UAPSDEnable."
    REFERENCE
        "TR-181 Device Data Model for TR-069."
    ::= {clabWIFIAccessPointEntry 11 }

clabWIFIAccessPointAssociatedDeviceNumberOfEntries    OBJECT-TYPE
    SYNTAX      Unsigned32 
    MAX-ACCESS  read-only
    STATUS      current
    DESCRIPTION
        "This object is defined in TR-181 Device.WiFi.AccessPoint{i}.AssociatedDeviceNumberOfEntries."
    REFERENCE
        "TR-181 Device Data Model for TR-069."
    ::= {clabWIFIAccessPointEntry 12 }

clabWIFIAccessPointRowStatus    OBJECT-TYPE
    SYNTAX      RowStatus 
    MAX-ACCESS  read-create
    STATUS      current
    DESCRIPTION
        "The status of this instance."
    ::= {clabWIFIAccessPointEntry 13 }
    
clabWIFIAccessPointPublicAccessMode    OBJECT-TYPE
    SYNTAX      TruthValue
    MAX-ACCESS  read-create
    STATUS      current
    DESCRIPTION
        "Establishes SSID as Public if True(1).  The default
         is False(2) (i.e., Private). "    
    ::= { clabWIFIAccessPointEntry 14 }

clabWIFIAccessPointIsolationEnable    OBJECT-TYPE
    SYNTAX      TruthValue
    MAX-ACCESS  read-create
    STATUS      current
    DESCRIPTION
        " Enables or disables device isolation. A value 
          of true means that the devices connected to the 
          Access Point are isolated from all other devices 
          within the home network (as is typically the case 
          for a Wireless Passpoint). This object is defined 
          in TR-181 
          Device.WiFi.AccessPoint{i}.IsolationEnable."
    ::= {clabWIFIAccessPointEntry 15 }

clabWIFIAccessPointMaxAssociatedDevices    OBJECT-TYPE
    SYNTAX      Unsigned32
    MAX-ACCESS  read-create
    STATUS      current
    DESCRIPTION
        " The maximum number of devices that can simultaneously 
          be connected to the access point. A value of 0 means 
          that there is no specific limit. This object is defined 
          in TR-181 Device.WiFi.AccessPoint{i}. MaxAssociatedDevices."
    ::= {clabWIFIAccessPointEntry 16 }

clabWIFIAccessPointPasspointSupported    OBJECT-TYPE
    SYNTAX      TruthValue
    MAX-ACCESS  read-create
    STATUS      current
    DESCRIPTION
        " Passpoint2.0 is supported or not supported. This object is 
          Defined as a CableLabs extension to TR-181 
          Device.WiFi.AccessPoint{i}.PasspointSupported."
    ::= {clabWIFIAccessPointEntry 17 }

clabWIFIAccessPointPasspointEnabled    OBJECT-TYPE
    SYNTAX      TruthValue
    MAX-ACCESS  read-create
    STATUS      current
    DESCRIPTION
        " Passpoint2.0 is enabled/disabled. This object is 
          Defined as a CableLabs extension to TR-181 
          Device.WiFi.AccessPoint{i}.PasspointEnabled."
    ::= {clabWIFIAccessPointEntry 18 }

clabWIFIAccessPointInterworkingCapability   OBJECT-TYPE
    SYNTAX      TruthValue
    MAX-ACCESS  read-create
    STATUS      current
    DESCRIPTION
        " Interworking Service is supported or not supported. 
          If true, then indicates the access point supports 
          interworking with external networks. This object is 
          Defined as a CableLabs extension to TR-181 
          Device.WiFi.AccessPoint{i}.InterWorkingServiceSupported."
    ::= {clabWIFIAccessPointEntry 19 }

clabWIFIAccessPointInterworkingServiceEnabled   OBJECT-TYPE
    SYNTAX      TruthValue
    MAX-ACCESS  read-write
    STATUS      current
    DESCRIPTION
        " Interworking Service is enabled/disabled. This object is 
          Defined as a CableLabs extension to TR-181 
          Device.WiFi.AccessPoint{i}.InterworkingServiceEnabled."
    ::= {clabWIFIAccessPointEntry 20 }

clabWIFIAccessPointAccessControlFilterEnable   OBJECT-TYPE
    SYNTAX      TruthValue
    MAX-ACCESS  read-write
    STATUS      current
    DESCRIPTION
        " This attribute enables MAC filtering as a condition 
          of AP access (i.e., allow/disallow). This object is 
          Defined as a CableLabs extension to TR-181 
          Device.WiFi.AccessPoint{i}.AccessControlFilterEnabled."
    ::= {clabWIFIAccessPointEntry 21 }

clabWIFIAccessPointMACAddressControlEnable   OBJECT-TYPE
    SYNTAX      TruthValue
    MAX-ACCESS  read-write
    STATUS      current
    DESCRIPTION
        "This object is defined in TR-181 Device.WiFi.AccessPoint{i}.MACAddressControlEnable."
    REFERENCE
        "TR-181 Device Data Model for TR-069."
    ::= {clabWIFIAccessPointEntry 22 }

clabWIFIAccessPointAllowedMACAddress   OBJECT-TYPE
    SYNTAX      OCTET STRING (SIZE(0..1024))
    MAX-ACCESS  read-write
    STATUS      current
    DESCRIPTION
        "This object is defined in TR-181 Device.WiFi.AccessPoint{i}.AllowedMACAddress."
    REFERENCE
        "TR-181 Device Data Model for TR-069."
    ::= {clabWIFIAccessPointEntry 23 }

clabWIFIAccessPointClientSessionNumberOfEntries   OBJECT-TYPE
    SYNTAX      Unsigned32
    MAX-ACCESS  read-only
    STATUS      current
    DESCRIPTION
        " Number of entries in the Client Session Table."
    ::= {clabWIFIAccessPointEntry 24 }

clabWIFIAccessPointAssociatedDeviceCount   OBJECT-TYPE
    SYNTAX      Unsigned32
    MAX-ACCESS  read-only
    STATUS      deprecated
    DESCRIPTION
        "Deprecated, as this object duplicates the previous defined 
         object clabWIFIAccessPointAssociatedDeviceNumberOfEntries.
         Total number of active devices associated at any point in time."
    ::= {clabWIFIAccessPointEntry 25 }

clabWIFIAccessPointSecurityTable OBJECT-TYPE
    SYNTAX      SEQUENCE OF ClabWIFIAccessPointSecurityEntry
    MAX-ACCESS  not-accessible
    STATUS      current
    DESCRIPTION
        "This object is defined in TR-181 Device.WiFi.AccessPoint{i}.Security."
    REFERENCE
        "TR-181 Device Data Model for TR-069."
    ::= {clabWIFIObjects 7 }

clabWIFIAccessPointSecurityEntry    OBJECT-TYPE
    SYNTAX      ClabWIFIAccessPointSecurityEntry
    MAX-ACCESS  not-accessible
    STATUS      current
    DESCRIPTION
        "The Conceptual row of clabWIFIAccessPointSecurityTable."
    REFERENCE
        "802.11-2007"
    INDEX {
            clabWIFIAccessPointId
          }
    ::= {clabWIFIAccessPointSecurityTable 1 }

ClabWIFIAccessPointSecurityEntry ::= SEQUENCE {
    clabWIFIAccessPointSecurityModesSupported
                 SnmpAdminString,
    clabWIFIAccessPointSecurityModeEnabled
                 INTEGER,
    clabWIFIAccessPointSecurityWEPKey
                 OCTET STRING,
    clabWIFIAccessPointSecurityPreSharedKey
                 OCTET STRING,
    clabWIFIAccessPointSecurityKeyPassphrase
                 SnmpAdminString,
    clabWIFIAccessPointSecurityRekeyingInterval
                 Unsigned32,
    clabWIFIAccessPointSecurityRadiusServerIPAddrType
                 InetAddressType,
    clabWIFIAccessPointSecurityRadiusServerIPAddr
                 InetAddress,
    clabWIFIAccessPointSecurityRadiusServerPort
                 InetPortNumber,
    clabWIFIAccessPointSecurityRadiusSecret
                 SnmpAdminString,
    clabWIFIAccessPointSecurityRowstatus
                 RowStatus,
    clabWIFIAccessPointSecurityWEPKey2
                 OCTET STRING,
    clabWIFIAccessPointSecurityWEPKey3
                 OCTET STRING,
    clabWIFIAccessPointSecurityWEPKey4
                 OCTET STRING,
    clabWIFIAccessPointSecurityWEPIndex
                 Unsigned32,
    clabWIFIAccessPointSecurityWEPPassPhrase
                 SnmpAdminString,
    clabWIFIAccessPointSecurityWPAEncryption
                 INTEGER,
    clabWIFIAccessPointSecuritySecondaryRadiusServerIPAddrType
                 InetAddressType,
    clabWIFIAccessPointSecuritySecondaryRadiusServerIPAddr
                 InetAddress,
    clabWIFIAccessPointSecuritySecondaryRadiusServerPort
                 InetPortNumber,
    clabWIFIAccessPointSecuritySecondaryRadiusSecret
                 SnmpAdminString,
    clabWIFIAccessPointSecurityEnableManagementFrameProtection
                 TruthValue,
    clabWIFIAccessPointSecurityReset
                 TruthValue,
    clabWIFIAccessPointRadiusRetries
                 Integer32,
    clabWIFIAccessPointSecurityLanRoutingEnabled
                 TruthValue
   }

clabWIFIAccessPointSecurityModesSupported    OBJECT-TYPE
    SYNTAX      SnmpAdminString
    MAX-ACCESS  read-only
    STATUS      current
    DESCRIPTION
        "This object is defined in TR-181 Device.WiFi.AccessPoint{i}.Security.ModesSupported."
    REFERENCE
        "TR-181 Device Data Model for TR-069."
    ::= {clabWIFIAccessPointSecurityEntry 1 }

clabWIFIAccessPointSecurityModeEnabled    OBJECT-TYPE
    SYNTAX      INTEGER  {
                            none(1),
                            wep64(2),
                            wep128(3),
                            wpaPersonal(4),
                            wpa2Personal(5),
                            wpawpa2Personal(6),
                            wpaEnterprise(7),
                            wpa2Enterprise(8),
                            wpawpa2Enterprise(9)
                         }
    MAX-ACCESS  read-create
    STATUS      current
    DESCRIPTION
        "This object is defined in TR-181 Device.WiFi.AccessPoint{i}.Security.ModeEnabled."
    REFERENCE
        "TR-181 Device Data Model for TR-069."
    ::= {clabWIFIAccessPointSecurityEntry 2 }

clabWIFIAccessPointSecurityWEPKey    OBJECT-TYPE
    SYNTAX      OCTET STRING (SIZE (0 | 5 | 13)) 
    MAX-ACCESS  read-create
    STATUS      current
    DESCRIPTION
        "This object is defined in TR-181 Device.WiFi.AccessPoint{i}.Security.WEPKey."
    REFERENCE
        "TR-181 Device Data Model for TR-069."
    ::= {clabWIFIAccessPointSecurityEntry 3 }

clabWIFIAccessPointSecurityPreSharedKey    OBJECT-TYPE
    SYNTAX      OCTET STRING (SIZE(0 | 32)) 
    MAX-ACCESS  read-create
    STATUS      current
    DESCRIPTION
        "This object is defined in TR-181 Device.WiFi.AccessPoint{i}.Security.PreSharedKey."
    REFERENCE
        "TR-181 Device Data Model for TR-069."
    ::= {clabWIFIAccessPointSecurityEntry 4 }

clabWIFIAccessPointSecurityKeyPassphrase    OBJECT-TYPE
    SYNTAX      SnmpAdminString (SIZE(0..63))  
    MAX-ACCESS  read-create
    STATUS      current
    DESCRIPTION
        "This object is defined in TR-181 Device.WiFi.AccessPoint{i}.Security.KeyPassphrase."
    REFERENCE
        "TR-181 Device Data Model for TR-069."
    ::= {clabWIFIAccessPointSecurityEntry 5 }

clabWIFIAccessPointSecurityRekeyingInterval    OBJECT-TYPE
    SYNTAX      Unsigned32 
    UNITS       "seconds"
    MAX-ACCESS  read-create
    STATUS      current
    DESCRIPTION
        "This object is defined in TR-181 Device.WiFi.AccessPoint{i}.Security.RekeyingInterval."
    REFERENCE
        "TR-181 Device Data Model for TR-069."
    DEFVAL { 3600 }
    ::= {clabWIFIAccessPointSecurityEntry 6 }

clabWIFIAccessPointSecurityRadiusServerIPAddrType    OBJECT-TYPE
    SYNTAX      InetAddressType 
    MAX-ACCESS  read-create
    STATUS      current
    DESCRIPTION
        "This object is defined in TR-181 Device.WiFi.AccessPoint{i}.Security.RadiusServerIPAddrType."
    REFERENCE
        "TR-181 Device Data Model for TR-069."
    ::= {clabWIFIAccessPointSecurityEntry 7 }

clabWIFIAccessPointSecurityRadiusServerIPAddr    OBJECT-TYPE
    SYNTAX      InetAddress 
    MAX-ACCESS  read-create
    STATUS      current
    DESCRIPTION
        "This object is defined in TR-181 Device.WiFi.AccessPoint{i}.Security.RadiusServerIPAddr."
    REFERENCE
        "TR-181 Device Data Model for TR-069."
    ::= {clabWIFIAccessPointSecurityEntry 8 }

clabWIFIAccessPointSecurityRadiusServerPort    OBJECT-TYPE
    SYNTAX      InetPortNumber 
    MAX-ACCESS  read-create
    STATUS      current
    DESCRIPTION
        "This object is defined in TR-181 Device.WiFi.AccessPoint{i}.Security.RadiusServerPort."
    REFERENCE
        "TR-181 Device Data Model for TR-069."
    DEFVAL { 1812 }
    ::= {clabWIFIAccessPointSecurityEntry 9 }

clabWIFIAccessPointSecurityRadiusSecret    OBJECT-TYPE
    SYNTAX      SnmpAdminString 
    MAX-ACCESS  read-create
    STATUS      current
    DESCRIPTION
        "This object is defined in TR-181 Device.WiFi.AccessPoint{i}.Security.RadiusSecret."
    REFERENCE
        "TR-181 Device Data Model for TR-069."
    ::= {clabWIFIAccessPointSecurityEntry 10 }

clabWIFIAccessPointSecurityRowstatus    OBJECT-TYPE
    SYNTAX      RowStatus 
    MAX-ACCESS  read-create
    STATUS      current
    DESCRIPTION
        "The status of this instance."
    ::= {clabWIFIAccessPointSecurityEntry 11 }
    
clabWIFIAccessPointSecurityWEPKey2     OBJECT-TYPE
    SYNTAX    OCTET STRING (SIZE (0 | 5 | 13))
    MAX-ACCESS  read-create
    STATUS      current
    DESCRIPTION
        "The WEP key 2 expressed as a hexadecimal string."
    ::= {clabWIFIAccessPointSecurityEntry 12 }

clabWIFIAccessPointSecurityWEPKey3     OBJECT-TYPE
    SYNTAX    OCTET STRING (SIZE (0 | 5 | 13))
    MAX-ACCESS  read-create
    STATUS      current
    DESCRIPTION
        "The WEP key 3 expressed as a hexadecimal string."
    ::= {clabWIFIAccessPointSecurityEntry 13 }

clabWIFIAccessPointSecurityWEPKey4     OBJECT-TYPE
    SYNTAX    OCTET STRING (SIZE (0 | 5 | 13))
    MAX-ACCESS  read-create
    STATUS      current
    DESCRIPTION
        "The WEP key 4 expressed as a hexadecimal string."
    ::= {clabWIFIAccessPointSecurityEntry 14 }

clabWIFIAccessPointSecurityWEPIndex    OBJECT-TYPE
    SYNTAX    Unsigned32 (1..4)
    MAX-ACCESS  read-create
    STATUS      current
    DESCRIPTION
        "This attribute defines the selected WEP key."
    ::= {clabWIFIAccessPointSecurityEntry 15 }

clabWIFIAccessPointSecurityWEPPassPhrase     OBJECT-TYPE
    SYNTAX    SnmpAdminString (SIZE(0 | 5..63))
    MAX-ACCESS  read-create
    STATUS      current
    DESCRIPTION
        "This attribute defines a human readable password to derive
        the WEP keys, following well-known key generation algorithm for 
        this purpose.
        When this attribute is a zero-length string, WEP keys are used
        directly. Otherwise, the values of the WEP keys cannot be 
        changed directly and an error on write is returned."
    ::= {clabWIFIAccessPointSecurityEntry 16 }

clabWIFIAccessPointSecurityWPAEncryption     OBJECT-TYPE
    SYNTAX    INTEGER {
                       aes(1),
                       tkipaes(2)
                      }
    MAX-ACCESS  read-create
    STATUS      current
    DESCRIPTION
        "This attribute defines the encryption algorithm used for WPA."
 ::= {clabWIFIAccessPointSecurityEntry 17 }
 
clabWIFIAccessPointSecuritySecondaryRadiusServerIPAddrType    OBJECT-TYPE
    SYNTAX      InetAddressType
    MAX-ACCESS  read-create
    STATUS      current
    DESCRIPTION
        "This object is the address type of TR-181
        Device.WiFi.AccessPoint{i}.Security.
        SecondaryRadiusServerIPAddr."
    REFERENCE
        "TR-181 Device Data Model for TR-069."
    ::= {clabWIFIAccessPointSecurityEntry 18 }

clabWIFIAccessPointSecuritySecondaryRadiusServerIPAddr    OBJECT-TYPE
    SYNTAX      InetAddress
    MAX-ACCESS  read-create
    STATUS      current
    DESCRIPTION
        "This object is defined in TR-181
         Device.WiFi.AccessPoint{i}.Security.SecondaryRadiusServerIPAddr."
    REFERENCE
        "TR-181 Device Data Model for TR-069."
    ::= {clabWIFIAccessPointSecurityEntry 19 }

clabWIFIAccessPointSecuritySecondaryRadiusServerPort    OBJECT-TYPE
    SYNTAX      InetPortNumber
    MAX-ACCESS  read-create
    STATUS      current
    DESCRIPTION
        "This object is defined in TR-181
         Device.WiFi.AccessPoint{i}.Security.SecondaryRadiusServerPort."
    REFERENCE
        "TR-181 Device Data Model for TR-069."
    DEFVAL { 1812 }
    ::= {clabWIFIAccessPointSecurityEntry 20 }

clabWIFIAccessPointSecuritySecondaryRadiusSecret    OBJECT-TYPE
    SYNTAX      SnmpAdminString
    MAX-ACCESS  read-create
    STATUS      current
    DESCRIPTION
        "This object is defined in TR-181
         Device.WiFi.AccessPoint{i}.Security.SecondaryRadiusSecret."
    REFERENCE
        "TR-181 Device Data Model for TR-069."    
    ::= {clabWIFIAccessPointSecurityEntry 21 }

clabWIFIAccessPointSecurityEnableManagementFrameProtection    OBJECT-TYPE
    SYNTAX      TruthValue 
    MAX-ACCESS  read-create
    STATUS      current
    DESCRIPTION
        "This object enables Management Frame Protection."
    ::= { clabWIFIAccessPointSecurityEntry 22 }

clabWIFIAccessPointSecurityReset    OBJECT-TYPE
    SYNTAX      TruthValue 
    MAX-ACCESS  read-write
    STATUS      current
    DESCRIPTION
        "This object is defined in TR-181
         Device.WiFi.AccessPoint{i}.Security.Reset."
    REFERENCE
        "TR-181 Device Data Model for TR-069."
    ::= { clabWIFIAccessPointSecurityEntry 23 }
    
clabWIFIAccessPointRadiusRetries    OBJECT-TYPE
    SYNTAX      Integer32 
    MAX-ACCESS  read-only
    STATUS      current
    DESCRIPTION
        "This attribute indicates the failover Radius retry count."
    ::= { clabWIFIAccessPointSecurityEntry 24 }

clabWIFIAccessPointSecurityLanRoutingEnabled    OBJECT-TYPE
    SYNTAX      TruthValue 
    MAX-ACCESS  read-write
    STATUS      current
    DESCRIPTION
        "This attribute indicates LAN routing is enabled. 'true' indicates LAN Routing is enabled, 'false' otherwise."
    ::= { clabWIFIAccessPointSecurityEntry 25 }

clabWIFIAccessPointWPSTable OBJECT-TYPE
    SYNTAX      SEQUENCE OF ClabWIFIAccessPointWPSEntry
    MAX-ACCESS  not-accessible
    STATUS      current
    DESCRIPTION
        "This object is defined in TR-181 Device.WiFi.AccessPoint{i}.WPS."
    REFERENCE
        "TR-181 Device Data Model for TR-069."
    ::= {clabWIFIObjects 8 }

clabWIFIAccessPointWPSEntry    OBJECT-TYPE
    SYNTAX      ClabWIFIAccessPointWPSEntry
    MAX-ACCESS  not-accessible
    STATUS      current
    DESCRIPTION
        "The Conceptual row of clabWIFIAccessPointWPSTable."
    REFERENCE
        "WPSv1.0"
    INDEX {
            clabWIFIAccessPointId
          }
    ::= {clabWIFIAccessPointWPSTable 1 }

ClabWIFIAccessPointWPSEntry ::= SEQUENCE {
    clabWIFIAccessPointWPSEnable
                 TruthValue,
    clabWIFIAccessPointWPSConfigMethodsSupported
                 SnmpAdminString,
    clabWIFIAccessPointWPSConfigMethodsEnabled
                 INTEGER,
    clabWIFIAccessPointWPSRowStatus
                 RowStatus,
    clabWIFIAccessPointWPSSetWPSMethod
                 INTEGER,
    clabWIFIAccessPointWPSAPPin
                 SnmpAdminString,
    clabWIFIAccessPointWPSSetWPSClientPin
		 SnmpAdminString,
    clabWIFIAccessPointWPSConfigMethodsEnable
                 SnmpAdminString,
    clabWIFIAccessPointWPSSetWPSMethods
                 BITS
}

clabWIFIAccessPointWPSEnable    OBJECT-TYPE
    SYNTAX      TruthValue 
    MAX-ACCESS  read-create
    STATUS      current
    DESCRIPTION
        "This object is defined in TR-181 Device.WiFi.AccessPoint{i}.WPS.Enable."
    REFERENCE
        "TR-181 Device Data Model for TR-069."
    DEFVAL { true }
    ::= {clabWIFIAccessPointWPSEntry 1 }

clabWIFIAccessPointWPSConfigMethodsSupported    OBJECT-TYPE
    SYNTAX      SnmpAdminString
    MAX-ACCESS  read-only
    STATUS      current
    DESCRIPTION
        "This object is defined in TR-181 Device.WiFi.AccessPoint{i}.WPS.ConfigMethodsSupported."
    REFERENCE
        "TR-181 Device Data Model for TR-069."
    ::= {clabWIFIAccessPointWPSEntry 2 }

clabWIFIAccessPointWPSConfigMethodsEnabled    OBJECT-TYPE
        SYNTAX      INTEGER  {
                            usbFlashDrive(1),
                            ethernet(2),
                            externalNFCToken(3),
                            integratedNFCToken(4),
                            nfcInterface(5),
                            pin(7),
                            pushButton(8)
                         }
    MAX-ACCESS  read-create
    STATUS      deprecated
    DESCRIPTION
        "This object is defined in TR-181 Device.WiFi.AccessPoint{i}.WPS.ConfigMethodsEnabled."
    REFERENCE
        "TR-181 Device Data Model for TR-069."
    ::= {clabWIFIAccessPointWPSEntry 3 }

clabWIFIAccessPointWPSRowStatus    OBJECT-TYPE
    SYNTAX      RowStatus
    MAX-ACCESS  read-create
    STATUS      current
    DESCRIPTION
        "The status of this instance."
    ::= {clabWIFIAccessPointWPSEntry 4 } 

clabWIFIAccessPointWPSSetWPSMethod    OBJECT-TYPE
    SYNTAX      INTEGER {
                         usbFlashDrive(1),
                         ethernet(2),
                         externalNFCToken(3),
                         integratedNFCToken(4),
                         nfcInterface(5),
                         display(6),
                         pin(7),
                         pushButton(8),
                         keypad(9)
                        }

    MAX-ACCESS  read-write
    STATUS      deprecated
    DESCRIPTION
        "This object is defined as an CableLabs Extension to TR-181
         Device.WiFi.AccessPoint{i}.WPS.  The value must be selected 
         from the clabWIFIAccessPointWPSConfigMethodsSupported list 
         above."
    REFERENCE
        "TR-181 Device Data Model for TR-069."
    ::= {clabWIFIAccessPointWPSEntry 5 }
 
clabWIFIAccessPointWPSAPPin    OBJECT-TYPE
    SYNTAX      SnmpAdminString 
    MAX-ACCESS  read-only
    STATUS      current
    DESCRIPTION
        " This object is defined as an CableLabs Extension to 
          TR-181 Device.WiFi.AccessPoint{i}.WPS.  The value 
          returned is the factory default PIN."
    REFERENCE
        "TR-181 Device Data Model for TR-069."
    ::= {clabWIFIAccessPointWPSEntry 6 }

clabWIFIAccessPointWPSSetWPSClientPin    OBJECT-TYPE
    SYNTAX      SnmpAdminString 
    MAX-ACCESS  read-write
    STATUS      current
    DESCRIPTION
        " This object is defined as an CableLabs Extension to 
          TR-181 Device.WiFi.AccessPoint{i}.WPS.  The value 
          returned is the factory default PIN."
    REFERENCE
        "TR-181 Device Data Model for TR-069."
    ::= {clabWIFIAccessPointWPSEntry 7 }

clabWIFIAccessPointWPSConfigMethodsEnable    OBJECT-TYPE
    SYNTAX      SnmpAdminString
    MAX-ACCESS  read-create
    STATUS      current
    DESCRIPTION
        "This object is defined in TR-181
         Device.WiFi.AccessPoint{i}.WPS.ConfigMethodsEnabled."
    REFERENCE
        "TR-181 Device Data Model for TR-069."
    ::= {clabWIFIAccessPointWPSEntry 8 }

clabWIFIAccessPointWPSSetWPSMethods    OBJECT-TYPE
    SYNTAX      BITS {
                         usbFlashDrive(0),
                         ethernet(1),
                         externalNFCToken(2),
                         integratedNFCToken(3),
                         nfcInterface(4),
                         display(5),
                         pin(6),
                         pushButton(7),
                         keypad(8)
                        }

    MAX-ACCESS  read-write
    STATUS      current
    DESCRIPTION
        "This object is defined as an CableLabs Extension to TR-181
         Device.WiFi.AccessPoint{i}.WPS.  The value must be selected 
         from the clabWIFIAccessPointWPSConfigMethodsSupported list 
         above."
    REFERENCE
        "TR-181 Device Data Model for TR-069."
    ::= {clabWIFIAccessPointWPSEntry 9 }


clabWIFIAssociatedDeviceTable OBJECT-TYPE
    SYNTAX      SEQUENCE OF ClabWIFIAssociatedDeviceEntry
    MAX-ACCESS  not-accessible
    STATUS      current
    DESCRIPTION
        "This object is defined in TR-181 Device.WiFi.AssociatedDevice{i}."
    REFERENCE
        "TR-181 Device Data Model for TR-069."
    ::= {clabWIFIObjects 9 }

clabWIFIAssociatedDeviceEntry    OBJECT-TYPE
    SYNTAX      ClabWIFIAssociatedDeviceEntry
    MAX-ACCESS  not-accessible
    STATUS      current
    DESCRIPTION
        "The Conceptual row of clabWIFIAssociatedDeviceTable."
    INDEX {
            clabWIFIAccessPointId, clabWIFIAssociatedDeviceId
          }
    ::= {clabWIFIAssociatedDeviceTable 1 }

ClabWIFIAssociatedDeviceEntry ::= SEQUENCE {
    clabWIFIAssociatedDeviceId
                 Unsigned32,
    clabWIFIAssociatedDeviceMACAddress
                 MacAddress,
    clabWIFIAssociatedDeviceAuthenticationState
                 TruthValue,
    clabWIFIAssociatedDeviceLastDataDownlinkRate
                 Unsigned32,
    clabWIFIAssociatedDeviceLastDataUplinkRate
                 Unsigned32,
    clabWIFIAssociatedDeviceSignalStrength
                 Integer32,
    clabWIFIAssociatedDeviceRetransmissions
                 Unsigned32,
    clabWIFIAssociatedDeviceActive
                 TruthValue,
    clabWIFIAssociatedDeviceMaxPacketRetryCount
                 Unsigned32,
    clabWIFIAssociatedDeviceStationCount
                 Counter32,
    clabWIFIAssociatedDeviceMaxNumOfStations
                 Unsigned32,
    clabWIFIAssociatedDeviceSecurityMode
                 INTEGER,
    clabWIFIAssociatedDeviceEncryptionAlgorithm
                 INTEGER, 
    clabWIFIAssociatedDeviceAssociationState
                 INTEGER                 
    }

clabWIFIAssociatedDeviceId    OBJECT-TYPE
    SYNTAX      Unsigned32 
    MAX-ACCESS  not-accessible
    STATUS      current
    DESCRIPTION
        "The key for a unique instance of this object. There is one 
        instance for each unique Associated device MAC Address."
    ::= {clabWIFIAssociatedDeviceEntry 1 }

clabWIFIAssociatedDeviceMACAddress    OBJECT-TYPE
    SYNTAX      MacAddress 
    MAX-ACCESS  read-only
    STATUS      current
    DESCRIPTION
        "This object is defined in TR-181 Device.WiFi.AssociatedDevice{i}.MACAddress."
    REFERENCE
        "TR-181 Device Data Model for TR-069."
    ::= {clabWIFIAssociatedDeviceEntry 2 }

clabWIFIAssociatedDeviceAuthenticationState    OBJECT-TYPE
    SYNTAX      TruthValue 
    MAX-ACCESS  read-only
    STATUS      current
    DESCRIPTION
        "This object is defined in TR-181 Device.WiFi.AssociatedDevice{i}.AuthenticationState."
    REFERENCE
        "TR-181 Device Data Model for TR-069."
    ::= {clabWIFIAssociatedDeviceEntry 3 }

clabWIFIAssociatedDeviceLastDataDownlinkRate    OBJECT-TYPE
    SYNTAX      Unsigned32 (1000..600000) 
    UNITS       "kbps"
    MAX-ACCESS  read-only
    STATUS      current
    DESCRIPTION
        "This object is defined in TR-181 Device.WiFi.AssociatedDevice{i}.LastDataDownlinkRate."
    REFERENCE
        "TR-181 Device Data Model for TR-069."
    ::= {clabWIFIAssociatedDeviceEntry 4 }

clabWIFIAssociatedDeviceLastDataUplinkRate    OBJECT-TYPE
    SYNTAX      Unsigned32 (1000..600000) 
    UNITS       "kbps"
    MAX-ACCESS  read-only
    STATUS      current
    DESCRIPTION
        "This object is defined in TR-181 Device.WiFi.AssociatedDevice{i}.DeviceLastDataUplinkRate."
    REFERENCE
        "TR-181 Device Data Model for TR-069."
    ::= {clabWIFIAssociatedDeviceEntry 5 }

clabWIFIAssociatedDeviceSignalStrength    OBJECT-TYPE
    SYNTAX      Integer32 (-200..0)
    UNITS       "dBm"
    MAX-ACCESS  read-only
    STATUS      current
    DESCRIPTION
        "This object is defined in TR-181 Device.WiFi.AssociatedDevice{i}.SignalStrength."
    REFERENCE
        "TR-181 Device Data Model for TR-069."
    ::= {clabWIFIAssociatedDeviceEntry 6 }

clabWIFIAssociatedDeviceRetransmissions    OBJECT-TYPE
    SYNTAX      Unsigned32 (0..100)
    UNITS       "packets"
    MAX-ACCESS  read-only
    STATUS      current
    DESCRIPTION
        "This object is defined in TR-181 Device.WiFi.AssociatedDevice{i}.Retransmissions."
    REFERENCE
        "TR-181 Device Data Model for TR-069."
    ::= {clabWIFIAssociatedDeviceEntry 7 }

clabWIFIAssociatedDeviceActive    OBJECT-TYPE
    SYNTAX      TruthValue 
    MAX-ACCESS  read-only
    STATUS      current
    DESCRIPTION
        "This object is defined in TR-181 Device.WiFi.AssociatedDevice{i}.Active."
    REFERENCE
        "TR-181 Device Data Model for TR-069."
    ::= {clabWIFIAssociatedDeviceEntry 8 }

clabWIFIAssociatedDeviceMaxPacketRetryCount    OBJECT-TYPE
    SYNTAX      Unsigned32 
    UNITS       "packets"
    MAX-ACCESS  read-write
    STATUS      current
    DESCRIPTION
        "This object indicates the number of packets to be retransmitted 
         to have an upper limit."
    ::= {clabWIFIAssociatedDeviceEntry 9 }

clabWIFIAssociatedDeviceStationCount    OBJECT-TYPE
    SYNTAX      Counter32
    UNITS       "stations" 
    MAX-ACCESS  read-only
    STATUS      deprecated
    DESCRIPTION
        "This object indicates the total number of stations associated at
         any point in time."
    ::= {clabWIFIAssociatedDeviceEntry 10 }

clabWIFIAssociatedDeviceMaxNumOfStations    OBJECT-TYPE
    SYNTAX      Unsigned32 
    UNITS       "stations"
    MAX-ACCESS  read-write
    STATUS      deprecated
    DESCRIPTION
        "This object specifies the maximum number of STAs associated at
         any point in time."
    ::= {clabWIFIAssociatedDeviceEntry 11 }

clabWIFIAssociatedDeviceSecurityMode    OBJECT-TYPE
    SYNTAX      INTEGER  {
                             none(1),
                             wep64(2),
                             wep128(3),
                             wpaPersonal(4),
                             wpa2Personal(5),
                             wpaWPA2Personal(6),
                             wpaEnterprise(7),
                             wpa2Enterprise(8),
                             wpaWpa2Enterprise(9)                         
                         }

    MAX-ACCESS  read-only
    STATUS      current
    DESCRIPTION
        "Reports the security mode for the associated device."
    ::= {clabWIFIAssociatedDeviceEntry 12 }

clabWIFIAssociatedDeviceEncryptionAlgorithm    OBJECT-TYPE
    SYNTAX      INTEGER  {
                          unknown(1),
                          tkip(2),
                          aes(3)                         
                         }
    MAX-ACCESS  read-only
    STATUS      deprecated
    DESCRIPTION
        "This object reports encryption method used during authentication."
    ::= {clabWIFIAssociatedDeviceEntry 13 }

clabWIFIAssociatedDeviceAssociationState    OBJECT-TYPE
SYNTAX      INTEGER  {
                      connected(1),
                      clientDisassociated(2),
                      forcedDisassociationAuth(3),
                      forcedDisassociationTimeout(4),
                      forcedDisassociationNetMode(5),
                      forcedDisassociationSnr(6),
                      other(7)
                     } 
    MAX-ACCESS  read-only
    STATUS      current
    DESCRIPTION
        "This object reports the status of any known devices that are or 
         have been associated if the CPE tracks device history after 
         disassociation."
    ::= {clabWIFIAssociatedDeviceEntry 14 }


clabWIFIDataRateStatsTable OBJECT-TYPE
    SYNTAX      SEQUENCE OF ClabWIFIDataRateStatsEntry
    MAX-ACCESS  not-accessible
    STATUS      deprecated
    DESCRIPTION
        "This object contains statistics for each speed rate of 
        an 802.11 LAN interface."
    ::= {clabWIFIObjects 10 }

clabWIFIDataRateStatsEntry    OBJECT-TYPE
    SYNTAX      ClabWIFIDataRateStatsEntry
    MAX-ACCESS  not-accessible
    STATUS      deprecated
    DESCRIPTION
        "The Conceptual row of clabWIFIDataRateStatsTable."
    INDEX {
            clabWIFIRadioId, clabWIFIDataRateStatsRate
          }
    ::= {clabWIFIDataRateStatsTable 1 }

ClabWIFIDataRateStatsEntry ::= SEQUENCE {
    clabWIFIDataRateStatsRate
                 Unsigned32,
    clabWIFIDataRateStatsFramesSent
                 Counter64,
    clabWIFIDataRateStatsFramesRetransmissionsSent
                 Counter64,
    clabWIFIDataRateStatsFramesReceived
                 Counter64,
    clabWIFIDataRateStatsFramesDuplicatedReceived
                 Counter64
      }

clabWIFIDataRateStatsRate    OBJECT-TYPE
    SYNTAX      Unsigned32 
    UNITS       "Mbps"
    MAX-ACCESS  not-accessible
    STATUS      deprecated
    DESCRIPTION
        "This key represents the data speed for the statistics 
        collected. the value is reported in integer units of Mbps."
    ::= {clabWIFIDataRateStatsEntry 1 }

clabWIFIDataRateStatsFramesSent    OBJECT-TYPE
    SYNTAX      Counter64 
    UNITS       "frames"
    MAX-ACCESS  read-only
    STATUS      deprecated
    DESCRIPTION
        "The FramesSent Parameter indicates the total number of frames 
        transmitted out of the interface (not marked as duplicated).
The value of this counter MAY be reset to zero when the CPE is rebooted."
    ::= {clabWIFIDataRateStatsEntry 2 }

clabWIFIDataRateStatsFramesRetransmissionsSent    OBJECT-TYPE
    SYNTAX      Counter64 
    UNITS       "frames"
    MAX-ACCESS  read-only
    STATUS      deprecated
    DESCRIPTION
        "The FramesRetransmissionsSent parameter indicates the total 
        number of frames retransmitted out of the interface (marked 
        as duplicated).
        The value of this counter MAY be reset to zero when the CPE 
        is rebooted."
    ::= {clabWIFIDataRateStatsEntry 3 }

clabWIFIDataRateStatsFramesReceived    OBJECT-TYPE
    SYNTAX      Counter64 
    UNITS       "frames"
    MAX-ACCESS  read-only
    STATUS      deprecated
    DESCRIPTION
        "The FramesReceived parameter indicates the total number of 
        frames received on this interface (not marked as duplicated).
        The value of this counter MAY be reset to zero when the CPE is 
        rebooted."
    ::= {clabWIFIDataRateStatsEntry 4 }

clabWIFIDataRateStatsFramesDuplicatedReceived    OBJECT-TYPE
    SYNTAX      Counter64 
    UNITS       "frames"
    MAX-ACCESS  read-only
    STATUS      deprecated
    DESCRIPTION
        "The FramesDuplicatedReceived indicates the total number of 
        duplicated frames received on this interface.
        The value of this counter MAY be reset to zero when the CPE 
        is rebooted."
    ::= {clabWIFIDataRateStatsEntry 5 }

clabWIFIPeriodicStatsTable OBJECT-TYPE
    SYNTAX      SEQUENCE OF ClabWIFIPeriodicStatsEntry
    MAX-ACCESS  not-accessible
    STATUS      current
    DESCRIPTION
        "This object contains periodic statistics for an 802.11 SSID 
        on a CPE device. Note that these statistics refer to the link 
        layer, not to the physical layer. This object does not include 
        the total byte and packet statistics, which are, for 
        historical reasons, in the parent object."
    ::= {clabWIFIObjects 11 }

clabWIFIPeriodicStatsEntry    OBJECT-TYPE
    SYNTAX      ClabWIFIPeriodicStatsEntry
    MAX-ACCESS  not-accessible
    STATUS      current
    DESCRIPTION
        "The Conceptual row of clabWIFIPeriodicStatsTable."
    INDEX {
            clabWIFISSIDId, 
            clabWIFIPeriodicStatsInterval, 
            clabWIFIPeriodicStatsId
          }
    ::= {clabWIFIPeriodicStatsTable 1 }

ClabWIFIPeriodicStatsEntry ::= SEQUENCE {
    clabWIFIPeriodicStatsInterval
                 Unsigned32,
    clabWIFIPeriodicStatsId
                 Unsigned32,
    clabWIFIPeriodicStatsDeviceMACAddress
                 MacAddress,
    clabWIFIPeriodicStatsFramesSent
                 Counter64,
    clabWIFIPeriodicStatsDataFramesSentAck
                 Counter64,
    clabWIFIPeriodicStatsDataFramesSentNoAck
                 Counter64,
    clabWIFIPeriodicStatsDataFramesLost
                 Counter64,
    clabWIFIPeriodicStatsFramesReceived
                 Counter64,
    clabWIFIPeriodicStatsDataFramesReceived
                 Counter64,
    clabWIFIPeriodicStatsDataFramesDuplicateReceived
                 Counter64,
    clabWIFIPeriodicStatsProbesReceived
                 Counter32,
    clabWIFIPeriodicStatsProbesRejected
                 Counter32,
    clabWIFIPeriodicStatsRSSI
                 Integer32,
    clabWIFIPeriodicStatsSNR
                 Integer32,
    clabWIFIPeriodicStatsDisassociations
                 Counter32,
    clabWIFIPeriodicStatsAuthenticationFailures
                 Counter32,
    clabWIFIPeriodicStatsLastTimeAssociation
                 DateAndTime,
    clabWIFIPeriodicStatsLastTimeDisassociation
                 DateAndTime
      }

clabWIFIPeriodicStatsInterval    OBJECT-TYPE
    SYNTAX      Unsigned32 (0 | 24 | 48 | 96 )
    MAX-ACCESS  not-accessible
    STATUS      current
    DESCRIPTION
        "This key indicates the Interval where the measurements were 
        Accumulated.
        The interval of measurements is synchronized with the wall clock.
        The total number of intervals is based on a 24 hour period. 
        At an interval of 15 minutes 96 intervals (1..96)  are defined, 
        at 30 minutes, 48 intervals (1..48) and 24 intervals (1..24) 
        for 1 hour measurement interval.
        Devices with  no capabilities to report measurements per interval 
        will report the value 0 for the interval attribute of the unique 
        statistics  instance."
    ::= {clabWIFIPeriodicStatsEntry 1 }

clabWIFIPeriodicStatsId    OBJECT-TYPE
    SYNTAX      Unsigned32 
    MAX-ACCESS  not-accessible
    STATUS      current
    DESCRIPTION
        "The Id key represents a unique identifier for a client 
        Mac address in a given statistics measurement interval."
    ::= {clabWIFIPeriodicStatsEntry 2 }

clabWIFIPeriodicStatsDeviceMACAddress    OBJECT-TYPE
    SYNTAX      MacAddress 
    MAX-ACCESS  read-only
    STATUS      current
    DESCRIPTION
        "The DeviceMACAddress represents the MAC address of an 
        associated client device."
    ::= {clabWIFIPeriodicStatsEntry 3 }

clabWIFIPeriodicStatsFramesSent    OBJECT-TYPE
    SYNTAX      Counter64 
    UNITS       "frames"
    MAX-ACCESS  read-only
    STATUS      current
    DESCRIPTION
        "FrameSent is the total number of frames transmitted out of 
        the interface.
        For conventional 802.11 MAC (a,b,g) this counter corresponds 
        to the total of MSDUs (MAC Service Data Unit) being transmitted.
        For High Throughput transmissions this corresponds to the 
        A-MSDU (Aggregation MSDU)
        The value of this counter MAY be reset to zero when the 
        CPE is rebooted."
    ::= {clabWIFIPeriodicStatsEntry 4 }

clabWIFIPeriodicStatsDataFramesSentAck    OBJECT-TYPE
    SYNTAX      Counter64 
    UNITS       "frames"
    MAX-ACCESS  read-only
    STATUS      current
    DESCRIPTION
        "DataFramesSentAck is the total number of MSDU frames marked 
        as duplicates and non duplicates acknowledged.
        The value of this counter MAY be reset to zero when the CPE 
        is rebooted."
    ::= {clabWIFIPeriodicStatsEntry 5 }

clabWIFIPeriodicStatsDataFramesSentNoAck    OBJECT-TYPE
    SYNTAX      Counter64 
    UNITS       "frames"
    MAX-ACCESS  read-only
    STATUS      current
    DESCRIPTION
        "DataFramesSentNoAck is the total number of MSDU frames 
        retransmitted out of the interface (i.e., marked as duplicate 
        and non-duplicate) and not acknowledged but not including 
        those defined in dataFramesLost.
        The value of this counter MAY be reset to zero when the 
        CPE is rebooted."
    ::= {clabWIFIPeriodicStatsEntry 6 }

clabWIFIPeriodicStatsDataFramesLost    OBJECT-TYPE
    SYNTAX      Counter64 
    UNITS       "frames"
    MAX-ACCESS  read-only
    STATUS      current
    DESCRIPTION
        "DataFramesLost is the total number of MSDU frames retransmitted 
        out of the interface that where not acknowledged and discarded 
        for reaching max number of retransmissions.
        The value of this counter MAY be reset to zero when the CPE 
        is rebooted."
    ::= {clabWIFIPeriodicStatsEntry 7 }

clabWIFIPeriodicStatsFramesReceived    OBJECT-TYPE
    SYNTAX      Counter64 
    UNITS       "frames"
    MAX-ACCESS  read-only
    STATUS      current
    DESCRIPTION
        "FramesReceived is the total number of frames received by the 
        interface.
        For conventional 802.11 MAC (a,b,g) this counter corresponds to the 
        total of MSDUs (MAC Service Data Unit) being transmitted.
        For High Throughput transmissions (n) this corresponds to A-MSDUs 
        (Aggregation MSDU) and MSDUs.
        The value of this counter MAY be reset to zero when the CPE 
        is rebooted."
    ::= {clabWIFIPeriodicStatsEntry 8 }

clabWIFIPeriodicStatsDataFramesReceived    OBJECT-TYPE
    SYNTAX      Counter64 
    UNITS       "frames"
    MAX-ACCESS  read-only
    STATUS      current
    DESCRIPTION
        "DataFramesReceived is the total number of MSDU frames 
        received and  marked as non-duplicates.
        The value of this counter MAY be reset to zero when the CPE 
        is rebooted."
    ::= {clabWIFIPeriodicStatsEntry 9 }

clabWIFIPeriodicStatsDataFramesDuplicateReceived    OBJECT-TYPE
    SYNTAX      Counter64 
    UNITS       "frames"
    MAX-ACCESS  read-only
    STATUS      current
    DESCRIPTION
        "DataFramesDuplicateReceived is the total number of duplicated 
        frames received on this interface.
        The value of this counter MAY be reset to zero when the 
        CPE is rebooted."
    ::= {clabWIFIPeriodicStatsEntry 10 }

clabWIFIPeriodicStatsProbesReceived    OBJECT-TYPE
    SYNTAX      Counter32 
    UNITS       "probes"
    MAX-ACCESS  read-only
    STATUS      current
    DESCRIPTION
        "ProbesReceived is the total number of probes received."
    ::= {clabWIFIPeriodicStatsEntry 11 }

clabWIFIPeriodicStatsProbesRejected    OBJECT-TYPE
    SYNTAX      Counter32 
    UNITS       "probes"
    MAX-ACCESS  read-only
    STATUS      current
    DESCRIPTION
        "ProbesRejected is the total number of probes rejected."
    ::= {clabWIFIPeriodicStatsEntry 12 }

clabWIFIPeriodicStatsRSSI    OBJECT-TYPE
    SYNTAX      Integer32 
    UNITS       "dBm"
    MAX-ACCESS  read-only
    STATUS      current
    DESCRIPTION
        "The Received Signal Strength indicator is the energy observed 
        at the antenna receiver for a current transmission."
    ::= {clabWIFIPeriodicStatsEntry 13 }

clabWIFIPeriodicStatsSNR    OBJECT-TYPE
    SYNTAX      Integer32 
    UNITS       "dB"
    MAX-ACCESS  read-only
    STATUS      current
    DESCRIPTION
        "The signal to Noise Ratio (SNR) parameter represents the strength 
        of the signal compared to received noise."
    ::= {clabWIFIPeriodicStatsEntry 14 }

clabWIFIPeriodicStatsDisassociations    OBJECT-TYPE
    SYNTAX      Counter32 
    UNITS       "disassociations"
    MAX-ACCESS  read-only
    STATUS      current
    DESCRIPTION
        "Disassociations represents the total number of client 
        disassociations."
    ::= {clabWIFIPeriodicStatsEntry 15 }

clabWIFIPeriodicStatsAuthenticationFailures    OBJECT-TYPE
    SYNTAX      Counter32 
    UNITS       "authenticationfailures"
    MAX-ACCESS  read-only
    STATUS      current
    DESCRIPTION
        "AuthenticationFailures indicates the total number of 
        authentication failures."
    ::= {clabWIFIPeriodicStatsEntry 16 }

clabWIFIPeriodicStatsLastTimeAssociation    OBJECT-TYPE
    SYNTAX      DateAndTime 
    MAX-ACCESS  read-only
    STATUS      current
    DESCRIPTION
        "The LastTimeAssociation parameter represents the last 
        time the client was associated."
    ::= {clabWIFIPeriodicStatsEntry 17 }

clabWIFIPeriodicStatsLastTimeDisassociation    OBJECT-TYPE
    SYNTAX      DateAndTime 
    MAX-ACCESS  read-only
    STATUS      current
    DESCRIPTION
        "LastTimeDisassociation parameter represents the last time 
        the client disassociate from the interface. 
The all zeros value indicates the client is currently associated. "
    ::= {clabWIFIPeriodicStatsEntry 18 }

clabWIFISSIDPolicyTable OBJECT-TYPE
    SYNTAX      SEQUENCE OF ClabWIFISSIDPolicyEntry
    MAX-ACCESS  not-accessible
    STATUS      current
    DESCRIPTION
        "The SSIDPolicy object defines the configuration of policies, 
        behaviors and event thresholds controlled per SSID."
    ::= {clabWIFIObjects 12 }

clabWIFISSIDPolicyEntry    OBJECT-TYPE
    SYNTAX      ClabWIFISSIDPolicyEntry
    MAX-ACCESS  not-accessible
    STATUS      current
    DESCRIPTION
        "The Conceptual row of clabWIFISSIDPolicyTable."
    INDEX {
            clabWIFISSIDId
          }
    ::= {clabWIFISSIDPolicyTable 1 }

ClabWIFISSIDPolicyEntry ::= SEQUENCE {
    clabWIFISSIDPolicyBlockAfterAttempts
                 Unsigned32,
    clabWIFISSIDPolicyAllocatedBandwidth
                 Unsigned32,
    clabWIFISSIDPolicyAuthenticationFailures
                 Unsigned32,
    clabWIFISSIDPolicyNonAuthenticatedTraffic
                 Unsigned32,
    clabWIFISSIDPolicyAssociationFailures
                 Unsigned32,
    clabWIFISSIDPolicyStatsInterval
                 Unsigned32,
    clabWIFISSIDPolicySNRThreshold
                 Integer32,
    clabWIFISSIDPolicyANPIThreshold
                 Integer32,
    clabWIFISSIDPolicyLowReceivedPowerThreshold
                 Integer32,
    clabWIFISSIDPolicyLowPowerDeniedAccessThreshold
                 Integer32,
    clabWIFISSIDPolicyLowPowerDisassociationThreshold
                 Integer32,
    clabWIFISSIDPolicyRowStatus
                 RowStatus,
    clabWIFISSIDPolicyBeaconMcsLevelInUse
                 SnmpAdminString,
    clabWIFISSIDPolicyBeaconMcsLevelsSupported
                 SnmpAdminString             
      }

clabWIFISSIDPolicyBlockAfterAttempts    OBJECT-TYPE
    SYNTAX      Unsigned32 
    MAX-ACCESS  read-create
    STATUS      current
    DESCRIPTION
        "The BlockAfterAttempts parameter indicates the maximum number 
        of attempts a client is allowed to attempt registration before 
        being denied access. Exceeding this value generates one event. 
        Events from same client should not reoccur more than once an 
        hour.
        The value zero indicates no connection attempts restrictions."
    DEFVAL      { 0 }
    ::= {clabWIFISSIDPolicyEntry 1 }

clabWIFISSIDPolicyAllocatedBandwidth    OBJECT-TYPE
    SYNTAX      Unsigned32 
    UNITS       "Mbps"
    MAX-ACCESS  read-create
    STATUS      current
    DESCRIPTION
        "The AllocatedBandwidth parameter indicates the maximum 
        bandwidth reserved for a particular interface. 
The value zero indicates no limit."
    DEFVAL      { 0 }
    ::= {clabWIFISSIDPolicyEntry 2 }

clabWIFISSIDPolicyAuthenticationFailures    OBJECT-TYPE
    SYNTAX      Unsigned32 
    MAX-ACCESS  read-create
    STATUS      current
    DESCRIPTION
        "The AuthenticationFailures parameter indicates the number of 
        Authenticationfailures a station simultaneously produces to 
        generate the event.
        Events from same client should not reoccur more than once an 
        hour.
        The value 0 indicates no threshold and events of this type are 
        not generated."
    DEFVAL      { 0 }
    ::= {clabWIFISSIDPolicyEntry 3 }

clabWIFISSIDPolicyNonAuthenticatedTraffic    OBJECT-TYPE
    SYNTAX      Unsigned32
    MAX-ACCESS  read-create
    STATUS      current
    DESCRIPTION
        "The NonAuthenticatedTraffic parameter represents the number 
        of non-authenticated messages received from a station to generate 
        an event. Events from same client should not reoccur more 
        than once an hour.
        The value 0 indicates no threshold and events of this type are 
        not generated."
    DEFVAL      { 0 }
    ::= {clabWIFISSIDPolicyEntry 4 }

clabWIFISSIDPolicyAssociationFailures    OBJECT-TYPE
    SYNTAX      Unsigned32 
    MAX-ACCESS  read-create
    STATUS      current
    DESCRIPTION
        "The AssociationFailures indicates the number of simultaneous 
        association failures from a station to generate an event. 
        Events from same client should not reoccur more than once an 
        hour.
        The value 0 indicates no threshold and events of this type are 
        not generated."
    DEFVAL      { 0 }
    ::= {clabWIFISSIDPolicyEntry 5 }

clabWIFISSIDPolicyStatsInterval    OBJECT-TYPE
    SYNTAX      Unsigned32 
    UNITS       "minutes"
    MAX-ACCESS  read-create
    STATUS      current
    DESCRIPTION
        "The StatsInterval parameter indicates the interval value to 
        collect per-interval statistics.

        The value 0 indicates no interval and values reported are 
        snapshots at the time of the request. "
    DEFVAL      { 0 }
    ::= {clabWIFISSIDPolicyEntry 6 }

clabWIFISSIDPolicySNRThreshold    OBJECT-TYPE
    SYNTAX      Integer32 
    UNITS       "dB"
    MAX-ACCESS  read-create
    STATUS      current
    DESCRIPTION
        "The SNR parameter indicates the threshold to report SNR. 
        The value -100 indicates no threshold, and events of this 
        type are not generated."
    DEFVAL      { -100 }
    ::= {clabWIFISSIDPolicyEntry 7 }

clabWIFISSIDPolicyANPIThreshold    OBJECT-TYPE
    SYNTAX      Integer32 
    UNITS       "dBm"
    MAX-ACCESS  read-create
    STATUS      current
    DESCRIPTION
        "The ANPI parameter indicates the threshold to report the 
        Average Noise plus Interference. The value -100 indicates no 
        threshold, and events of this type are not generated."
    DEFVAL      { -100 }
    ::= {clabWIFISSIDPolicyEntry 8 }

clabWIFISSIDPolicyLowReceivedPowerThreshold    OBJECT-TYPE
    SYNTAX      Integer32 
    UNITS       "dBm"
    MAX-ACCESS  read-create
    STATUS      current
    DESCRIPTION
        "The LowReceivedPowerThreshold parameter indicates the power 
        level threshold to generate an event whenever the station 
        received power is below the threshold. The value -100 indicates 
        no threshold is set, and events of this type are not generated."
    DEFVAL      { -100 }
    ::= {clabWIFISSIDPolicyEntry 9 }

clabWIFISSIDPolicyLowPowerDeniedAccessThreshold    OBJECT-TYPE
    SYNTAX      Integer32 
    UNITS       "dBm"
    MAX-ACCESS  read-create
    STATUS      current
    DESCRIPTION
        "The LowPowerDeniedAccessThreshold parameter indicates the 
        power level threshold to deny client association whenever the 
        station received power is below the threshold. The value -100 
        indicates no threshold, and events of this type are not 
        generated."
    DEFVAL      { -100 }
    ::= {clabWIFISSIDPolicyEntry 10 }

clabWIFISSIDPolicyLowPowerDisassociationThreshold    OBJECT-TYPE
    SYNTAX      Integer32 
    UNITS       "dBm"
    MAX-ACCESS  read-create
    STATUS      current
    DESCRIPTION
        "The LowerPowerDissasociationThreshold parameter indicates 
        the threshold to report Disassociation due to low power. 
        The Wi-Fi GW should refuse associations when the power level 
        is below this RSSI level. The value -100 indicates no 
        threshold, and events of this type are not generated."
    DEFVAL      { -100 }
    ::= {clabWIFISSIDPolicyEntry 11 }
    
clabWIFISSIDPolicyRowStatus    OBJECT-TYPE
    SYNTAX      RowStatus 
    MAX-ACCESS  read-create
    STATUS      current
    DESCRIPTION
        "The status of this instance."
    ::= {clabWIFISSIDPolicyEntry 12 }     

clabWIFISSIDPolicyBeaconMcsLevelInUse    OBJECT-TYPE
    SYNTAX      SnmpAdminString 
    MAX-ACCESS  read-create
    STATUS      current
    DESCRIPTION
        "The BeaconMcsLevelInUse parameter specifies the beacon MCS to 
         be used."
    ::= {clabWIFISSIDPolicyEntry 13 }

clabWIFISSIDPolicyBeaconMcsLevelsSupported    OBJECT-TYPE
    SYNTAX      SnmpAdminString 
    MAX-ACCESS  read-only
    STATUS      current
    DESCRIPTION
        "The BeaconMcsLevelsSupported parameter specifies all the beacon MCSs 
         supported."
    ::= {clabWIFISSIDPolicyEntry 14 }


clabWIFIClientSessionsTable OBJECT-TYPE
    SYNTAX      SEQUENCE OF ClabWIFIClientSessionsEntry
    MAX-ACCESS  not-accessible
    STATUS      current
    DESCRIPTION
        "The ClientSessions object represents the current 
        and closed sessions (association connections). 
        When the maximum number of instances is reached, the oldest 
        closed session instance is replaced by a newly created client 
        association."
    ::= {clabWIFIObjects 13 }

clabWIFIClientSessionsEntry    OBJECT-TYPE
    SYNTAX      ClabWIFIClientSessionsEntry
    MAX-ACCESS  not-accessible
    STATUS      current
    DESCRIPTION
        "The Conceptual row of clabWIFIClientSessionsTable."
    INDEX {
            clabWIFIAccessPointId, clabWIFIClientSessionsId
          }
    ::= {clabWIFIClientSessionsTable 1 }

ClabWIFIClientSessionsEntry ::= SEQUENCE {
    clabWIFIClientSessionsId
                 Unsigned32,
    clabWIFIClientSessionsDeviceMACAddress
                 MacAddress,
    clabWIFIClientSessionsStart
                 DateAndTime,
    clabWIFIClientSessionsStop
                 DateAndTime,
    clabWIFIClientSessionsTerminationCode
                 Unsigned32,
    clabWIFIClientSessionsTerminationMeaning
                 SnmpAdminString
      }

clabWIFIClientSessionsId    OBJECT-TYPE
    SYNTAX      Unsigned32 
    MAX-ACCESS  not-accessible
    STATUS      current
    DESCRIPTION
        "The Id key identifies a single client  MAC Address."
    ::= {clabWIFIClientSessionsEntry 1 }

clabWIFIClientSessionsDeviceMACAddress    OBJECT-TYPE
    SYNTAX      MacAddress 
    MAX-ACCESS  read-only
    STATUS      current
    DESCRIPTION
        "The DeviceMACAddress parameter indicates the MAC address 
        of an associated client device."
    ::= {clabWIFIClientSessionsEntry 2 }

clabWIFIClientSessionsStart    OBJECT-TYPE
    SYNTAX      DateAndTime 
    MAX-ACCESS  read-only
    STATUS      current
    DESCRIPTION
        "The Start parameter indicates the time when the session 
        started."
    ::= {clabWIFIClientSessionsEntry 3 }

clabWIFIClientSessionsStop    OBJECT-TYPE
    SYNTAX      DateAndTime 
    MAX-ACCESS  read-only
    STATUS      current
    DESCRIPTION
        "The Stop parameter indicates the time when the session ended. 
        If the session us current the value reported is all zeros."
    ::= {clabWIFIClientSessionsEntry 4 }

clabWIFIClientSessionsTerminationCode    OBJECT-TYPE
    SYNTAX      Unsigned32 
    MAX-ACCESS  read-only
    STATUS      current
    DESCRIPTION
        "The TerminationCode parameter indicates the Reason Code or the 
        Status Code that lead to ending the association of the station. 
        Reason code and Status code overlaps. The context of the type of 
        termination is provided by the TerminationMeaning attribute.
        The value zero indicates the session is active."
    ::= {clabWIFIClientSessionsEntry 5 }

clabWIFIClientSessionsTerminationMeaning    OBJECT-TYPE
    SYNTAX      SnmpAdminString (SIZE(0..32))
    MAX-ACCESS  read-only
    STATUS      current
    DESCRIPTION
        "The TerminationMeaning parameter indicates the meaning of the 
        Reason Code or Status Code for the ended session.  
        The zero-length string is used when the instance corresponds 
        to an active session."
    ::= {clabWIFIClientSessionsEntry 6 }

clabWIFIClientStatsTable OBJECT-TYPE
    SYNTAX      SEQUENCE OF ClabWIFIClientStatsEntry
    MAX-ACCESS  not-accessible
    STATUS      current
    DESCRIPTION
        "The ClientStats object contains accumulative statistics 
        for each client station.
        A station is reported only after is associated for the 
        first time. "
    ::= {clabWIFIObjects 14 }

clabWIFIClientStatsEntry    OBJECT-TYPE
    SYNTAX      ClabWIFIClientStatsEntry
    MAX-ACCESS  not-accessible
    STATUS      current
    DESCRIPTION
        "The Conceptual row of clabWIFIClientStatsTable."
    INDEX {
            clabWIFIAccessPointId, 
            clabWIFIClientStatsInterval, 
            clabWIFIClientStatsId
          }
    ::= {clabWIFIClientStatsTable 1 }

ClabWIFIClientStatsEntry ::= SEQUENCE {
    clabWIFIClientStatsInterval
                 Unsigned32,
    clabWIFIClientStatsId
                 Unsigned32,
    clabWIFIClientStatsDeviceMACAddress
                 MacAddress,
    clabWIFIClientStatsFramesSent
                 Counter64,
    clabWIFIClientStatsDataFramesSentAck
                 Counter64,
    clabWIFIClientStatsDataFramesSentNoAck
                 Counter64,
    clabWIFIClientStatsDataFramesLost
                 Counter64,
    clabWIFIClientStatsFramesReceived
                 Counter64,
    clabWIFIClientStatsDataFramesReceived
                 Counter64,
    clabWIFIClientStatsDataFramesDuplicateReceived
                 Counter64,
    clabWIFIClientStatsProbesReceived
                 Counter32,
    clabWIFIClientStatsProbesRejected
                 Counter32,
    clabWIFIClientStatsRSSI
                 Integer32,
    clabWIFIClientStatsSNR
                 Integer32,
    clabWIFIClientStatsDisassociations
                 Counter32,
    clabWIFIClientStatsAuthenticationFailures
                 Counter32,
    clabWIFIClientStatsLastTimeAssociation
                 DateAndTime,
    clabWIFIClientStatsLastTimeDisassociation
                 DateAndTime,
    clabWIFIClientStatsThroughput
                 Unsigned32,
    clabWIFIClientStatsPktErrorRatePerSTA
                 Unsigned32
      }

clabWIFIClientStatsInterval    OBJECT-TYPE
    SYNTAX      Unsigned32 (0 | 24 | 48 | 96 )
    MAX-ACCESS  not-accessible
    STATUS      current
    DESCRIPTION
        "The Interval parameter indicate the measurements were 
        accumulated.
        The interval of measurements is synchronized with the 
        wall clock
        The total number of intervals is based on a 24 hour period. 
        At an interval of 15 minutes 96 intervals (1..96)  are defined, 
        at 30 minutes, 48 intervals (1..48) and 24 intervals (1..24) 
        for 1 hour measurement interval.
        Devices with  no capable to report measurements per interval 
        will report the value 0 for the interval attribute."
    ::= {clabWIFIClientStatsEntry 1 }

clabWIFIClientStatsId    OBJECT-TYPE
    SYNTAX      Unsigned32 
    MAX-ACCESS  not-accessible
    STATUS      current
    DESCRIPTION
        "The Id key identifies a single client  MAC Address."
    ::= {clabWIFIClientStatsEntry 2 }

clabWIFIClientStatsDeviceMACAddress    OBJECT-TYPE
    SYNTAX      MacAddress 
    MAX-ACCESS  read-only
    STATUS      current
    DESCRIPTION
        "The DeviceMACAddress parameter indicates the MAC address of 
        an associated client device."
    ::= {clabWIFIClientStatsEntry 3 }

clabWIFIClientStatsFramesSent    OBJECT-TYPE
    SYNTAX      Counter64 
    UNITS       "frames"
    MAX-ACCESS  read-only
    STATUS      current
    DESCRIPTION
        "The FramesSent parameter indicates the total number of frames 
        transmitted out of the interface.
        For conventional 802.11 MAC (a,b,g) this counter corresponds 
        to the total of MSDUs (MAC Service Data Unit) being transmitted.
        For High Throughput transmissions this corresponds to the 
        A-MSDU (Aggregation MSDU)
        The value of this counter MAY be reset to zero when the CPE 
        is rebooted."
    ::= {clabWIFIClientStatsEntry 4 }

clabWIFIClientStatsDataFramesSentAck    OBJECT-TYPE
    SYNTAX      Counter64 
    UNITS       "frames"
    MAX-ACCESS  read-only
    STATUS      current
    DESCRIPTION
        "The DataFramesSentAck parameter indicates the total number of 
        MSDU frames marked as duplicates and non duplicates acknowledged.
        The value of this counter MAY be reset to zero when the CPE is 
        rebooted."
    ::= {clabWIFIClientStatsEntry 5 }

clabWIFIClientStatsDataFramesSentNoAck    OBJECT-TYPE
    SYNTAX      Counter64 
    UNITS       "frames"
    MAX-ACCESS  read-only
    STATUS      current
    DESCRIPTION
        "The DataFramesSentNoAck parameter indicates the total number of 
        MSDU frames retransmitted out of the interface 
        (i.e., marked as duplicate and non-duplicate) and not acknowledged 
        but not including those defined in dataFramesLost.
        The value of this counter MAY be reset to zero when the CPE is 
        rebooted."
    ::= {clabWIFIClientStatsEntry 6 }

clabWIFIClientStatsDataFramesLost    OBJECT-TYPE
    SYNTAX      Counter64 
    UNITS       "frames"
    MAX-ACCESS  read-only
    STATUS      current
    DESCRIPTION
        "The DataFramesLost parameter indicates the total number of 
        MSDU frames retransmitted out of the interface that where not 
        acknowledged and discarded for reaching max number of 
        retransmissions.
        The value of this counter MAY be reset to zero when the CPE is 
        rebooted."
    ::= {clabWIFIClientStatsEntry 7 }

clabWIFIClientStatsFramesReceived    OBJECT-TYPE
    SYNTAX      Counter64 
    UNITS       "frames"
    MAX-ACCESS  read-only
    STATUS      current
    DESCRIPTION
        "The FramesReceived parameter indicates the total number of 
        frames received by the interface.
        For conventional 802.11 MAC (a,b,g) this counter corresponds 
        to the total of MSDUs (MAC Service Data Unit) being transmitted.
        For High Throughput transmissions (n) this corresponds to 
        A-MSDUs (Aggregation MSDU) and MSDUs.
        The value of this counter MAY be reset to zero when the 
        CPE is rebooted."
    ::= {clabWIFIClientStatsEntry 8 }

clabWIFIClientStatsDataFramesReceived    OBJECT-TYPE
    SYNTAX      Counter64 
    UNITS       "frames"
    MAX-ACCESS  read-only
    STATUS      current
    DESCRIPTION
        "The DataFramesReceived parameter indicates the total number 
        of MSDU frames received and  marked as non-duplicates.
        The value of this counter MAY be reset to zero when the CPE 
        is rebooted."
    ::= {clabWIFIClientStatsEntry 9 }

clabWIFIClientStatsDataFramesDuplicateReceived    OBJECT-TYPE
    SYNTAX      Counter64 
    UNITS       "frames"
    MAX-ACCESS  read-only
    STATUS      current
    DESCRIPTION
        "The DataFramesDuplicateReceived parameter indicates the total 
        number of duplicated frames received on this interface.
        The value of this counter MAY be reset to zero when the 
        CPE is rebooted."
    ::= {clabWIFIClientStatsEntry 10 }

clabWIFIClientStatsProbesReceived    OBJECT-TYPE
    SYNTAX      Counter32 
    UNITS       "probes"
    MAX-ACCESS  read-only
    STATUS      current
    DESCRIPTION
        "The ProbesReceived parameter indicates the Total number of 
        probes received."
    ::= {clabWIFIClientStatsEntry 11 }

clabWIFIClientStatsProbesRejected    OBJECT-TYPE
    SYNTAX      Counter32 
    UNITS       "probes"
    MAX-ACCESS  read-only
    STATUS      current
    DESCRIPTION
        "The ProbesRejected parameter indicates the total number of 
        probes rejected."
    ::= {clabWIFIClientStatsEntry 12 }

clabWIFIClientStatsRSSI    OBJECT-TYPE
    SYNTAX      Integer32 
    UNITS       "dBm"
    MAX-ACCESS  read-only
    STATUS      current
    DESCRIPTION
        "The Received Signal Strength Indicator, RSSI, parameter is the 
        energy observed at the antenna receiver for a current 
        transmission."
    ::= {clabWIFIClientStatsEntry 13 }

clabWIFIClientStatsSNR    OBJECT-TYPE
    SYNTAX      Integer32 
    UNITS       "dB"
    MAX-ACCESS  read-only
    STATUS      current
    DESCRIPTION
        "The signal to Noise Ratio (SNR) parameter indicates the signal 
        strength received from a client compared to the noise received."
    ::= {clabWIFIClientStatsEntry 14 }

clabWIFIClientStatsDisassociations    OBJECT-TYPE
    SYNTAX      Counter32 
    UNITS       "disassociations"
    MAX-ACCESS  read-only
    STATUS      current
    DESCRIPTION
        "The Disassociations parameter indicates the total number of 
        client disassociations."
    ::= {clabWIFIClientStatsEntry 15 }

clabWIFIClientStatsAuthenticationFailures    OBJECT-TYPE
    SYNTAX      Counter32 
    UNITS       "authenticationfailures"
    MAX-ACCESS  read-only
    STATUS      current
    DESCRIPTION
        "The AuthenticationFailures parameter indicates the total 
        number of authentication failures."
    ::= {clabWIFIClientStatsEntry 16 }

clabWIFIClientStatsLastTimeAssociation    OBJECT-TYPE
    SYNTAX      DateAndTime 
    MAX-ACCESS  read-only
    STATUS      current
    DESCRIPTION
        "The LastTimeAssociation parameter indicates the Last time 
        the client was associated."
    ::= {clabWIFIClientStatsEntry 17 }

clabWIFIClientStatsLastTimeDisassociation    OBJECT-TYPE
    SYNTAX      DateAndTime 
    MAX-ACCESS  read-only
    STATUS      current
    DESCRIPTION
        "The  LastTimeDisassociation parameter indicates the last time 
        the client disassociate from the interface. 
        The all zeros value indicates the client is currently 
        associated. "
    ::= {clabWIFIClientStatsEntry 18 }

clabWIFIClientStatsThroughput    OBJECT-TYPE
    SYNTAX      Unsigned32 
    MAX-ACCESS  read-only
    STATUS      current
    DESCRIPTION
        " This object indicates the throughput expressed in Kbps."
    ::= {clabWIFIClientStatsEntry 19 }

clabWIFIClientStatsPktErrorRatePerSTA    OBJECT-TYPE
    SYNTAX      Unsigned32 
    MAX-ACCESS  read-only
    STATUS      current
    DESCRIPTION
        " This object indicates the traffic quality (e.g., HTTP, TCP) 
         of a STA."
    ::= {clabWIFIClientStatsEntry 20 }


clabWIFIRadiusClientTable OBJECT-TYPE
    SYNTAX      SEQUENCE OF ClabWIFIRadiusClientEntry
    MAX-ACCESS  not-accessible
    STATUS      current
    DESCRIPTION
        "This object is the extension of Radius Client operation
        for the Access Point 802.1x Authenticator for WPA Enterprise. 
        An instance is relevant when the attribute 
        AccessPointSecurity.ModeEnabled is 'WPA-Enterprise' or
        'WPA2-Enterprise' or 'WPA-WPA2-Enterprise'."
    ::= {clabWIFIObjects 15 }

clabWIFIRadiusClientEntry    OBJECT-TYPE
    SYNTAX      ClabWIFIRadiusClientEntry
    MAX-ACCESS  not-accessible
    STATUS      current
    DESCRIPTION
        "The Conceptual row of clabWIFIRadiusClientTable."
    INDEX {
            clabWIFIAccessPointId
          }
    ::= {clabWIFIRadiusClientTable 1 }

ClabWIFIRadiusClientEntry ::= SEQUENCE {
    clabWIFIRadiusClientNASIdentifier
                 SnmpAdminString,
    clabWIFIRadiusClientLocationPolicy
                 OCTET STRING,
    clabWIFIRadiusClientOperatorName
                 SnmpAdminString,
    clabWIFIRadiusClientLocationInformation
                 OCTET STRING,
    clabWIFIRadiusClientLocationData
                 OCTET STRING,
    clabWIFIRadiusClientUsageReports
                 TruthValue,
    clabWIFIRadiusClientIntervalInterimReport
                 TruthValue,
    clabWIFIRadiusClientAPTransitionReport
                 TruthValue,
    clabWIFIRadiusClientGigawordReport
                 TruthValue,
    clabWIFIRadiusClientRowStatus
                 RowStatus
      }

clabWIFIRadiusClientNASIdentifier    OBJECT-TYPE
    SYNTAX      SnmpAdminString
    MAX-ACCESS  read-create
    STATUS      current
    DESCRIPTION
        "The NAS-Identifier parameter corresponds to the Radius 
        attribute NAS-Identifier used in Access request messages.
        The device always sends the Radius parameter NAS-IP-Address
        and will send the NAS-Identifier parameter when this 
        attribute is set to other than the zero-length string. 
        The NAS-Identifier attribute can be used as a hint to 
        indicate the authentication server the SSID domain where 
        the WiFi endpoint tries to authenticate, i.e., 
        when more than one SSID domains are using the same 
        Radius server instance."
    ::= {clabWIFIRadiusClientEntry 1 }

clabWIFIRadiusClientLocationPolicy    OBJECT-TYPE
    SYNTAX      OCTET STRING (SIZE(0..64)) 
    MAX-ACCESS  read-create
    STATUS      current
    DESCRIPTION
        "The LocationPolicy  corresponds to the string value of the 
        Radius Basic-Location-Policy-Rules attribute per RFC 5580"
    ::= {clabWIFIRadiusClientEntry 2 }

clabWIFIRadiusClientOperatorName    OBJECT-TYPE
    SYNTAX      SnmpAdminString (SIZE(0..32)) 
    MAX-ACCESS  read-create
    STATUS      current
    DESCRIPTION
        "The OperatorName parameter corresponds to the string value of the 
        Radius Operator-Name attribute per RFC 5580."
    ::= {clabWIFIRadiusClientEntry 3 }

clabWIFIRadiusClientLocationInformation    OBJECT-TYPE
    SYNTAX      OCTET STRING (SIZE(0..253)) 
    MAX-ACCESS  read-create
    STATUS      current
    DESCRIPTION
        "The LocationInformation parameter corresponds to the string 
        value of the Radius Location-Information  attribute per 
        RFC 5580."
    ::= {clabWIFIRadiusClientEntry 4 }

clabWIFIRadiusClientLocationData    OBJECT-TYPE
    SYNTAX      OCTET STRING (SIZE(0..253)) 
    MAX-ACCESS  read-create
    STATUS      current
    DESCRIPTION
        "The Location Data parameter corresponds to the string value of 
        the Radius LocationData attribute per RFC 5580."
    ::= {clabWIFIRadiusClientEntry 5 }

clabWIFIRadiusClientUsageReports    OBJECT-TYPE
    SYNTAX      TruthValue 
    MAX-ACCESS  read-create
    STATUS      current
    DESCRIPTION
        "The UsageReports parameter indicates whether the client send 
        usage data 'true' or not 'false'."
    DEFVAL      { false }
    ::= {clabWIFIRadiusClientEntry 6 }

clabWIFIRadiusClientIntervalInterimReport    OBJECT-TYPE
    SYNTAX      TruthValue 
    MAX-ACCESS  read-create
    STATUS      current
    DESCRIPTION
        "The IntervalInterimReport parameter indicates whether the client 
        send Interim reports at time intervals 'true' or not 'false'."
    DEFVAL      { false }
    ::= {clabWIFIRadiusClientEntry 7 }

clabWIFIRadiusClientAPTransitionReport    OBJECT-TYPE
    SYNTAX      TruthValue 
    MAX-ACCESS  read-create
    STATUS      current
    DESCRIPTION
        "A 'true' value for the APTransitionReport parameter indicates the 
        client sends Interim reports when the stations transitions to a 
        different Access point."
    DEFVAL      { false }
    ::= {clabWIFIRadiusClientEntry 8 }

clabWIFIRadiusClientGigawordReport    OBJECT-TYPE
    SYNTAX      TruthValue 
    MAX-ACCESS  read-create
    STATUS      current
    DESCRIPTION
        "A 'true' value for Gigaword Report indicates the client sends 
        Interim reports when the 32-bit counters rollover"
    DEFVAL      { false }
    ::= {clabWIFIRadiusClientEntry 9 }

clabWIFIRadiusClientRowStatus    OBJECT-TYPE
    SYNTAX      RowStatus 
    MAX-ACCESS  read-create
    STATUS      current
    DESCRIPTION
        "The status of this instance."
    ::= {clabWIFIRadiusClientEntry 10 }

clabWIFIWIFICommitSettings OBJECT IDENTIFIER
    ::= {clabWIFIObjects 16 }

clabWIFIWIFICommitSettingsValue    OBJECT-TYPE
    SYNTAX      TruthValue 
    MAX-ACCESS  read-write
    STATUS      deprecated
    DESCRIPTION
        "This attribute when set to 'true' flushes the WiFi settings in
        non-volatile memory and reinitialize the WiFi system with the 
        new set of values without reboot. 

        This attribute reports a value 'false' when WiFi attributes have
        been changed but the changes are not active (i.e.,. not flushed
        in non-volatile and not part of the active configuration).  

        Systems that support immediate commit upon any attribute change 
        will report this attribute as 'true' always, and silently 
        accepts sets to 'true'."

    ::= {clabWIFIWIFICommitSettings 1 } 
    
clabWIFIApNeighborStatsTable OBJECT-TYPE
    SYNTAX      SEQUENCE OF ClabWIFIApNeighborStatsEntry
    MAX-ACCESS  not-accessible
    STATUS      deprecated
    DESCRIPTION
        "This table defines neighbor information known through channel
         scans."
    ::= {clabWIFIObjects 17 }

clabWIFIApNeighborStatsEntry    OBJECT-TYPE
    SYNTAX      ClabWIFIApNeighborStatsEntry
    MAX-ACCESS  not-accessible
    STATUS      deprecated
    DESCRIPTION
        "The conceptual row of clabWIFIApNeighborStatsTable."
    INDEX {
            clabWIFIAccessPointId
          }
    ::= {clabWIFIApNeighborStatsTable 1 }

ClabWIFIApNeighborStatsEntry ::= SEQUENCE {
    clabWIFIApNeighborStatsSSID
                 SnmpAdminString,
    clabWIFIApNeighborStatsCurrentChannel
                 Unsigned32,
    clabWIFIApNeighborStatsCurrentBandwidth
                 Unsigned32,
    clabWIFIApNeighborStatsRSSI
                 Integer32
      }

clabWIFIApNeighborStatsSSID    OBJECT-TYPE
    SYNTAX      SnmpAdminString (SIZE(0..32))
    MAX-ACCESS  read-only
    STATUS      deprecated
    DESCRIPTION
        "The attribute indicates the current SSID of the neighbor."
    ::= {clabWIFIApNeighborStatsEntry 1 }  
    
clabWIFIApNeighborStatsCurrentChannel    OBJECT-TYPE
    SYNTAX      Unsigned32 (1..255)
    MAX-ACCESS  read-only
    STATUS      deprecated
    DESCRIPTION
        "The attribute indicates the current channel being used by the 
         neighboring AP."
    ::= {clabWIFIApNeighborStatsEntry 2 }
    
clabWIFIApNeighborStatsCurrentBandwidth    OBJECT-TYPE
    SYNTAX      Unsigned32 (20 | 40 | 80 | 160)
    UNITS       "MHz"
    MAX-ACCESS  read-only
    STATUS      deprecated
    DESCRIPTION
        "The attribute indicates the current bandwidth in which the 
         neighboring AP is operating."
    ::= {clabWIFIApNeighborStatsEntry 3 }  
    
clabWIFIApNeighborStatsRSSI    OBJECT-TYPE
    SYNTAX      Integer32 
    UNITS       "dBm"
    MAX-ACCESS  read-only
    STATUS      deprecated
    DESCRIPTION
        "The attribute indicates the signal strength at which packets
         from the neighboring AP are received at the measuring AP, in 
         terms of dBm."
    ::= {clabWIFIApNeighborStatsEntry 4 } 
    
clabWIFIAccessPointAccessControlFilter OBJECT IDENTIFIER
    ::= { clabWIFIObjects 18 }

clabWIFIAccessPointClearAccessControlFilterTable OBJECT-TYPE
    SYNTAX      TruthValue
    MAX-ACCESS  read-write
    STATUS      current
    DESCRIPTION
        "Writing true to this object clears the clabWIFIAccessPointAccessControlFilterTable 
         of all entries. Reading this object always return false"
    ::= { clabWIFIAccessPointAccessControlFilter 1 } 

clabWIFIAccessPointAccessControlFilterAccessAllow OBJECT-TYPE
    SYNTAX      TruthValue
    MAX-ACCESS  read-write
    STATUS      current
    DESCRIPTION
        "True allows access to AP, False denies Access to AP."
    ::= { clabWIFIAccessPointAccessControlFilter 2 }

clabWIFIAccessPointAccessControlFilterTable OBJECT-TYPE
    SYNTAX      SEQUENCE OF ClabWIFIAccessPointAccessControlFilterEntry
    MAX-ACCESS  not-accessible
    STATUS      current
    DESCRIPTION
        "This table provides a list of MAC address with filter decisions
         (allow/deny access)."
    ::= { clabWIFIAccessPointAccessControlFilter 3 }

clabWIFIAccessPointAccessControlFilterEntry    OBJECT-TYPE
    SYNTAX      ClabWIFIAccessPointAccessControlFilterEntry
    MAX-ACCESS  not-accessible
    STATUS      current
    DESCRIPTION
        "The conceptual row of clabWIFIAccessPointAccessControlFilterTable."
    INDEX {
            clabWIFIAccessPointId,
            clabWIFIAccessPointAccessControlFilterIndex
          }
    ::= { clabWIFIAccessPointAccessControlFilterTable  1 }

ClabWIFIAccessPointAccessControlFilterEntry ::= SEQUENCE {
    clabWIFIAccessPointAccessControlFilterIndex
                 Unsigned32,
    clabWIFIAccessPointAccessControlFilterMACAddress
                 MacAddress
    }

clabWIFIAccessPointAccessControlFilterIndex OBJECT-TYPE
    SYNTAX      Unsigned32
    MAX-ACCESS  not-accessible
    STATUS      current
    DESCRIPTION
        "Secondary index to allow multiple MACs associated with same AP."
    ::= { clabWIFIAccessPointAccessControlFilterEntry    1 }  

clabWIFIAccessPointAccessControlFilterMACAddress OBJECT-TYPE
    SYNTAX      MacAddress
    MAX-ACCESS  read-only
    STATUS      current
    DESCRIPTION
        "STA MAC to be filtered. The value of 
         clabWIFIAccessPointAccessControlFilterAccessAllow
         indicates whether the MAC is allowed or not allowed."
    ::= { clabWIFIAccessPointAccessControlFilterEntry    2 }

clabWIFIAccessPointAccessControlFilterNumberOfEntries OBJECT-TYPE
    SYNTAX      Integer32
    MAX-ACCESS  read-only
    STATUS      current
    DESCRIPTION
        "The number of entries in the clabWIFIAccessPointAccessControlFilterTable."
    ::= { clabWIFIAccessPointAccessControlFilter 4 }

clabWIFIAccessPointPasspoint OBJECT IDENTIFIER
    ::= {clabWIFIObjects 19 }

clabWIFIAccessPointInterworkingServiceTable OBJECT-TYPE
    SYNTAX      SEQUENCE OF ClabWIFIAccessPointInterworkingServiceEntry
    MAX-ACCESS  not-accessible
    STATUS      current
    DESCRIPTION
        "This table This object is used to configure the Passpoint parameters 
         for each Access Point."
    ::= { clabWIFIAccessPointPasspoint 1 }

clabWIFIAccessPointInterworkingServiceEntry    OBJECT-TYPE
    SYNTAX      ClabWIFIAccessPointInterworkingServiceEntry
    MAX-ACCESS  not-accessible
    STATUS      current
    DESCRIPTION
        "The conceptual row of clabWIFIAccessPointInterworkingServiceTable."
    INDEX {
            clabWIFIAccessPointId
                      }
    ::= { clabWIFIAccessPointInterworkingServiceTable 1 }
	
ClabWIFIAccessPointInterworkingServiceEntry ::= SEQUENCE {
    clabWIFIAccessPointInterworkingServiceInternet
                 TruthValue,
    clabWIFIAccessPointInterworkingServiceHESSID
                 MacAddress,
    clabWIFIAccessPointInterworkingServiceAccessNetworkType
                 OCTET STRING,
    clabWIFIAccessPointInterworkingServiceVenueGroupCode
                 OCTET STRING,
    clabWIFIAccessPointInterworkingServiceVenueTypeCode
                 OCTET STRING
    }  

clabWIFIAccessPointInterworkingServiceInternet OBJECT-TYPE
    SYNTAX      TruthValue
    MAX-ACCESS  read-write
    STATUS      current
    DESCRIPTION
        " Set to true if the network provides connectivity to the Internet; 
          otherwise it is set to false indicating that it is unspecified 
          whether the network provides connectivity to the Internet." 
    ::= { clabWIFIAccessPointInterworkingServiceEntry 1 }      

clabWIFIAccessPointInterworkingServiceHESSID OBJECT-TYPE
    SYNTAX      MacAddress
    MAX-ACCESS  read-only
    STATUS      current
    DESCRIPTION
        " MACAddress] Homogeneous Extended Service Set Identifier (HESSID)
          The HESSID is a globally unique identifier that in conjunction 
          with the WLAN-SSID, may be used to provide network identification 
          for a subscription service provider network AP."
    ::= { clabWIFIAccessPointInterworkingServiceEntry 2 }

clabWIFIAccessPointInterworkingServiceAccessNetworkType OBJECT-TYPE
    SYNTAX      OCTET STRING  (SIZE(1)) 
    MAX-ACCESS  read-only
    STATUS      current
    DESCRIPTION
        " Access Network Type value to be included in the Interworking IE in
          the beacons. (refer 8.4.2.94 of IEEE Std 802.11-2012). Possible 
          values are:
                        0 - Private network
                        1 - Private network with guest access 
                        2 - Chargeable public network 
                        3 - Free public network 
                        4 - Personal device network
                        5 - Emergency services only network 
                        6-13 - Reserved 
                        14 - Test or experimental
                        15 - Wildcard
          Note enumeration was not possible (i.e., cannot enumerate with 0)"
    ::= { clabWIFIAccessPointInterworkingServiceEntry 3 }      

clabWIFIAccessPointInterworkingServiceVenueGroupCode OBJECT-TYPE
    SYNTAX      OCTET STRING  (SIZE(1)) 
    MAX-ACCESS  read-only
    STATUS      current
    DESCRIPTION
        " Indicates the Venue Group of the Venue Info Field (refer 8.4.1.34 
          of IEEE Std 802.11-2012) where the access point is installed:
                        0 - Unspecified
                        1 - Assembly 
                        2 - Business 
                        3 - Educational 
                        4 - Factory and Industrial
                        5 - Institutional
                        7 - Residential
                        8 - Storage
                        9 - Utility and Maintenance
                        10 - Vehicular                      
                        11 - Outdoor
                        12-255 Reserved 
          Note enumeration was not possible (i.e., cannot enumerate with 0)"
    ::= { clabWIFIAccessPointInterworkingServiceEntry 4 }      

clabWIFIAccessPointInterworkingServiceVenueTypeCode OBJECT-TYPE
    SYNTAX      OCTET STRING  (SIZE(1)) 
    MAX-ACCESS  read-only
    STATUS      current
    DESCRIPTION
        " Indicates the Venue Type of the Venue Info Field (refer 8.4.1.34 of 
          IEEE Std 802.11-2012) where the access point is installed. The 
          possible values are listed in the referanced standard."
    ::= { clabWIFIAccessPointInterworkingServiceEntry  5 }      

clabWIFIAccessPointPasspointTable OBJECT-TYPE
    SYNTAX      SEQUENCE OF ClabWIFIAccessPointPasspointEntry
    MAX-ACCESS  not-accessible
    STATUS      current
    DESCRIPTION
        "This table This object is used to configure the Passpoint parameters 
         for each Access Point."
    ::= { clabWIFIAccessPointPasspoint 2 }

clabWIFIAccessPointPasspointEntry    OBJECT-TYPE
    SYNTAX      ClabWIFIAccessPointPasspointEntry
    MAX-ACCESS  not-accessible
    STATUS      current
    DESCRIPTION
        "The conceptual row of clabWIFIAccessPointPasspointTable."
    INDEX {
            clabWIFIAccessPointId
                      }
    ::= { clabWIFIAccessPointPasspointTable 1 }
	
ClabWIFIAccessPointPasspointEntry ::= SEQUENCE {
    clabWIFIAccessPointPasspointCapabilityList
                 OCTET STRING,
    clabWIFIAccessPointPasspointOnlineSignupSupported
                 TruthValue,
    clabWIFIAccessPointPasspointDGAFEnable
                 TruthValue,
    clabWIFIAccessPointPasspointP2PEnable
                 TruthValue,
    clabWIFIAccessPointPasspointQoSMappingEnable
                 TruthValue,
    clabWIFIAccessPointPasspointASRAEnable
                 TruthValue,
    clabWIFIAccessPointPasspointANQPDomainID
                 Integer32,
    clabWIFIAccessPointPasspointEAPMethod
                 OCTET STRING,
    clabWIFIAccessPointPasspointManagementFrameProtectionEnable
                 TruthValue,
    clabWIFIAccessPointPasspointCapabilities 
                 BITS
    }

clabWIFIAccessPointPasspointCapabilityList OBJECT-TYPE
    SYNTAX      OCTET STRING (SIZE(1..255)) 
    MAX-ACCESS  read-only
    STATUS      deprecated
    DESCRIPTION
        "HS Capability List drawn from the following table in exact order. 
               HS Query list (1)
               HS Capability list (2)  
               Operator Friendly Name (3)
               WAN Metrics (4)
               Connection Capability (5)
               NAI Home Realm Query (6)
               Operating Class Indication (7)
               OSU Providers list (8)
               Reserved (9)
               Icon Request (10)
               Icon Binary File (11)
         Each Octet corresponds to a capability by realitve position as follows.
               0-not supported
               1-supported"
    ::= { clabWIFIAccessPointPasspointEntry 1 }     

clabWIFIAccessPointPasspointOnlineSignupSupported OBJECT-TYPE
    SYNTAX      TruthValue
    MAX-ACCESS  read-only
    STATUS      current
    DESCRIPTION
        "True OSU supported, False = No OSU support."
    ::= { clabWIFIAccessPointPasspointEntry 2 }

clabWIFIAccessPointPasspointDGAFEnable OBJECT-TYPE
    SYNTAX      TruthValue
    MAX-ACCESS  read-write
    STATUS      current
    DESCRIPTION
        "'True' Indicates Downstream Forwarding of Group-Addressed 
         Frames (DGAF) is supported.  'False' indicates no support 
         For DGAF"
    ::= { clabWIFIAccessPointPasspointEntry 3 }

clabWIFIAccessPointPasspointP2PEnable OBJECT-TYPE
    SYNTAX      TruthValue
    MAX-ACCESS  read-write
    STATUS      current
    DESCRIPTION
        "'True' indicates P2P cross connect is supported.
          'False' indicates P2P is not supported."
    ::= { clabWIFIAccessPointPasspointEntry 4 }

clabWIFIAccessPointPasspointQoSMappingEnable OBJECT-TYPE
    SYNTAX      TruthValue
    MAX-ACCESS  read-write
    STATUS      current
    DESCRIPTION
        "'True' enables Qos Mapping, 'False' disables'.  The mapping
          Is vendor implementation specific."
    ::= { clabWIFIAccessPointPasspointEntry 5 }

clabWIFIAccessPointPasspointASRAEnable OBJECT-TYPE
    SYNTAX      TruthValue
    MAX-ACCESS  read-write
    STATUS      current
    DESCRIPTION
        "'True' enables Additional Step Required for Access. 
         'False' disables'.  "
    ::= { clabWIFIAccessPointPasspointEntry 6 }

clabWIFIAccessPointPasspointANQPDomainID OBJECT-TYPE
    SYNTAX      Integer32
    MAX-ACCESS  read-only
    STATUS      current
    DESCRIPTION
        " ANQP Domain ID is a 16-bit field included in Beacon and Probe 
          response frames transmitted by the AP.

          All APs in the same ESS sharing a common, nonzero value of 
          ANQP Domain ID shall have identical ANQP information for the ANQP
          elements and Hotspot 2.0 vendor-specific ANQP elements.

          APs having their ANQP Domain ID field set to a value of zero have 
          unique ANQP information in one or more of their ANQP elements or 
          Hotspot 2.0 vendor-specific ANQP elements, or have not been 
          implemented with means of knowing whether their ANQP information is unique.

          APs having their ANQP Domain ID field set to -1 should not include ANQP
          Domain ID field in the HS2.0 indication element."
    ::= { clabWIFIAccessPointPasspointEntry 7 }

clabWIFIAccessPointPasspointEAPMethod OBJECT-TYPE
    SYNTAX      OCTET STRING
    MAX-ACCESS  read-only
    STATUS      current
    DESCRIPTION
        " EAP Method used by the AP. Refer to Device.IEEE8021x."
    ::= { clabWIFIAccessPointPasspointEntry 8 }

clabWIFIAccessPointPasspointManagementFrameProtectionEnable OBJECT-TYPE
    SYNTAX      TruthValue
    MAX-ACCESS  read-write
    STATUS      current
    DESCRIPTION
        "'True' enables Management Frame Protection, 'False' disables."
    ::= { clabWIFIAccessPointPasspointEntry 9 }

clabWIFIAccessPointPasspointCapabilities OBJECT-TYPE
     SYNTAX   BITS {
                     hsQueryList(0),
                     hsCapabilityList(1) ,
                     operatorFriendlyName(2),
                     wanMetrics(3),
                     connectionCapability(4),
                     naiHomeRealmQuery(5),
                     operatingClassIndication(6),
                     osuProvidersList(7),
                     reserved(8),
                     iconRequest(9),
                     iconBinaryFile(10)
                   }

    MAX-ACCESS  read-only
    STATUS      current
    DESCRIPTION
        "HS Capability List drawn from the following table. 
               HS Query list
               HS Capability list  
               Operator Friendly Name
               WAN Metrics
               Connection Capability
               NAI Home Realm Query
               Operating Class Indication
               OSU Providers list
               Reserved
               Icon Request
               Icon Binary File
         Each bit corresponds to a capability follows.
               0-not supported
               1-supported"
    ::= { clabWIFIAccessPointPasspointEntry 10 }     

clabWIFIAccessPointPasspointVenueNamesTable OBJECT-TYPE
    SYNTAX      SEQUENCE OF ClabWIFIAccessPointPasspointVenueNamesEntry
    MAX-ACCESS  not-accessible
    STATUS      deprecated
    DESCRIPTION
        "This table is used to configure the Passpoint venue names
         with country code for each."
    ::= { clabWIFIAccessPointPasspoint 3 }

clabWIFIAccessPointPasspointVenueNamesEntry    OBJECT-TYPE
    SYNTAX      ClabWIFIAccessPointPasspointVenueNamesEntry
    MAX-ACCESS  not-accessible
    STATUS      deprecated
    DESCRIPTION
        "The conceptual row of clabWIFIAccessPointPasspointVenueNamesTable."
    INDEX {
            clabWIFIAccessPointId
                      }
    ::= { clabWIFIAccessPointPasspointVenueNamesTable 1 }

ClabWIFIAccessPointPasspointVenueNamesEntry ::= SEQUENCE {
        clabWIFIAccessPointPasspointVenueNameIndex
                 Unsigned32,
        clabWIFIAccessPointPasspointVenueNameCountryCode
                 OCTET STRING,
        clabWIFIAccessPointPasspointVenueName
                 OCTET STRING 
    }

clabWIFIAccessPointPasspointVenueNameIndex OBJECT-TYPE
    SYNTAX      Unsigned32
    MAX-ACCESS  not-accessible
    STATUS      deprecated
    DESCRIPTION
        "Venue name country code."
    ::= { clabWIFIAccessPointPasspointVenueNamesEntry 1 }
 
clabWIFIAccessPointPasspointVenueNameCountryCode OBJECT-TYPE
    SYNTAX      OCTET STRING (SIZE(3|5))
    MAX-ACCESS  read-only
    STATUS      deprecated
    DESCRIPTION
        "Venue name country code."
    ::= { clabWIFIAccessPointPasspointVenueNamesEntry 2 }
 
clabWIFIAccessPointPasspointVenueName OBJECT-TYPE
    SYNTAX      OCTET STRING (SIZE(1..255)) 
    MAX-ACCESS  read-only
    STATUS      deprecated
    DESCRIPTION
        "Indicates the Venue Name where the access point is installed.  
         This additional meta data about the venue is included in the 
         Venue Name ANQP-element. This parameter accepts UTF-8 encoded 
         string represented as hexBinary string. "
    ::= { clabWIFIAccessPointPasspointVenueNamesEntry 3 }

clabWIFIAccessPointPasspointOperatorNamesTable OBJECT-TYPE
    SYNTAX      SEQUENCE OF ClabWIFIAccessPointPasspointOperatorNamesEntry
    MAX-ACCESS  not-accessible
    STATUS      current
    DESCRIPTION
        "This table is used to configure the Passpoint operator names
         with country code for each."
    ::= { clabWIFIAccessPointPasspoint 4 }

clabWIFIAccessPointPasspointOperatorNamesEntry    OBJECT-TYPE
    SYNTAX      ClabWIFIAccessPointPasspointOperatorNamesEntry
    MAX-ACCESS  not-accessible
    STATUS      current
    DESCRIPTION
        "The conceptual row of clabWIFIAccessPointPasspointOperatorNamesTable."
    INDEX {
            clabWIFIAccessPointId,
            clabWIFIAccessPointPasspointOperatorNameIndex
                      }
    ::= { clabWIFIAccessPointPasspointOperatorNamesTable 1 }
	
ClabWIFIAccessPointPasspointOperatorNamesEntry ::= SEQUENCE {
        clabWIFIAccessPointPasspointOperatorNameIndex
                 Unsigned32,        
        clabWIFIAccessPointPasspointOperatorNameCountryCode
                 OCTET STRING,
        clabWIFIAccessPointPasspointOperatorName
                 OCTET STRING 
    }

clabWIFIAccessPointPasspointOperatorNameIndex OBJECT-TYPE
    SYNTAX      Unsigned32
    MAX-ACCESS  not-accessible
    STATUS      current
    DESCRIPTION
        "Venue name country code."
    ::= { clabWIFIAccessPointPasspointOperatorNamesEntry 1 }

clabWIFIAccessPointPasspointOperatorNameCountryCode OBJECT-TYPE
    SYNTAX      OCTET STRING (SIZE(3|5))
    MAX-ACCESS  read-only
    STATUS      current
    DESCRIPTION
        "Venue name country code."
    ::= { clabWIFIAccessPointPasspointOperatorNamesEntry 2 }
 
clabWIFIAccessPointPasspointOperatorName OBJECT-TYPE
    SYNTAX      OCTET STRING (SIZE(1..255)) 
    MAX-ACCESS  read-only
    STATUS      current
    DESCRIPTION
        " Indicates the Operator Friendly Name of the entity operating 
          the IEEE 802.11 AN i.e. the Passpoint Operator. This parameter 
          accepts UTF-8 encoded string represented as hexBinary string. "
    ::= { clabWIFIAccessPointPasspointOperatorNamesEntry 3 }

clabWIFIAccessPointPasspointConsortiumTable OBJECT-TYPE
    SYNTAX      SEQUENCE OF ClabWIFIAccessPointPasspointConsortiumEntry
    MAX-ACCESS  not-accessible
    STATUS      current
    DESCRIPTION
        " A table of Consortium OIs (Organization Identifiers)which are 
         to be transmitted in an ANQP Roaming Consortium ANQP-element. 
         Each entry of this table corresponds to a roaming consortium or single 
         SSP. The first three entries of this table are transmitted in Beacon 
         and Probe response frames."
    ::= { clabWIFIAccessPointPasspoint 5 }

clabWIFIAccessPointPasspointConsortiumEntry    OBJECT-TYPE
    SYNTAX      ClabWIFIAccessPointPasspointConsortiumEntry
    MAX-ACCESS  not-accessible
    STATUS      current
    DESCRIPTION
        "The conceptual row of clabWIFIAccessPointPasspointConsortium Table."
    INDEX {
            clabWIFIAccessPointId,
            clabWIFIAccessPointPasspointConsortiumIndex
                      }
    ::= { clabWIFIAccessPointPasspointConsortiumTable 1 }
	
ClabWIFIAccessPointPasspointConsortiumEntry ::= SEQUENCE {
        clabWIFIAccessPointPasspointConsortiumIndex
                 Unsigned32,        
        clabWIFIAccessPointPasspointConsortiumOI
                 OCTET STRING 
    }

clabWIFIAccessPointPasspointConsortiumIndex OBJECT-TYPE
    SYNTAX      Unsigned32
    MAX-ACCESS  not-accessible
    STATUS      current
    DESCRIPTION
        "OI Table Index."
    ::= { clabWIFIAccessPointPasspointConsortiumEntry 1 }

clabWIFIAccessPointPasspointConsortiumOI OBJECT-TYPE
    SYNTAX      OCTET STRING (SIZE(3|5))
    MAX-ACCESS  read-only
    STATUS      current
    DESCRIPTION
        " The Organization Identifier field is 3 octets in length if 
          the organizationally unique identifier is an OUI, or 5 octets 
          in length if the organizationally unique identifier is 36 bits 
          in length. See 802.11-2012 for more information. "
    ::= { clabWIFIAccessPointPasspointConsortiumEntry 2 }

clabWIFIAccessPointPasspointDomainNamesTable OBJECT-TYPE
    SYNTAX      SEQUENCE OF ClabWIFIAccessPointPasspointDomainNamesEntry
    MAX-ACCESS  not-accessible
    STATUS      deprecated
    DESCRIPTION
        "This table A table of Domain Names of the entity operating the 
         IEEE 802.11 access network."
    ::= { clabWIFIAccessPointPasspoint 6 }

clabWIFIAccessPointPasspointDomainNamesEntry    OBJECT-TYPE
    SYNTAX      ClabWIFIAccessPointPasspointDomainNamesEntry
    MAX-ACCESS  not-accessible
    STATUS      current
    DESCRIPTION
        "The conceptual row of clabWIFIAccessPointPasspointDomainNamesTable."
    INDEX {
            clabWIFIAccessPointId,
            clabWIFIAccessPointPasspointDomainNamesIndex
                      }
    ::= { clabWIFIAccessPointPasspointDomainNamesTable 1 }
	
ClabWIFIAccessPointPasspointDomainNamesEntry ::= SEQUENCE {
        clabWIFIAccessPointPasspointDomainNamesIndex
                 Unsigned32,        
        clabWIFIAccessPointPasspointDomainNamesDomainName
                 OCTET STRING 
    }

clabWIFIAccessPointPasspointDomainNamesIndex OBJECT-TYPE
    SYNTAX      Unsigned32
    MAX-ACCESS  not-accessible
    STATUS      current
    DESCRIPTION
        "OI Table Index."
    ::= { clabWIFIAccessPointPasspointDomainNamesEntry 1 }

clabWIFIAccessPointPasspointDomainNamesDomainName OBJECT-TYPE
    SYNTAX      OCTET STRING (SIZE(3|5))
    MAX-ACCESS  read-only
    STATUS      current
    DESCRIPTION
        " The Organization Identifier field is 3 octets in length if 
          the organizationally unique identifier is an OUI, or 5 octets 
          in length if the organizationally unique identifier is 36 bits 
          in length. See 802.11-2012 for more information. "
    ::= { clabWIFIAccessPointPasspointDomainNamesEntry 2 }
  
clabWIFIAccessPointPasspointThreeGPPNetworkTable OBJECT-TYPE
    SYNTAX      SEQUENCE OF ClabWIFIAccessPointPasspointThreeGPPNetworkEntry
    MAX-ACCESS  not-accessible
    STATUS      current
    DESCRIPTION
        " A table of 3GPP Cellular Networks. The table contains Mobile Country
          Code (MCC) and Mobile Network Code (MNC) of the cellular networks 
          that the access point supports."
    ::= { clabWIFIAccessPointPasspoint 7 }

clabWIFIAccessPointPasspointThreeGPPNetworkEntry    OBJECT-TYPE
    SYNTAX      ClabWIFIAccessPointPasspointThreeGPPNetworkEntry
    MAX-ACCESS  not-accessible
    STATUS      current
    DESCRIPTION
        "The conceptual row of clabWIFIAccessPointPasspointThreeGPPNetworks Table."
    INDEX {
            clabWIFIAccessPointId,
            clabWIFIAccessPointPasspointThreeGPPNetworkIndex
                      }
    ::= { clabWIFIAccessPointPasspointThreeGPPNetworkTable 1 }
	
ClabWIFIAccessPointPasspointThreeGPPNetworkEntry ::= SEQUENCE {
        clabWIFIAccessPointPasspointThreeGPPNetworkIndex
                 Unsigned32,        
        clabWIFIAccessPointPasspointThreeGPPNetworkMNC
                 OCTET STRING,
        clabWIFIAccessPointPasspointThreeGPPNetworkMCC
                 OCTET STRING 
    }

clabWIFIAccessPointPasspointThreeGPPNetworkIndex OBJECT-TYPE
    SYNTAX      Unsigned32
    MAX-ACCESS  not-accessible
    STATUS      current
    DESCRIPTION
        "Venue name country code."
    ::= { clabWIFIAccessPointPasspointThreeGPPNetworkEntry 1 }
 
clabWIFIAccessPointPasspointThreeGPPNetworkMNC OBJECT-TYPE
    SYNTAX      OCTET STRING (SIZE(2|3))
    MAX-ACCESS  read-only
    STATUS      current
    DESCRIPTION
        "3GPP Network Code"
    ::= { clabWIFIAccessPointPasspointThreeGPPNetworkEntry 5 }

clabWIFIAccessPointPasspointThreeGPPNetworkMCC OBJECT-TYPE
    SYNTAX      OCTET STRING (SIZE(3))
    MAX-ACCESS  read-only
    STATUS      current
    DESCRIPTION
        " 3GPP Country Code "
    ::= { clabWIFIAccessPointPasspointThreeGPPNetworkEntry 6 }

clabWIFIAccessPointPasspointNAIRealmsTable OBJECT-TYPE
    SYNTAX      SEQUENCE OF ClabWIFIAccessPointPasspointNAIRealmsEntry
    MAX-ACCESS  not-accessible
    STATUS      deprecated
    DESCRIPTION
        "NAI Realms corresponding to SSPs for other entities accessible 
         via this AP.  This object is defined in 
         TR-181 Device.WiFi.AP.{i}.X_CableLabs_Passpoint_NAIRealm.{i} and 
         its children."
    ::= { clabWIFIAccessPointPasspoint 8 }

clabWIFIAccessPointPasspointNAIRealmsEntry    OBJECT-TYPE
    SYNTAX      ClabWIFIAccessPointPasspointNAIRealmsEntry
    MAX-ACCESS  not-accessible
    STATUS      deprecated
    DESCRIPTION
        "The conceptual row of clabWIFIAccessPointPasspointNAIRealms Table."
    INDEX {
            clabWIFIAccessPointId,
            clabWIFIAccessPointPasspointNAIRealmsIndex, 
            clabWIFIAccessPointPasspointNAIRealmsEapMethodsIndex,
            clabWIFIAccessPointPasspointNAIRealmsEapMethodsAuthParmIndex
           }
    ::= { clabWIFIAccessPointPasspointNAIRealmsTable 1 }
	
ClabWIFIAccessPointPasspointNAIRealmsEntry ::= SEQUENCE {
        clabWIFIAccessPointPasspointNAIRealmsIndex
                 Unsigned32,
        clabWIFIAccessPointPasspointNAIRealmsEapMethodsIndex
                 Unsigned32,
        clabWIFIAccessPointPasspointNAIRealmsEapMethodsAuthParmIndex        
                 Unsigned32,
        clabWIFIAccessPointPasspointNAIRealmsEncodingType
                 INTEGER,
        clabWIFIAccessPointPasspointNAIRealms
                 OCTET STRING,
        clabWIFIAccessPointPasspointNAIRealmsEapMethod
                 INTEGER,
        clabWIFIAccessPointPasspointNAIRealmsEapAuthParametersID 
                 OCTET STRING,
        clabWIFIAccessPointPasspointNAIRealmsEapAuthParametersValue
                 OCTET STRING
    }

clabWIFIAccessPointPasspointNAIRealmsIndex OBJECT-TYPE
    SYNTAX      Unsigned32
    MAX-ACCESS  not-accessible
    STATUS      deprecated
    DESCRIPTION
        "A unique index number for each NAI Realm."
    ::= { clabWIFIAccessPointPasspointNAIRealmsEntry 1 }

clabWIFIAccessPointPasspointNAIRealmsEapMethodsIndex OBJECT-TYPE
    SYNTAX      Unsigned32
    MAX-ACCESS  not-accessible
    STATUS      deprecated
    DESCRIPTION
        "A unique index number for each EAP Method associated 
          with an NAI Realm."
    ::= { clabWIFIAccessPointPasspointNAIRealmsEntry 2 }

clabWIFIAccessPointPasspointNAIRealmsEapMethodsAuthParmIndex OBJECT-TYPE
    SYNTAX      Unsigned32
    MAX-ACCESS  not-accessible
    STATUS      deprecated
    DESCRIPTION
        "A unique index number for each set of authentication parameters
         associated with each EAP Method."
    ::= { clabWIFIAccessPointPasspointNAIRealmsEntry 3 }

clabWIFIAccessPointPasspointNAIRealmsEncodingType OBJECT-TYPE
    SYNTAX      INTEGER {
                       rfc(1),
                       utf(2)
                      }
    MAX-ACCESS  read-only
    STATUS      deprecated
    DESCRIPTION
        " Indicates NAI Realm Encoding Type used to encode NAI Realm 
          ANQP Element. A value of 1 indicates that the NAI Realm in 
          the NAI Realm subfield is formatted in accordance with IETF 
          RFC4282. A value of 2 indicates that it is a UTF-8 formatted 
          character string."
    ::= { clabWIFIAccessPointPasspointNAIRealmsEntry 4 }   

clabWIFIAccessPointPasspointNAIRealms OBJECT-TYPE
    SYNTAX      OCTET STRING (SIZE(1..252))
    MAX-ACCESS  read-only
    STATUS      deprecated
    DESCRIPTION
        " NAI Realm Name."
    ::= { clabWIFIAccessPointPasspointNAIRealmsEntry 5 }   

clabWIFIAccessPointPasspointNAIRealmsEapMethod OBJECT-TYPE
    SYNTAX      INTEGER {
                        none(1),
                        eaptls(2),
                        eapttls(3),
                        peap(4),
                        eapmschapv2(5)
                        }
    MAX-ACCESS  read-only
    STATUS      deprecated
    DESCRIPTION
        "EAP Method type that the NAI Realm supports."
    ::= { clabWIFIAccessPointPasspointNAIRealmsEntry 11 } 

clabWIFIAccessPointPasspointNAIRealmsEapAuthParametersID OBJECT-TYPE
    SYNTAX      OCTET STRING
    MAX-ACCESS  read-only
    STATUS      deprecated
    DESCRIPTION
        "EAP Method Authentication Parameters."
    ::= { clabWIFIAccessPointPasspointNAIRealmsEntry 12 }

clabWIFIAccessPointPasspointNAIRealmsEapAuthParametersValue OBJECT-TYPE
    SYNTAX      OCTET STRING
    MAX-ACCESS  read-only
    STATUS      deprecated
    DESCRIPTION
        "EAP Method Authentication Parameters."
    ::= { clabWIFIAccessPointPasspointNAIRealmsEntry 13 }

clabWIFIAccessPointPasspointOSUTable OBJECT-TYPE
    SYNTAX      SEQUENCE OF ClabWIFIAccessPointPasspointOSUEntry
    MAX-ACCESS  not-accessible
    STATUS      deprecated
    DESCRIPTION
        "This table contains information regarding the Online Sign Up (OSU) 
         Service that is advertised via OSU Provider List element in beacon
         and probe frames. Refer section 4.8 of WFA HS2.0.  This object is
         defined in TR-181 Device.WiFi.AP.{i}.X_CableLabs_Passpoint_OS and 
         its children."
    ::= { clabWIFIAccessPointPasspoint 9 }

clabWIFIAccessPointPasspointOSUEntry    OBJECT-TYPE
    SYNTAX      ClabWIFIAccessPointPasspointOSUEntry
    MAX-ACCESS  not-accessible
    STATUS      deprecated
    DESCRIPTION
        "The conceptual row of clabWIFIAccessPointPasspointOSUTable."
    INDEX {
            clabWIFIAccessPointId,
            clabWIFIAccessPointPasspointOSUProviderIndex, 
            clabWIFIAccessPointPasspointOSUProviderNamesIndex,
            clabWIFIAccessPointPasspointOSUProviderIconsIndex
           }
    ::= { clabWIFIAccessPointPasspointOSUTable 1 }
	
    ClabWIFIAccessPointPasspointOSUEntry ::= SEQUENCE {
        clabWIFIAccessPointPasspointOSUProviderIndex
                 Unsigned32,
        clabWIFIAccessPointPasspointOSUProviderNamesIndex
                 Unsigned32,
        clabWIFIAccessPointPasspointOSUProviderIconsIndex
                 Unsigned32,
        clabWIFIAccessPointPasspointOSUProviderServiceDescIndex
                 Unsigned32,
        clabWIFIAccessPointPasspointOSUProviderServerURI
                 SnmpAdminString,
        clabWIFIAccessPointPasspointOSUProviderNAI
                 OCTET STRING,
        clabWIFIAccessPointPasspointOSUProviderNamesLanguageCode 
                 Unsigned32,
        clabWIFIAccessPointPasspointOSUProviderNamesFriendlyName
                 OCTET STRING,
        clabWIFIAccessPointPasspointOSUProviderIconFileName
                 OCTET STRING,
        clabWIFIAccessPointPasspointOSUProviderIconType
                 OCTET STRING,
        clabWIFIAccessPointPasspointOSUProviderIconWidth
                 Unsigned32,
        clabWIFIAccessPointPasspointOSUProviderIconHeight
                 Unsigned32,
        clabWIFIAccessPointPasspointOSUProviderIconLanguageCode
                 Unsigned32,
        clabWIFIAccessPointPasspointOSUProviderServiceDescLanguageCode
                 Unsigned32,
        clabWIFIAccessPointPasspointOSUProviderServiceDescription
                 OCTET STRING,
        clabWIFIAccessPointPasspointOSUProviderMethodsList
                 OCTET STRING
    }

clabWIFIAccessPointPasspointOSUProviderIndex OBJECT-TYPE
    SYNTAX      Unsigned32
    MAX-ACCESS  not-accessible
    STATUS      deprecated
    DESCRIPTION
        "A unique index number for each OSU Provider."
    ::= { clabWIFIAccessPointPasspointOSUEntry 1 }

clabWIFIAccessPointPasspointOSUProviderNamesIndex OBJECT-TYPE
    SYNTAX      Unsigned32
    MAX-ACCESS  not-accessible
    STATUS      deprecated
    DESCRIPTION
        "A unique index number for OSU provider friendly name."
    ::= { clabWIFIAccessPointPasspointOSUEntry 2 }

clabWIFIAccessPointPasspointOSUProviderIconsIndex OBJECT-TYPE
    SYNTAX      Unsigned32
    MAX-ACCESS  not-accessible
    STATUS      deprecated
    DESCRIPTION
        "A unique index number for each icon associated with an OSU provider."
    ::= { clabWIFIAccessPointPasspointOSUEntry 3 }

clabWIFIAccessPointPasspointOSUProviderServiceDescIndex OBJECT-TYPE
    SYNTAX      Unsigned32
    MAX-ACCESS  not-accessible
    STATUS      deprecated
    DESCRIPTION
        "A unique index number for each icon associated with an Service
         Description."
::= { clabWIFIAccessPointPasspointOSUEntry 4 }

clabWIFIAccessPointPasspointOSUProviderServerURI OBJECT-TYPE
    SYNTAX      SnmpAdminString
    MAX-ACCESS  read-only
    STATUS      deprecated
    DESCRIPTION
        " The URI of the OSU Server that is used for OSU with the 
          Service Provider indicated in the Names table. It is 
          formatted in accordance with the IETF RFC 3986."
    ::= { clabWIFIAccessPointPasspointOSUEntry 5 }   

clabWIFIAccessPointPasspointOSUProviderNAI OBJECT-TYPE
    SYNTAX      OCTET STRING (SIZE(1..253))
    MAX-ACCESS  read-only
    STATUS      deprecated
    DESCRIPTION
        " Contains the NAI that is used for OSU with the Service
          Provider Name. OSUNAI is formatted in accordance with 
          IETF RFC 4282."
    ::= { clabWIFIAccessPointPasspointOSUEntry 6 }   

clabWIFIAccessPointPasspointOSUProviderNamesLanguageCode OBJECT-TYPE
    SYNTAX      Unsigned32 (2 | 3)
    MAX-ACCESS  read-only
    STATUS      deprecated
    DESCRIPTION
        "A 2 or 3 octet ISO-14962-1997 encoded string field that 
         defines the language used in the OSU Provider Friendly 
         Name field. The code value is selected from ISO-639."
    ::= { clabWIFIAccessPointPasspointOSUEntry 7 } 

clabWIFIAccessPointPasspointOSUProviderNamesFriendlyName OBJECT-TYPE
    SYNTAX      OCTET STRING (SIZE(1..504))
    MAX-ACCESS  read-only
    STATUS      deprecated
    DESCRIPTION
        "Indicates the UTF-8 encoded (represented as hexBinary) OSU 
         Provider Friendly Name in the human language identified by 
         the language code. This parameter accepts UTF-8 encoded 
         string represented as hexBinary string."
    ::= { clabWIFIAccessPointPasspointOSUEntry 8 }
 
clabWIFIAccessPointPasspointOSUProviderIconFileName OBJECT-TYPE
    SYNTAX      OCTET STRING (SIZE(1..255))
    MAX-ACCESS  read-only
    STATUS      deprecated
    DESCRIPTION
        "The IconFilename is a UTF-8 encoded field whose value 
         contains the filename of the Icon having the metadata 
         provided in this icon instance."
    ::= { clabWIFIAccessPointPasspointOSUEntry 9 }

clabWIFIAccessPointPasspointOSUProviderIconType OBJECT-TYPE
    SYNTAX      OCTET STRING (SIZE(0..255))
    MAX-ACCESS  read-only
    STATUS      deprecated
    DESCRIPTION
        " The IconType is the MIME media type of the binary icon 
          file named by the IconFilename. The IconType field is 
          formatted in accordance with RFC 6838 and its value is 
          selected from the IANA MIME Media Types registered at
          http://www.iana.org/assignments/media-types/index.html."
    ::= { clabWIFIAccessPointPasspointOSUEntry 10 }

clabWIFIAccessPointPasspointOSUProviderIconWidth  OBJECT-TYPE
    SYNTAX      Unsigned32 (1..65535)
    MAX-ACCESS  read-only
    STATUS      deprecated
    DESCRIPTION
        " Width in pixel of the OSU Provider icon named by the 
          IconFilename."
    ::= { clabWIFIAccessPointPasspointOSUEntry 11 }

clabWIFIAccessPointPasspointOSUProviderIconHeight OBJECT-TYPE
    SYNTAX      Unsigned32 (1..65535)
    MAX-ACCESS  read-only
    STATUS      deprecated
    DESCRIPTION
        " Height in pixel of the OSU Provider icon named by the 
          IconFilename."
    ::= { clabWIFIAccessPointPasspointOSUEntry 12 }

clabWIFIAccessPointPasspointOSUProviderIconLanguageCode OBJECT-TYPE
    SYNTAX      Unsigned32 (2 | 3)
    MAX-ACCESS  read-only
    STATUS      deprecated
    DESCRIPTION
        " A 2 or 3 octet ISO-14962-1997 encoded string field that 
          defines the language used in the Icon file if any. The 
          code value is selected from ISO-639. If there is no 
          linguistic content to the icon/logo, the LanguageCode is 
          set to 'zxx'."
    ::= { clabWIFIAccessPointPasspointOSUEntry 13 }

clabWIFIAccessPointPasspointOSUProviderServiceDescLanguageCode OBJECT-TYPE
    SYNTAX      Unsigned32 (2 | 3)
    MAX-ACCESS  read-only
    STATUS      deprecated
    DESCRIPTION
        " A 2 or 3 octet ISO-14962-1997 encoded string field that 
          defines the language used in the OSU Provider Friendly 
          Name field. The code value is selected from ISO-639."
    ::= { clabWIFIAccessPointPasspointOSUEntry 14 }

clabWIFIAccessPointPasspointOSUProviderServiceDescription OBJECT-TYPE
    SYNTAX      OCTET STRING (SIZE(504))
    MAX-ACCESS  read-only
    STATUS      deprecated
    DESCRIPTION
        " Indicates the UTF-8 encoded (represented as hexBinary) 
          string containing the ServiceProviders description of the
          service offering."
    ::= { clabWIFIAccessPointPasspointOSUEntry 15 }

clabWIFIAccessPointPasspointOSUProviderMethodsList OBJECT-TYPE
    SYNTAX      OCTET STRING (SIZE(0..255))
    MAX-ACCESS  read-write
    STATUS      deprecated
    DESCRIPTION
        " A comma separated list of OSU Method values represented as integers. 
          The methods are listed in the ServiceProvider's preferred order 
          with the most-preferred method first. Possible values (integers)
          are selected from Table 10 of WFA HS2.0.

            0 - OMA-DM
            1 - SOAP-XML SPP

          All other values (2 - 255) are reserved. Example value '0,1' without quotes."
    ::= { clabWIFIAccessPointPasspointOSUEntry 16 }

clabWIFIAccessPointPasspoint2VenueNamesTable OBJECT-TYPE
    SYNTAX      SEQUENCE OF ClabWIFIAccessPointPasspoint2VenueNamesEntry
    MAX-ACCESS  not-accessible
    STATUS      current
    DESCRIPTION
        "This table is used to configure the Passpoint venue names
         with country code for each."
    ::= { clabWIFIAccessPointPasspoint 10 }
	
clabWIFIAccessPointPasspoint2VenueNamesEntry    OBJECT-TYPE
    SYNTAX      ClabWIFIAccessPointPasspoint2VenueNamesEntry
    MAX-ACCESS  not-accessible
    STATUS      current
    DESCRIPTION
        "The conceptual row of clabWIFIAccessPointPasspoint2VenueNamesTable."
    INDEX {
            clabWIFIAccessPointId,
			clabWIFIAccessPointPasspoint2VenueNameIndex
                      }
    ::= { clabWIFIAccessPointPasspoint2VenueNamesTable 1 }

ClabWIFIAccessPointPasspoint2VenueNamesEntry ::= SEQUENCE {
        clabWIFIAccessPointPasspoint2VenueNameIndex
                 Unsigned32,
        clabWIFIAccessPointPasspoint2VenueNameCountryCode
                 SnmpAdminString,
        clabWIFIAccessPointPasspoint2VenueName
                 SnmpAdminString 
    }

clabWIFIAccessPointPasspoint2VenueNameIndex OBJECT-TYPE
    SYNTAX      Unsigned32
    MAX-ACCESS  not-accessible
    STATUS      current
    DESCRIPTION
        "Venue name country code."
    ::= { clabWIFIAccessPointPasspoint2VenueNamesEntry 1 }
 
clabWIFIAccessPointPasspoint2VenueNameCountryCode OBJECT-TYPE
    SYNTAX      SnmpAdminString (SIZE(3|5))
    MAX-ACCESS  read-only
    STATUS      current
    DESCRIPTION
        "Venue name country code."
    ::= { clabWIFIAccessPointPasspoint2VenueNamesEntry 2 }
 
clabWIFIAccessPointPasspoint2VenueName OBJECT-TYPE
    SYNTAX      SnmpAdminString (SIZE(1..255)) 
    MAX-ACCESS  read-only
    STATUS      current
    DESCRIPTION
        "Indicates the Venue Name where the access point is installed.  
         This additional meta data about the venue is included in the 
         Venue Name ANQP-element. This parameter accepts UTF-8 encoded 
         string represented as hexBinary string. "
    ::= { clabWIFIAccessPointPasspoint2VenueNamesEntry 3 }

clabWIFIAccessPointPasspoint2NAIRealmsTable OBJECT-TYPE
    SYNTAX      SEQUENCE OF ClabWIFIAccessPointPasspoint2NAIRealmsEntry
    MAX-ACCESS  not-accessible
    STATUS      current
    DESCRIPTION
        "NAI Realms corresponding to SSPs for other entities accessible 
         via this AP.  This object is defined in 
         TR-181 Device.WiFi.AP.{i}.X_CableLabs_Passpoint_NAIRealm.{i} and 
         its children."
    ::= { clabWIFIAccessPointPasspoint 11 }
	
clabWIFIAccessPointPasspoint2NAIRealmsEntry    OBJECT-TYPE
    SYNTAX      ClabWIFIAccessPointPasspoint2NAIRealmsEntry
    MAX-ACCESS  not-accessible
    STATUS      current
    DESCRIPTION
        "The conceptual row of clabWIFIAccessPointPasspoint2NAIRealms Table."
    INDEX {
            clabWIFIAccessPointId,
            clabWIFIAccessPointPasspoint2NAIRealmsIndex
           }
    ::= { clabWIFIAccessPointPasspoint2NAIRealmsTable 1 }
	
ClabWIFIAccessPointPasspoint2NAIRealmsEntry ::= SEQUENCE {
        clabWIFIAccessPointPasspoint2NAIRealmsIndex
                 Unsigned32,
        clabWIFIAccessPointPasspoint2NAIRealmsEncodingType
                 INTEGER,
        clabWIFIAccessPointPasspoint2NAIRealms
                 SnmpAdminString
    }

clabWIFIAccessPointPasspoint2NAIRealmsIndex OBJECT-TYPE
    SYNTAX      Unsigned32
    MAX-ACCESS  not-accessible
    STATUS      current
    DESCRIPTION
        "A unique index number for each NAI Realm."
    ::= { clabWIFIAccessPointPasspoint2NAIRealmsEntry 1 }

clabWIFIAccessPointPasspoint2NAIRealmsEncodingType OBJECT-TYPE
    SYNTAX      INTEGER {
                       rfc(1),
                       utf(2)
                      }
    MAX-ACCESS  read-only
    STATUS      current
    DESCRIPTION
        " Indicates NAI Realm Encoding Type used to encode NAI Realm 
          ANQP Element. A value of 1 indicates that the NAI Realm in 
          the NAI Realm subfield is formatted in accordance with IETF 
          RFC4282. A value of 2 indicates that it is a UTF-8 formatted 
          character string."
    ::= { clabWIFIAccessPointPasspoint2NAIRealmsEntry 2 }   

clabWIFIAccessPointPasspoint2NAIRealms OBJECT-TYPE
    SYNTAX      SnmpAdminString (SIZE(1..252))
    MAX-ACCESS  read-only
    STATUS      current
    DESCRIPTION
        " NAI Realm Name."
    ::= { clabWIFIAccessPointPasspoint2NAIRealmsEntry 3 }   

clabWIFIAccessPointPasspoint2NAIRealmsEapMethodsTable OBJECT-TYPE
    SYNTAX      SEQUENCE OF ClabWIFIAccessPointPasspoint2NAIRealmsEapMethodsEntry
    MAX-ACCESS  not-accessible
    STATUS      current
    DESCRIPTION
        "This table is used to get the EAP method for each Realm."
    REFERENCE
    		"clabWIFIAccessPointPasspoint"
    ::= {clabWIFIAccessPointPasspoint 12 }

clabWIFIAccessPointPasspoint2NAIRealmsEapMethodsEntry    OBJECT-TYPE
    SYNTAX      ClabWIFIAccessPointPasspoint2NAIRealmsEapMethodsEntry
    MAX-ACCESS  not-accessible
    STATUS      current
    DESCRIPTION
        "The conceptual row of clabWIFIAccessPointPasspoint2NAIRealmsEapMethods Table."
    INDEX {
            clabWIFIAccessPointId,
			clabWIFIAccessPointPasspoint2NAIRealmsIndex,
			clabWIFIAccessPointPasspoint2NAIRealmsEapMethodsIndex
          }
    ::= {clabWIFIAccessPointPasspoint2NAIRealmsEapMethodsTable 1 }

ClabWIFIAccessPointPasspoint2NAIRealmsEapMethodsEntry ::= SEQUENCE {
        clabWIFIAccessPointPasspoint2NAIRealmsEapMethodsIndex
                 Unsigned32,
        clabWIFIAccessPointPasspoint2NAIRealmsEapMethod
                 INTEGER
      }

clabWIFIAccessPointPasspoint2NAIRealmsEapMethodsIndex OBJECT-TYPE
    SYNTAX      Unsigned32
    MAX-ACCESS  not-accessible
    STATUS      current
    DESCRIPTION
        "A unique index number for each EAP Method associated 
          with an NAI Realm."
    ::= { clabWIFIAccessPointPasspoint2NAIRealmsEapMethodsEntry 1 }

clabWIFIAccessPointPasspoint2NAIRealmsEapMethod OBJECT-TYPE
    SYNTAX      INTEGER {
                        none(1),
                        eaptls(2),
                        eapttls(3),
                        peap(4),
                        eapmschapv2(5)
                        }
    MAX-ACCESS  read-only
    STATUS      current
    DESCRIPTION
        "EAP Method type that the NAI Realm supports."
    ::= { clabWIFIAccessPointPasspoint2NAIRealmsEapMethodsEntry 2 } 

clabWIFIAccessPointPasspoint2NAIRealmsEapMethodsAuthTable OBJECT-TYPE
    SYNTAX      SEQUENCE OF ClabWIFIAccessPointPasspoint2NAIRealmsEapMethodsAuthEntry
    MAX-ACCESS  not-accessible
    STATUS      current
    DESCRIPTION
        "This table is used to get the Authentication ID and paramemters for each EAP method."
    REFERENCE
    		"clabWIFIAccessPointPasspoint"
    ::= {clabWIFIAccessPointPasspoint 13 }

clabWIFIAccessPointPasspoint2NAIRealmsEapMethodsAuthEntry    OBJECT-TYPE
    SYNTAX      ClabWIFIAccessPointPasspoint2NAIRealmsEapMethodsAuthEntry
    MAX-ACCESS  not-accessible
    STATUS      current
    DESCRIPTION
        "The conceptual row of clabWIFIAccessPointPasspoint2NAIRealmsEapMethodsAuth Table."
    INDEX {
            clabWIFIAccessPointId,
			clabWIFIAccessPointPasspoint2NAIRealmsIndex,
			clabWIFIAccessPointPasspoint2NAIRealmsEapMethodsIndex,
			clabWIFIAccessPointPasspoint2NAIRealmsEapMethodsAuthParmIndex
          }
    ::= {clabWIFIAccessPointPasspoint2NAIRealmsEapMethodsAuthTable 1 }

ClabWIFIAccessPointPasspoint2NAIRealmsEapMethodsAuthEntry ::= SEQUENCE {
        clabWIFIAccessPointPasspoint2NAIRealmsEapMethodsAuthParmIndex
                 Unsigned32,
        clabWIFIAccessPointPasspoint2NAIRealmsEapAuthParametersID 
                 OCTET STRING,
        clabWIFIAccessPointPasspoint2NAIRealmsEapAuthParametersValue
                 OCTET STRING
      }

clabWIFIAccessPointPasspoint2NAIRealmsEapMethodsAuthParmIndex OBJECT-TYPE
    SYNTAX      Unsigned32
    MAX-ACCESS  not-accessible
    STATUS      current
    DESCRIPTION
        "A unique index number for each set of authentication parameters
         associated with each EAP Method."
    ::= { clabWIFIAccessPointPasspoint2NAIRealmsEapMethodsAuthEntry 1 }

clabWIFIAccessPointPasspoint2NAIRealmsEapAuthParametersID OBJECT-TYPE
    SYNTAX      OCTET STRING
    MAX-ACCESS  read-only
    STATUS      current
    DESCRIPTION
        "EAP Method Authentication Parameters."
    ::= { clabWIFIAccessPointPasspoint2NAIRealmsEapMethodsAuthEntry 2 }

clabWIFIAccessPointPasspoint2NAIRealmsEapAuthParametersValue OBJECT-TYPE
    SYNTAX      OCTET STRING
    MAX-ACCESS  read-only
    STATUS      current
    DESCRIPTION
        "EAP Method Authentication Parameters."
    ::= { clabWIFIAccessPointPasspoint2NAIRealmsEapMethodsAuthEntry 3 }

clabWIFIAccessPointPasspoint2OSUTable OBJECT-TYPE
    SYNTAX      SEQUENCE OF ClabWIFIAccessPointPasspoint2OSUEntry
    MAX-ACCESS  not-accessible
    STATUS      current
    DESCRIPTION
        "This table contains information regarding the Online Sign Up (OSU) 
         Service that is advertised via OSU Provider List element in beacon
         and probe frames. Refer section 4.8 of WFA HS2.0.  This object is
         defined in TR-181 Device.WiFi.AP.{i}.X_CableLabs_Passpoint_OS and 
         its children."
    ::= { clabWIFIAccessPointPasspoint 14 }
	
clabWIFIAccessPointPasspoint2OSUEntry    OBJECT-TYPE
    SYNTAX      ClabWIFIAccessPointPasspoint2OSUEntry
    MAX-ACCESS  not-accessible
    STATUS      current
    DESCRIPTION
        "The conceptual row of clabWIFIAccessPointPasspoint2OSUTable."
    INDEX {
            clabWIFIAccessPointId,
            clabWIFIAccessPointPasspoint2OSUProviderIndex
           }
    ::= { clabWIFIAccessPointPasspoint2OSUTable 1 }
	
ClabWIFIAccessPointPasspoint2OSUEntry ::= SEQUENCE {
        clabWIFIAccessPointPasspoint2OSUProviderIndex
                 Unsigned32,
        clabWIFIAccessPointPasspoint2OSUProviderServerURI
                 SnmpAdminString,
        clabWIFIAccessPointPasspoint2OSUProviderNAI
                 SnmpAdminString,
        clabWIFIAccessPointPasspoint2OSUProviderMethodsList
                 OCTET STRING
    }

clabWIFIAccessPointPasspoint2OSUProviderIndex OBJECT-TYPE
    SYNTAX      Unsigned32
    MAX-ACCESS  not-accessible
    STATUS      current
    DESCRIPTION
        "A unique index number for each OSU Provider."
    ::= { clabWIFIAccessPointPasspoint2OSUEntry 1 }

clabWIFIAccessPointPasspoint2OSUProviderServerURI OBJECT-TYPE
    SYNTAX      SnmpAdminString (SIZE(0..255))
    MAX-ACCESS  read-only
    STATUS      current
    DESCRIPTION
        " The URI of the OSU Server that is used for OSU with the 
          Service Provider indicated in the Names table. It is 
          formatted in accordance with the IETF RFC 3986."
    ::= { clabWIFIAccessPointPasspoint2OSUEntry 2 }   

clabWIFIAccessPointPasspoint2OSUProviderNAI OBJECT-TYPE
    SYNTAX      SnmpAdminString (SIZE(1..253))
    MAX-ACCESS  read-only
    STATUS      current
    DESCRIPTION
        " Contains the NAI that is used for OSU with the Service
          Provider Name. OSUNAI is formatted in accordance with 
          IETF RFC 4282."
    ::= { clabWIFIAccessPointPasspoint2OSUEntry 3 }   

clabWIFIAccessPointPasspoint2OSUProviderMethodsList OBJECT-TYPE
    SYNTAX      OCTET STRING (SIZE(0..255))
    MAX-ACCESS  read-write
    STATUS      current
    DESCRIPTION
        " A comma separated list of OSU Method values represented as integers. 
          The methods are listed in the ServiceProvider's preferred order 
          with the most-preferred method first. Possible values (integers)
          are selected from Table 10 of WFA HS2.0.

            0 - OMA-DM
            1 - SOAP-XML SPP

          All other values (2 - 255) are reserved. Example value '0,1' without quotes."
    ::= { clabWIFIAccessPointPasspoint2OSUEntry 4 }

clabWIFIAccessPointPasspoint2OSUProviderNamesTable OBJECT-TYPE
    SYNTAX      SEQUENCE OF ClabWIFIAccessPointPasspoint2OSUProviderNamesEntry
    MAX-ACCESS  not-accessible
    STATUS      current
    DESCRIPTION
        "This table is used to get the provider names for each OSU provider."
    REFERENCE
    		"clabWIFIAccessPointPasspoint"
    ::= {clabWIFIAccessPointPasspoint 15 }

clabWIFIAccessPointPasspoint2OSUProviderNamesEntry    OBJECT-TYPE
    SYNTAX      ClabWIFIAccessPointPasspoint2OSUProviderNamesEntry
    MAX-ACCESS  not-accessible
    STATUS      current
    DESCRIPTION
        "The conceptual row of clabWIFIAccessPointPasspoint2OSUProviderNames Table."
    INDEX {
            clabWIFIAccessPointId,
			clabWIFIAccessPointPasspoint2OSUProviderIndex, 
            clabWIFIAccessPointPasspoint2OSUProviderNamesIndex
          }
    ::= {clabWIFIAccessPointPasspoint2OSUProviderNamesTable 1 }

ClabWIFIAccessPointPasspoint2OSUProviderNamesEntry ::= SEQUENCE {
        clabWIFIAccessPointPasspoint2OSUProviderNamesIndex
                 Unsigned32,
        clabWIFIAccessPointPasspoint2OSUProviderNamesLanguageCode 
                 Unsigned32,
        clabWIFIAccessPointPasspoint2OSUProviderNamesFriendlyName
                 SnmpAdminString
      }

clabWIFIAccessPointPasspoint2OSUProviderNamesIndex OBJECT-TYPE
    SYNTAX      Unsigned32
    MAX-ACCESS  not-accessible
    STATUS      current
    DESCRIPTION
        "A unique index number for OSU provider friendly name."
    ::= { clabWIFIAccessPointPasspoint2OSUProviderNamesEntry 1 }

clabWIFIAccessPointPasspoint2OSUProviderNamesLanguageCode OBJECT-TYPE
    SYNTAX      Unsigned32 (2 | 3)
    MAX-ACCESS  read-only
    STATUS      current
    DESCRIPTION
        "A 2 or 3 octet ISO-14962-1997 encoded string field that 
         defines the language used in the OSU Provider Friendly 
         Name field. The code value is selected from ISO-639."
    ::= { clabWIFIAccessPointPasspoint2OSUProviderNamesEntry 2 } 

clabWIFIAccessPointPasspoint2OSUProviderNamesFriendlyName OBJECT-TYPE
    SYNTAX      SnmpAdminString (SIZE(1..504))
    MAX-ACCESS  read-only
    STATUS      current
    DESCRIPTION
        "Indicates the UTF-8 encoded (represented as hexBinary) OSU 
         Provider Friendly Name in the human language identified by 
         the language code. This parameter accepts UTF-8 encoded 
         string represented as hexBinary string."
    ::= { clabWIFIAccessPointPasspoint2OSUProviderNamesEntry 3 }

clabWIFIAccessPointPasspoint2OSUProviderIconsTable OBJECT-TYPE
    SYNTAX      SEQUENCE OF ClabWIFIAccessPointPasspoint2OSUProviderIconsEntry
    MAX-ACCESS  not-accessible
    STATUS      current
    DESCRIPTION
        "This table is used to get the icon information for each OSU provider."
    REFERENCE
    		"clabWIFIAccessPointPasspoint"
    ::= {clabWIFIAccessPointPasspoint 16 }

clabWIFIAccessPointPasspoint2OSUProviderIconsEntry    OBJECT-TYPE
    SYNTAX      ClabWIFIAccessPointPasspoint2OSUProviderIconsEntry
    MAX-ACCESS  not-accessible
    STATUS      current
    DESCRIPTION
        "The conceptual row of clabWIFIAccessPointPasspoint2OSUProviderIcons Table."
    INDEX {
            clabWIFIAccessPointId,
			clabWIFIAccessPointPasspoint2OSUProviderIndex,
			clabWIFIAccessPointPasspoint2OSUProviderIconsIndex
          }
    ::= {clabWIFIAccessPointPasspoint2OSUProviderIconsTable 1 }

ClabWIFIAccessPointPasspoint2OSUProviderIconsEntry ::= SEQUENCE {
        clabWIFIAccessPointPasspoint2OSUProviderIconsIndex
                 Unsigned32,
        clabWIFIAccessPointPasspoint2OSUProviderIconFileName
                 SnmpAdminString,
        clabWIFIAccessPointPasspoint2OSUProviderIconType
                 OCTET STRING,
        clabWIFIAccessPointPasspoint2OSUProviderIconWidth
                 Unsigned32,
        clabWIFIAccessPointPasspoint2OSUProviderIconHeight
                 Unsigned32,
        clabWIFIAccessPointPasspoint2OSUProviderIconLanguageCode
                 Unsigned32
      }

clabWIFIAccessPointPasspoint2OSUProviderIconsIndex OBJECT-TYPE
    SYNTAX      Unsigned32
    MAX-ACCESS  not-accessible
    STATUS      current
    DESCRIPTION
        "A unique index number for each icon associated with an OSU provider."
    ::= { clabWIFIAccessPointPasspoint2OSUProviderIconsEntry 1 }

clabWIFIAccessPointPasspoint2OSUProviderIconFileName OBJECT-TYPE
    SYNTAX      SnmpAdminString (SIZE(1..255))
    MAX-ACCESS  read-only
    STATUS      current
    DESCRIPTION
        "The IconFilename is a UTF-8 encoded field whose value 
         contains the filename of the Icon having the metadata 
         provided in this icon instance."
    ::= { clabWIFIAccessPointPasspoint2OSUProviderIconsEntry 2 }

clabWIFIAccessPointPasspoint2OSUProviderIconType OBJECT-TYPE
    SYNTAX      OCTET STRING (SIZE(0..255))
    MAX-ACCESS  read-only
    STATUS      current
    DESCRIPTION
        " The IconType is the MIME media type of the binary icon 
          file named by the IconFilename. The IconType field is 
          formatted in accordance with RFC 6838 and its value is 
          selected from the IANA MIME Media Types registered at
          http://www.iana.org/assignments/media-types/index.html."
    ::= { clabWIFIAccessPointPasspoint2OSUProviderIconsEntry 3 }

clabWIFIAccessPointPasspoint2OSUProviderIconWidth  OBJECT-TYPE
    SYNTAX      Unsigned32 (1..65535)
    MAX-ACCESS  read-only
    STATUS      current
    DESCRIPTION
        " Width in pixel of the OSU Provider icon named by the 
          IconFilename."
    ::= { clabWIFIAccessPointPasspoint2OSUProviderIconsEntry 4 }

clabWIFIAccessPointPasspoint2OSUProviderIconHeight OBJECT-TYPE
    SYNTAX      Unsigned32 (1..65535)
    MAX-ACCESS  read-only
    STATUS      current
    DESCRIPTION
        " Height in pixel of the OSU Provider icon named by the 
          IconFilename."
    ::= { clabWIFIAccessPointPasspoint2OSUProviderIconsEntry 5 }

clabWIFIAccessPointPasspoint2OSUProviderIconLanguageCode OBJECT-TYPE
    SYNTAX      Unsigned32 (2 | 3)
    MAX-ACCESS  read-only
    STATUS      current
    DESCRIPTION
        " A 2 or 3 octet ISO-14962-1997 encoded string field that 
          defines the language used in the Icon file if any. The 
          code value is selected from ISO-639. If there is no 
          linguistic content to the icon/logo, the LanguageCode is 
          set to 'zxx'."
    ::= { clabWIFIAccessPointPasspoint2OSUProviderIconsEntry 6 }

clabWIFIAccessPointPasspoint2OSUProviderServiceDescTable OBJECT-TYPE
    SYNTAX      SEQUENCE OF ClabWIFIAccessPointPasspoint2OSUProviderServiceDescEntry
    MAX-ACCESS  not-accessible
    STATUS      current
    DESCRIPTION
        "This table is used to get the service descriptions for each OSU provider."
    REFERENCE
    		"clabWIFIAccessPointPasspoint"
    ::= {clabWIFIAccessPointPasspoint 17 }

clabWIFIAccessPointPasspoint2OSUProviderServiceDescEntry    OBJECT-TYPE
    SYNTAX      ClabWIFIAccessPointPasspoint2OSUProviderServiceDescEntry
    MAX-ACCESS  not-accessible
    STATUS      current
    DESCRIPTION
        "The conceptual row of clabWIFIAccessPointPasspoint2OSUProviderServiceDesc Table."
    INDEX {
            clabWIFIAccessPointId,
			clabWIFIAccessPointPasspoint2OSUProviderIndex,
			clabWIFIAccessPointPasspoint2OSUProviderServiceDescIndex
          }
    ::= {clabWIFIAccessPointPasspoint2OSUProviderServiceDescTable 1 }

ClabWIFIAccessPointPasspoint2OSUProviderServiceDescEntry ::= SEQUENCE {
    clabWIFIAccessPointPasspoint2OSUProviderServiceDescIndex
                 Unsigned32,
        clabWIFIAccessPointPasspoint2OSUProviderServiceDescLanguageCode
                 Unsigned32,
        clabWIFIAccessPointPasspoint2OSUProviderServiceDescription
                 SnmpAdminString
      }

clabWIFIAccessPointPasspoint2OSUProviderServiceDescIndex OBJECT-TYPE
    SYNTAX      Unsigned32
    MAX-ACCESS  not-accessible
    STATUS      current
    DESCRIPTION
        "A unique index number for each icon associated with an Service
         Description."
::= { clabWIFIAccessPointPasspoint2OSUProviderServiceDescEntry 1 }

clabWIFIAccessPointPasspoint2OSUProviderServiceDescLanguageCode OBJECT-TYPE
    SYNTAX      Unsigned32 (2 | 3)
    MAX-ACCESS  read-only
    STATUS      current
    DESCRIPTION
        " A 2 or 3 octet ISO-14962-1997 encoded string field that 
          defines the language used in the OSU Provider Friendly 
          Name field. The code value is selected from ISO-639."
    ::= { clabWIFIAccessPointPasspoint2OSUProviderServiceDescEntry 2 }

clabWIFIAccessPointPasspoint2OSUProviderServiceDescription OBJECT-TYPE
    SYNTAX      SnmpAdminString (SIZE(504))
    MAX-ACCESS  read-only
    STATUS      current
    DESCRIPTION
        " Indicates the UTF-8 encoded (represented as hexBinary) 
          string containing the ServiceProviders description of the
          service offering."
    ::= { clabWIFIAccessPointPasspoint2OSUProviderServiceDescEntry 3 }

clabWIFIAccessPointPasspointWANMetrics OBJECT IDENTIFIER
    ::= { clabWIFIObjects 20 }

clabWIFIAccessPointPasspointWANMetricsLinkStatus OBJECT-TYPE
    SYNTAX INTEGER {
                    reserved(1),
                    linkUp(2),
                    linkDown(3),
                    linkTest(4)
                   }
    MAX-ACCESS read-only
    STATUS current
    DESCRIPTION
        "Status of WAN link."
    ::= { clabWIFIAccessPointPasspointWANMetrics 1 }

clabWIFIAccessPointPasspointWANMetricsAtCapacity OBJECT-TYPE
    SYNTAX TruthValue
    MAX-ACCESS read-only
    STATUS current
    DESCRIPTION
        "Set to true if the WAN link is at capacity and no additional
         mobile devices will be permitted to associate to the AP.
         Otherwise false."
    ::= { clabWIFIAccessPointPasspointWANMetrics 2 }

clabWIFIAccessPointPasspointWANMetricsDownlinkSpeed OBJECT-TYPE
    SYNTAX Unsigned32
    MAX-ACCESS read-only
    STATUS current
    DESCRIPTION
        "An estimate of the WAN backhaul link's current downlink speed
         in kilobits per second (kbps). The maximum value of this field
         is 4,294,967,296 kbps (approx. 4.2Tbps)."
    ::= { clabWIFIAccessPointPasspointWANMetrics 3 }

clabWIFIAccessPointPasspointWANMetricsUplinkSpeed OBJECT-TYPE
    SYNTAX Unsigned32
    MAX-ACCESS read-only
    STATUS current
    DESCRIPTION
        "An estimate of the WAN backhaul link's current uplink speed in
         kilobits per second (kbps). The maximum value of this field is
         4,294,967,296 kbps (approx. 4.2Tbps)."
    ::= { clabWIFIAccessPointPasspointWANMetrics 4 }

clabWIFIAccessPointPasspointWANMetricsDownlinkLoad OBJECT-TYPE
    SYNTAX Unsigned32(0..100)
    UNITS       "percentage"
    MAX-ACCESS read-only
    STATUS current
    DESCRIPTION
        "Current percentage loading of the downlink WAN connection."
    ::= { clabWIFIAccessPointPasspointWANMetrics 5 }

clabWIFIAccessPointPasspointWANMetricsUplinkLoad OBJECT-TYPE
    SYNTAX Unsigned32(0..100)
    UNITS       "percentage"
    MAX-ACCESS read-only
    STATUS current
    DESCRIPTION
        "Current percentage loading of the uplink WAN connection."
    ::= { clabWIFIAccessPointPasspointWANMetrics 6 }

clabWIFIAccessPointAccountingTable OBJECT-TYPE
    SYNTAX      SEQUENCE OF ClabWIFIAccessPointAccountingEntry
    MAX-ACCESS  not-accessible
    STATUS      current
    DESCRIPTION
        "This object is defined in TR-181 Device.WiFi.AccessPoint{i}.Accounting."
    REFERENCE
        "TR-181 Device Data Model for TR-069."
    ::= { clabWIFIObjects 23 }

clabWIFIAccessPointAccountingEntry    OBJECT-TYPE
    SYNTAX      ClabWIFIAccessPointAccountingEntry
    MAX-ACCESS  not-accessible
    STATUS      current
    DESCRIPTION
        "The conceptual row of clabWIFIAccessPointAccounting Table."
    INDEX {
            clabWIFIAccessPointId
                      }
    ::= { clabWIFIAccessPointAccountingTable 1 }
	
ClabWIFIAccessPointAccountingEntry ::= SEQUENCE {
        clabWIFIAccessPointAccountingEnable
                 TruthValue, 
        clabWIFIAccessPointAccountingServerIPAddrType
                 InetAddressType,
        clabWIFIAccessPointAccountingServerIPAddr
                 InetAddress,
        clabWIFIAccessPointAccountingSecondaryServerIPAddrType
                 InetAddressType,                 
        clabWIFIAccessPointAccountingSecondaryServerIPAddr
                 InetAddress,                 
        clabWIFIAccessPointAccountingServerPort
                 InetPortNumber,
        clabWIFIAccessPointAccountingSecondaryServerPort
                 InetPortNumber,
        clabWIFIAccessPointAccountingSecret
                 SnmpAdminString,
        clabWIFIAccessPointAccountingSecondarySecret
                 SnmpAdminString,
        clabWIFIAccessPointAccountingInterimInterval
                 Unsigned32,
        clabWIFIAccessPointAccountingRowStatus
                 RowStatus        
    }

clabWIFIAccessPointAccountingEnable     OBJECT-TYPE
    SYNTAX TruthValue
    MAX-ACCESS read-write
    STATUS current
    DESCRIPTION
       "This object is defined in TR-181 Device.WiFi.AccessPoint{i}.Accounting.Enable."
    REFERENCE
        "TR-181 Device Data Model for TR-069."
    ::= { clabWIFIAccessPointAccountingEntry 1 }

clabWIFIAccessPointAccountingServerIPAddrType    OBJECT-TYPE
    SYNTAX      InetAddressType 
    MAX-ACCESS  read-create
    STATUS      current
    DESCRIPTION
        "This object is type of the address in TR-181 Device.WiFi.AccessPoint{i}.Accounting.ServerIPAddr."
    REFERENCE
        "TR-181 Device Data Model for TR-069."
    ::= {clabWIFIAccessPointAccountingEntry 2 }

clabWIFIAccessPointAccountingServerIPAddr    OBJECT-TYPE
    SYNTAX      InetAddress 
    MAX-ACCESS  read-create
    STATUS      current
    DESCRIPTION
        "This object is defined in TR-181 Device.WiFi.AccessPoint{i}.Accounting.ServerIPAddr."
    REFERENCE
        "TR-181 Device Data Model for TR-069."
    ::= {clabWIFIAccessPointAccountingEntry 3 }

clabWIFIAccessPointAccountingSecondaryServerIPAddrType    OBJECT-TYPE
    SYNTAX      InetAddressType 
    MAX-ACCESS  read-create
    STATUS      current
    DESCRIPTION
        "This object is type of the address in TR-181 Device.WiFi.AccessPoint{i}.Accounting.SecondaryServerIPAddr."
    REFERENCE
        "TR-181 Device Data Model for TR-069."
    ::= {clabWIFIAccessPointAccountingEntry 4 }

clabWIFIAccessPointAccountingSecondaryServerIPAddr    OBJECT-TYPE
    SYNTAX      InetAddress 
    MAX-ACCESS  read-create
    STATUS      current
    DESCRIPTION
        "This object is defined in TR-181 Device.WiFi.AccessPoint{i}.Accounting.SecondaryServerIPAddr."
    REFERENCE
        "TR-181 Device Data Model for TR-069."
    ::= {clabWIFIAccessPointAccountingEntry 5 }

clabWIFIAccessPointAccountingServerPort    OBJECT-TYPE
    SYNTAX      InetPortNumber 
    MAX-ACCESS  read-create
    STATUS      current
    DESCRIPTION
        "This object is defined in TR-181 Device.WiFi.AccessPoint{i}.Accounting.ServerPort."
    REFERENCE
        "TR-181 Device Data Model for TR-069."
    DEFVAL { 1813 }
    ::= {clabWIFIAccessPointAccountingEntry 6 }

clabWIFIAccessPointAccountingSecondaryServerPort    OBJECT-TYPE
    SYNTAX      InetPortNumber 
    MAX-ACCESS  read-create
    STATUS      current
    DESCRIPTION
        "This object is defined in TR-181 Device.WiFi.AccessPoint{i}.Accounting.SecondaryServerPort."
    REFERENCE
        "TR-181 Device Data Model for TR-069."
    DEFVAL { 1813 }
    ::= {clabWIFIAccessPointAccountingEntry 7 }

clabWIFIAccessPointAccountingSecret    OBJECT-TYPE
    SYNTAX      SnmpAdminString 
    MAX-ACCESS  read-create
    STATUS      current
    DESCRIPTION
        "This object is defined in TR-181 Device.WiFi.AccessPoint{i}.Accounting.Secret."
    REFERENCE
        "TR-181 Device Data Model for TR-069."
    ::= {clabWIFIAccessPointAccountingEntry 8 }

clabWIFIAccessPointAccountingSecondarySecret    OBJECT-TYPE
    SYNTAX      SnmpAdminString 
    MAX-ACCESS  read-create
    STATUS      current
    DESCRIPTION
        "This object is defined in TR-181 Device.WiFi.AccessPoint{i}.Accounting.SecondarySecret."
    REFERENCE
        "TR-181 Device Data Model for TR-069."
    ::= {clabWIFIAccessPointAccountingEntry 9 }

clabWIFIAccessPointAccountingInterimInterval    OBJECT-TYPE
    SYNTAX      Unsigned32 
    UNITS       "seconds"
    MAX-ACCESS  read-write
    STATUS      current
    DESCRIPTION
        "This object is defined in TR-181 Device.WiFi.AccessPoint{i}.Accounting.InterimInterval."
    REFERENCE
        "TR-181 Device Data Model for TR-069."
    ::= {clabWIFIAccessPointAccountingEntry 10 }

clabWIFIAccessPointAccountingRowStatus    OBJECT-TYPE
    SYNTAX      RowStatus 
    MAX-ACCESS  read-create
    STATUS      current
    DESCRIPTION
        "The status of this instance."
    ::= {clabWIFIAccessPointAccountingEntry 11 }  

clabWIFIAccessPointACTable OBJECT-TYPE
    SYNTAX      SEQUENCE OF ClabWIFIAccessPointACEntry
    MAX-ACCESS  not-accessible
    STATUS      deprecated
    DESCRIPTION
        "This object is defined in TR-181 Device.WiFi.AccessPoint{i}.AC."
    REFERENCE
        "TR-181 Device Data Model for TR-069."
    ::= { clabWIFIObjects 24 }

clabWIFIAccessPointACEntry    OBJECT-TYPE
    SYNTAX      ClabWIFIAccessPointACEntry
    MAX-ACCESS  not-accessible
    STATUS      deprecated
    DESCRIPTION
        "The conceptual row of clabWIFIAccessPointAC Table."
    INDEX {
            clabWIFIAccessPointId
                      }
    ::= { clabWIFIAccessPointACTable 1 }
	
ClabWIFIAccessPointACEntry ::= SEQUENCE {
        clabWIFIAccessPointACAccessCategory
                 INTEGER,
        clabWIFIAccessPointACAlias
                 OCTET STRING,
        clabWIFIAccessPointACAIFSN
                 Unsigned32,                
        clabWIFIAccessPointACECWMin
                 Unsigned32,
        clabWIFIAccessPointACECWMax
                 Unsigned32,
        clabWIFIAccessPointACTxOpMax
                 Unsigned32,
        clabWIFIAccessPointACAckPolicy
                 TruthValue,
        clabWIFIAccessPointACOutQLenHistogramIntervals
                 OCTET STRING,
        clabWIFIAccessPointACOutQLenHistogramSampleInterval
                 Unsigned32
    }

clabWIFIAccessPointACAccessCategory     OBJECT-TYPE
    SYNTAX      INTEGER  {
                           be(1),
                           bk(2),
                           vi(3),
                           vo(4)
                         }
    MAX-ACCESS read-only
    STATUS deprecated
    DESCRIPTION
       "This object is defined in TR-181 Device.WiFi.AccessPoint{i}.AC.AccessCategory."
    REFERENCE
        "TR-181 Device Data Model for TR-069."
    ::= { clabWIFIAccessPointACEntry 1 }

clabWIFIAccessPointACAlias    OBJECT-TYPE
    SYNTAX      OCTET STRING (SIZE(0..64))
    MAX-ACCESS  read-write
    STATUS      deprecated
    DESCRIPTION
       "This object is defined in TR-181 Device.WiFi.AccessPoint{i}.AC.Alias."
    REFERENCE
        "TR-181 Device Data Model for TR-069."
    ::= {clabWIFIAccessPointACEntry 2 }

clabWIFIAccessPointACAIFSN    OBJECT-TYPE
    SYNTAX      Unsigned32 
    MAX-ACCESS  read-write
    STATUS      deprecated
    DESCRIPTION
        "This object is defined in TR-181 Device.WiFi.AccessPoint{i}.AC.AIFSN."
    REFERENCE
        "TR-181 Device Data Model for TR-069."
    ::= {clabWIFIAccessPointACEntry 3 }

clabWIFIAccessPointACECWMin    OBJECT-TYPE
    SYNTAX      Unsigned32 
    MAX-ACCESS  read-write
    STATUS      deprecated
    DESCRIPTION
        "This object is defined in TR-181 Device.WiFi.AccessPoint{i}.AC.ECWMin."
    REFERENCE
        "TR-181 Device Data Model for TR-069."
    ::= {clabWIFIAccessPointACEntry 4 }

clabWIFIAccessPointACECWMax    OBJECT-TYPE
    SYNTAX      Unsigned32 
    MAX-ACCESS  read-write
    STATUS      deprecated
    DESCRIPTION
        "This object is defined in TR-181 Device.WiFi.AccessPoint{i}.AC.ECWMax."
    REFERENCE
        "TR-181 Device Data Model for TR-069."
    ::= {clabWIFIAccessPointACEntry 5 }

clabWIFIAccessPointACTxOpMax    OBJECT-TYPE
    SYNTAX      Unsigned32 
    MAX-ACCESS  read-write
    STATUS      deprecated
    DESCRIPTION
        "This object is defined in TR-181 Device.WiFi.AccessPoint{i}.AC.TxOpMax."
    REFERENCE
        "TR-181 Device Data Model for TR-069."
    ::= {clabWIFIAccessPointACEntry 6 }

clabWIFIAccessPointACAckPolicy    OBJECT-TYPE
    SYNTAX      TruthValue 
    MAX-ACCESS  read-write
    STATUS      deprecated
    DESCRIPTION
        "This object is defined in TR-181 Device.WiFi.AccessPoint{i}.AC.AckPolicy."
    REFERENCE
        "TR-181 Device Data Model for TR-069."
    ::= {clabWIFIAccessPointACEntry 7 }

clabWIFIAccessPointACOutQLenHistogramIntervals    OBJECT-TYPE
    SYNTAX      OCTET STRING
    MAX-ACCESS  read-write
    STATUS      deprecated
    DESCRIPTION
        "This object is defined in TR-181 Device.WiFi.AccessPoint{i}.AC.OutQlenHistogramIntervals."
    REFERENCE
        "TR-181 Device Data Model for TR-069."
    ::= {clabWIFIAccessPointACEntry 8 }

clabWIFIAccessPointACOutQLenHistogramSampleInterval    OBJECT-TYPE
    SYNTAX      Unsigned32
    MAX-ACCESS  read-write
    STATUS      deprecated
    DESCRIPTION
        "This object is defined in TR-181 Device.WiFi.AccessPoint{i}.AC.OutQlenHistograSampleInterval."
    REFERENCE
        "TR-181 Device Data Model for TR-069."
    ::= {clabWIFIAccessPointACEntry 9 }

clabWIFIAccessPointACStatsTable OBJECT-TYPE
    SYNTAX      SEQUENCE OF ClabWIFIAccessPointACStatsEntry
    MAX-ACCESS  not-accessible
    STATUS      deprecated
    DESCRIPTION
        "This object is defined in TR-181 Device.WiFi.AccessPoint{i}.AC.Stats."
    REFERENCE
        "TR-181 Device Data Model for TR-069."
    ::= { clabWIFIObjects 25 }

clabWIFIAccessPointACStatsEntry    OBJECT-TYPE
    SYNTAX      ClabWIFIAccessPointACStatsEntry
    MAX-ACCESS  not-accessible
    STATUS      deprecated
    DESCRIPTION
        "The conceptual row of clabWIFIAccessPointACStats Table."
    INDEX {
            clabWIFIAccessPointId
          }
    ::= { clabWIFIAccessPointACStatsTable 1 }
	
ClabWIFIAccessPointACStatsEntry ::= SEQUENCE {
        clabWIFIAccessPointACStatsBytesSent
                 Counter64,
        clabWIFIAccessPointACStatsBytesReceived
                 Counter64,
        clabWIFIAccessPointACStatsPacketsSent
                 Counter64,               
        clabWIFIAccessPointACStatsPacketsReceived
                 Counter64,
        clabWIFIAccessPointACStatsErrorsSent
                 Unsigned32,
        clabWIFIAccessPointACStatsErrorsReceived
                 Unsigned32,
        clabWIFIAccessPointACStatsDiscardPacketsSent
                 Unsigned32,
        clabWIFIAccessPointACStatsDiscardPacketsReceived
                 Unsigned32,
        clabWIFIAccessPointACStatsRetransCount
                 Unsigned32,
        clabWIFIAccessPointACStatsOutQLenHistogram
                 OCTET STRING
    }

clabWIFIAccessPointACStatsBytesSent     OBJECT-TYPE
    SYNTAX      Counter64   
    MAX-ACCESS  read-only
    STATUS      deprecated
    DESCRIPTION
       "This object is defined in TR-181 Device.WiFi.AccessPoint{i}.AC.Stats.BytesSent."
    REFERENCE
        "TR-181 Device Data Model for TR-069."
    ::= { clabWIFIAccessPointACStatsEntry 1 }

clabWIFIAccessPointACStatsBytesReceived    OBJECT-TYPE
    SYNTAX      Counter64
    MAX-ACCESS  read-only
    STATUS      deprecated
    DESCRIPTION
       "This object is defined in TR-181 Device.WiFi.AccessPoint{i}.AC.Stats.BytesReceived."
    REFERENCE
        "TR-181 Device Data Model for TR-069."
    ::= {clabWIFIAccessPointACStatsEntry 2 }

clabWIFIAccessPointACStatsPacketsSent   OBJECT-TYPE
    SYNTAX      Counter64
    MAX-ACCESS  read-only
    STATUS      deprecated
    DESCRIPTION
        "This object is defined in TR-181 Device.WiFi.AccessPoint{i}.AC.Stats.PacketsSent."
    REFERENCE
        "TR-181 Device Data Model for TR-069."
    ::= {clabWIFIAccessPointACStatsEntry 3 }

clabWIFIAccessPointACStatsPacketsReceived   OBJECT-TYPE
    SYNTAX      Counter64
    MAX-ACCESS  read-only
    STATUS      deprecated
    DESCRIPTION
        "This object is defined in TR-181 Device.WiFi.AccessPoint{i}.AC.Stats.PacketsReceived."
    REFERENCE
        "TR-181 Device Data Model for TR-069."
    ::= {clabWIFIAccessPointACStatsEntry 4 }

clabWIFIAccessPointACStatsErrorsSent   OBJECT-TYPE
    SYNTAX      Unsigned32
    MAX-ACCESS  read-only
    STATUS      deprecated
    DESCRIPTION
        "This object is defined in TR-181 Device.WiFi.AccessPoint{i}.AC.Stats.ErrorsSent."
    REFERENCE
        "TR-181 Device Data Model for TR-069."
    ::= {clabWIFIAccessPointACStatsEntry 5 }

clabWIFIAccessPointACStatsErrorsReceived   OBJECT-TYPE
    SYNTAX      Unsigned32
    MAX-ACCESS  read-only
    STATUS      deprecated
    DESCRIPTION
        "This object is defined in TR-181 Device.WiFi.AccessPoint{i}.AC.Stats.ErrorsReceieved."
    REFERENCE
        "TR-181 Device Data Model for TR-069."
    ::= {clabWIFIAccessPointACStatsEntry 6 }

clabWIFIAccessPointACStatsDiscardPacketsSent   OBJECT-TYPE
    SYNTAX      Unsigned32
    MAX-ACCESS  read-only
    STATUS      deprecated
    DESCRIPTION
        "This object is defined in TR-181 Device.WiFi.AccessPoint{i}.AC.Stats.DiscardPacketsSent."
    REFERENCE
        "TR-181 Device Data Model for TR-069."
    ::= {clabWIFIAccessPointACStatsEntry 7 }

clabWIFIAccessPointACStatsDiscardPacketsReceived   OBJECT-TYPE
    SYNTAX      Unsigned32
    MAX-ACCESS  read-only
    STATUS      deprecated
    DESCRIPTION
        "This object is defined in TR-181 Device.WiFi.AccessPoint{i}.AC.Stats.DiscardPacketsReceived."
    REFERENCE
        "TR-181 Device Data Model for TR-069."
    ::= {clabWIFIAccessPointACStatsEntry 8 }

clabWIFIAccessPointACStatsRetransCount   OBJECT-TYPE
    SYNTAX      Unsigned32
    MAX-ACCESS  read-only
    STATUS      deprecated
    DESCRIPTION
        "This object is defined in TR-181 Device.WiFi.AccessPoint{i}.AC.Stats.RetransCount."
    REFERENCE
        "TR-181 Device Data Model for TR-069."
    ::= {clabWIFIAccessPointACStatsEntry 9 }

clabWIFIAccessPointACStatsOutQLenHistogram   OBJECT-TYPE
    SYNTAX      OCTET STRING
    MAX-ACCESS  read-only
    STATUS      deprecated
    DESCRIPTION
        "This object is defined in TR-181 Device.WiFi.AccessPoint{i}.AC.Stats.OutQLenHistogram."
    REFERENCE
        "TR-181 Device Data Model for TR-069."
    ::= {clabWIFIAccessPointACStatsEntry 10 }

clabWIFIAccessPointAC2Table OBJECT-TYPE
    SYNTAX      SEQUENCE OF ClabWIFIAccessPointAC2Entry
    MAX-ACCESS  not-accessible
    STATUS      current
    DESCRIPTION
        "This object is defined in TR-181 Device.WiFi.AccessPoint{i}.AC."
    REFERENCE
        "TR-181 Device Data Model for TR-069."
    ::= { clabWIFIObjects 27 }

clabWIFIAccessPointAC2Entry    OBJECT-TYPE
    SYNTAX      ClabWIFIAccessPointAC2Entry
    MAX-ACCESS  not-accessible
    STATUS      current
    DESCRIPTION
        "The conceptual row of clabWIFIAccessPointAC2Table."
    INDEX {
            clabWIFIAccessPointId,
            clabWIFIAccessPointAC2Index
                      }
    ::= { clabWIFIAccessPointAC2Table 1 }
	
ClabWIFIAccessPointAC2Entry ::= SEQUENCE {
        clabWIFIAccessPointAC2Index
                 Unsigned32,
        clabWIFIAccessPointAC2AccessCategory
                 INTEGER,
        clabWIFIAccessPointAC2Alias
                 SnmpAdminString,
        clabWIFIAccessPointAC2AIFSN
                 Unsigned32,                
        clabWIFIAccessPointAC2ECWMin
                 Unsigned32,
        clabWIFIAccessPointAC2ECWMax
                 Unsigned32,
        clabWIFIAccessPointAC2TxOpMax
                 Unsigned32,
        clabWIFIAccessPointAC2AckPolicy
                 TruthValue,
        clabWIFIAccessPointAC2OutQLenHistogramIntervals
                 SnmpAdminString,
        clabWIFIAccessPointAC2OutQLenHistogramSampleInterval
                 Unsigned32
    }

clabWIFIAccessPointAC2Index    OBJECT-TYPE
    SYNTAX      Unsigned32 
    MAX-ACCESS  not-accessible
    STATUS      current
    DESCRIPTION
        "The key for a unique entry in clabWIFIAccessPointAC2Table. "
    ::= {clabWIFIAccessPointAC2Entry 1 }

clabWIFIAccessPointAC2AccessCategory     OBJECT-TYPE
    SYNTAX      INTEGER  {
                           be(1),
                           bk(2),
                           vi(3),
                           vo(4)
                         }
    MAX-ACCESS read-only
    STATUS current
    DESCRIPTION
       "This object is defined in TR-181 Device.WiFi.AccessPoint{i}.AC.AccessCategory."
    REFERENCE
        "TR-181 Device Data Model for TR-069."
    ::= { clabWIFIAccessPointAC2Entry 2 }

clabWIFIAccessPointAC2Alias    OBJECT-TYPE
    SYNTAX      SnmpAdminString (SIZE(0..64))
    MAX-ACCESS  read-write
    STATUS      current
    DESCRIPTION
       "This object is defined in TR-181 Device.WiFi.AccessPoint{i}.AC.Alias."
    REFERENCE
        "TR-181 Device Data Model for TR-069."
    ::= {clabWIFIAccessPointAC2Entry 3 }

clabWIFIAccessPointAC2AIFSN    OBJECT-TYPE
    SYNTAX      Unsigned32 (2..15)
    MAX-ACCESS  read-write
    STATUS      current
    DESCRIPTION
        "This object is defined in TR-181 Device.WiFi.AccessPoint{i}.AC.AIFSN."
    REFERENCE
        "TR-181 Device Data Model for TR-069."
    ::= {clabWIFIAccessPointAC2Entry 4 }

clabWIFIAccessPointAC2ECWMin    OBJECT-TYPE
    SYNTAX      Unsigned32 (0..15)
    MAX-ACCESS  read-write
    STATUS      current
    DESCRIPTION
        "This object is defined in TR-181 Device.WiFi.AccessPoint{i}.AC.ECWMin."
    REFERENCE
        "TR-181 Device Data Model for TR-069."
    ::= {clabWIFIAccessPointAC2Entry 5 }

clabWIFIAccessPointAC2ECWMax    OBJECT-TYPE
    SYNTAX      Unsigned32 (0..15)
    MAX-ACCESS  read-write
    STATUS      current
    DESCRIPTION
        "This object is defined in TR-181 Device.WiFi.AccessPoint{i}.AC.ECWMax."
    REFERENCE
        "TR-181 Device Data Model for TR-069."
    ::= {clabWIFIAccessPointAC2Entry 6 }

clabWIFIAccessPointAC2TxOpMax    OBJECT-TYPE
    SYNTAX      Unsigned32 (0..255)
    MAX-ACCESS  read-write
    STATUS      current
    DESCRIPTION
        "This object is defined in TR-181 Device.WiFi.AccessPoint{i}.AC.TxOpMax."
    REFERENCE
        "TR-181 Device Data Model for TR-069."
    ::= {clabWIFIAccessPointAC2Entry 7 }

clabWIFIAccessPointAC2AckPolicy    OBJECT-TYPE
    SYNTAX      TruthValue 
    MAX-ACCESS  read-write
    STATUS      current
    DESCRIPTION
        "This object is defined in TR-181 Device.WiFi.AccessPoint{i}.AC.AckPolicy."
    REFERENCE
        "TR-181 Device Data Model for TR-069."
    ::= {clabWIFIAccessPointAC2Entry 8 }

clabWIFIAccessPointAC2OutQLenHistogramIntervals    OBJECT-TYPE
    SYNTAX      SnmpAdminString
    MAX-ACCESS  read-write
    STATUS      current
    DESCRIPTION
        "This object is defined in TR-181 Device.WiFi.AccessPoint{i}.AC.OutQlenHistogramIntervals."
    REFERENCE
        "TR-181 Device Data Model for TR-069."
    ::= {clabWIFIAccessPointAC2Entry 9 }

clabWIFIAccessPointAC2OutQLenHistogramSampleInterval    OBJECT-TYPE
    SYNTAX      Unsigned32
    MAX-ACCESS  read-write
    STATUS      current
    DESCRIPTION
        "This object is defined in TR-181 Device.WiFi.AccessPoint{i}.AC.OutQlenHistograSampleInterval."
    REFERENCE
        "TR-181 Device Data Model for TR-069."
    ::= {clabWIFIAccessPointAC2Entry 10 }

clabWIFIAccessPointAC2StatsTable OBJECT-TYPE
    SYNTAX      SEQUENCE OF ClabWIFIAccessPointAC2StatsEntry
    MAX-ACCESS  not-accessible
    STATUS      current
    DESCRIPTION
        "This object is defined in TR-181 Device.WiFi.AccessPoint{i}.AC.Stats."
    REFERENCE
        "TR-181 Device Data Model for TR-069."
    ::= { clabWIFIObjects 28 }

clabWIFIAccessPointAC2StatsEntry    OBJECT-TYPE
    SYNTAX      ClabWIFIAccessPointAC2StatsEntry
    MAX-ACCESS  not-accessible
    STATUS      current
    DESCRIPTION
        "The conceptual row of clabWIFIAccessPointAC2Stats Table."
    INDEX {
            clabWIFIAccessPointId,
            clabWIFIAccessPointAC2StatsIndex
          }
    ::= { clabWIFIAccessPointAC2StatsTable 1 }
	
ClabWIFIAccessPointAC2StatsEntry ::= SEQUENCE {
        clabWIFIAccessPointAC2StatsIndex
                 Unsigned32,
        clabWIFIAccessPointAC2StatsBytesSent
                 Counter64,
        clabWIFIAccessPointAC2StatsBytesReceived
                 Counter64,
        clabWIFIAccessPointAC2StatsPacketsSent
                 Counter64,               
        clabWIFIAccessPointAC2StatsPacketsReceived
                 Counter64,
        clabWIFIAccessPointAC2StatsErrorsSent
                 Unsigned32,
        clabWIFIAccessPointAC2StatsErrorsReceived
                 Unsigned32,
        clabWIFIAccessPointAC2StatsDiscardPacketsSent
                 Unsigned32,
        clabWIFIAccessPointAC2StatsDiscardPacketsReceived
                 Unsigned32,
        clabWIFIAccessPointAC2StatsRetransCount
                 Unsigned32,
        clabWIFIAccessPointAC2StatsOutQLenHistogram
                 SnmpAdminString
    }

clabWIFIAccessPointAC2StatsIndex    OBJECT-TYPE
    SYNTAX      Unsigned32 
    MAX-ACCESS  not-accessible
    STATUS      current
    DESCRIPTION
        "The key for a unique entry in clabWIFIAccessPointAC2StatsTable. "
    ::= {clabWIFIAccessPointAC2StatsEntry 1 }

clabWIFIAccessPointAC2StatsBytesSent     OBJECT-TYPE
    SYNTAX      Counter64   
    MAX-ACCESS  read-only
    STATUS current
    DESCRIPTION
       "This object is defined in TR-181 Device.WiFi.AccessPoint{i}.AC.Stats.BytesSent."
    REFERENCE
        "TR-181 Device Data Model for TR-069."
    ::= { clabWIFIAccessPointAC2StatsEntry 2 }

clabWIFIAccessPointAC2StatsBytesReceived    OBJECT-TYPE
    SYNTAX      Counter64
    MAX-ACCESS  read-only
    STATUS      current
    DESCRIPTION
       "This object is defined in TR-181 Device.WiFi.AccessPoint{i}.AC.Stats.BytesReceived."
    REFERENCE
        "TR-181 Device Data Model for TR-069."
    ::= {clabWIFIAccessPointAC2StatsEntry 3 }

clabWIFIAccessPointAC2StatsPacketsSent   OBJECT-TYPE
    SYNTAX      Counter64
    MAX-ACCESS  read-only
    STATUS      current
    DESCRIPTION
        "This object is defined in TR-181 Device.WiFi.AccessPoint{i}.AC.Stats.PacketsSent."
    REFERENCE
        "TR-181 Device Data Model for TR-069."
    ::= {clabWIFIAccessPointAC2StatsEntry 4 }

clabWIFIAccessPointAC2StatsPacketsReceived   OBJECT-TYPE
    SYNTAX      Counter64
    MAX-ACCESS  read-only
    STATUS      current
    DESCRIPTION
        "This object is defined in TR-181 Device.WiFi.AccessPoint{i}.AC.Stats.PacketsReceived."
    REFERENCE
        "TR-181 Device Data Model for TR-069."
    ::= {clabWIFIAccessPointAC2StatsEntry 5 }

clabWIFIAccessPointAC2StatsErrorsSent   OBJECT-TYPE
    SYNTAX      Unsigned32
    MAX-ACCESS  read-only
    STATUS      current
    DESCRIPTION
        "This object is defined in TR-181 Device.WiFi.AccessPoint{i}.AC.Stats.ErrorsSent."
    REFERENCE
        "TR-181 Device Data Model for TR-069."
    ::= {clabWIFIAccessPointAC2StatsEntry 6 }

clabWIFIAccessPointAC2StatsErrorsReceived   OBJECT-TYPE
    SYNTAX      Unsigned32
    MAX-ACCESS  read-only
    STATUS      current
    DESCRIPTION
        "This object is defined in TR-181 Device.WiFi.AccessPoint{i}.AC.Stats.ErrorsReceieved."
    REFERENCE
        "TR-181 Device Data Model for TR-069."
    ::= {clabWIFIAccessPointAC2StatsEntry 7 }

clabWIFIAccessPointAC2StatsDiscardPacketsSent   OBJECT-TYPE
    SYNTAX      Unsigned32
    MAX-ACCESS  read-only
    STATUS      current
    DESCRIPTION
        "This object is defined in TR-181 Device.WiFi.AccessPoint{i}.AC.Stats.DiscardPacketsSent."
    REFERENCE
        "TR-181 Device Data Model for TR-069."
    ::= {clabWIFIAccessPointAC2StatsEntry 8 }

clabWIFIAccessPointAC2StatsDiscardPacketsReceived   OBJECT-TYPE
    SYNTAX      Unsigned32
    MAX-ACCESS  read-only
    STATUS      current
    DESCRIPTION
        "This object is defined in TR-181 Device.WiFi.AccessPoint{i}.AC.Stats.DiscardPacketsReceived."
    REFERENCE
        "TR-181 Device Data Model for TR-069."
    ::= {clabWIFIAccessPointAC2StatsEntry 9 }

clabWIFIAccessPointAC2StatsRetransCount   OBJECT-TYPE
    SYNTAX      Unsigned32
    MAX-ACCESS  read-only
    STATUS      current
    DESCRIPTION
        "This object is defined in TR-181 Device.WiFi.AccessPoint{i}.AC.Stats.RetransCount."
    REFERENCE
        "TR-181 Device Data Model for TR-069."
    ::= {clabWIFIAccessPointAC2StatsEntry 10 }

clabWIFIAccessPointAC2StatsOutQLenHistogram   OBJECT-TYPE
    SYNTAX      SnmpAdminString
    MAX-ACCESS  read-only
    STATUS      current
    DESCRIPTION
        "This object is defined in TR-181 Device.WiFi.AccessPoint{i}.AC.Stats.OutQLenHistogram."
    REFERENCE
        "TR-181 Device Data Model for TR-069."
    ::= {clabWIFIAccessPointAC2StatsEntry 11 }

clabWIFIAccessPointRadiusSettingsObjects OBJECT IDENTIFIER 
    ::= { clabWIFIObjects 26 }

clabWIFIAccessPointRadiusSettingsRadiusServerRetries    OBJECT-TYPE
    SYNTAX      Unsigned32
    MAX-ACCESS  read-write
    STATUS      current
    DESCRIPTION
        "Number of retries for Radius requests."
    ::= { clabWIFIAccessPointRadiusSettingsObjects 1 }

clabWIFIAccessPointRadiusSettingsRadiusServerRequestTimeout    OBJECT-TYPE
    SYNTAX      Unsigned32 
    UNITS       "seconds"
    MAX-ACCESS  read-write
    STATUS      current
    DESCRIPTION
        "Radius request timeout in seconds after which the request must be
         retransmitted for the number of retries available."
    ::= { clabWIFIAccessPointRadiusSettingsObjects 2 }

clabWIFIAccessPointRadiusSettingsPMKLifetime    OBJECT-TYPE
    SYNTAX      Unsigned32 
    UNITS       "seconds"
    MAX-ACCESS  read-write
    STATUS      current
    DESCRIPTION
        "Default time after which a Wi-Fi client is forced to re-authenticate."
    ::= { clabWIFIAccessPointRadiusSettingsObjects 3 }

clabWIFIAccessPointRadiusSettingsPMKCachingEnable   OBJECT-TYPE
    SYNTAX      TruthValue 
    MAX-ACCESS  read-write
    STATUS      current
    DESCRIPTION
        "Enable or disable caching of PMK."
    ::= { clabWIFIAccessPointRadiusSettingsObjects 4 }

clabWIFIAccessPointRadiusSettingsPMKCachingInterval   OBJECT-TYPE
    SYNTAX      Unsigned32
    UNITS       "seconds"
    MAX-ACCESS  read-write
    STATUS      current
    DESCRIPTION
        "Time interval after which the PMKSA (Pairwise Master Key Security Association) 
         cache is purged."
    ::= { clabWIFIAccessPointRadiusSettingsObjects 5 }

clabWIFIAccessPointRadiusSettingsMaxAuthenticationAttempts    OBJECT-TYPE
    SYNTAX      Unsigned32
    MAX-ACCESS  read-write
    STATUS      current
    DESCRIPTION
        "Indicates the number of times a client can unsuccessfully attempt 
         to login within incorrect credentials. When this limit is reached, 
         the client is blacklisted and not allowed to attempt to login to 
         the network. Setting this parameter to 0 (zero) disables the
         blacklisting feature.."
    ::= { clabWIFIAccessPointRadiusSettingsObjects 6 }

clabWIFIAccessPointRadiusSettingsBlacklistTableTimeout   OBJECT-TYPE
    SYNTAX      Unsigned32
    UNITS       "seconds"
    MAX-ACCESS  read-write
    STATUS      current
    DESCRIPTION
        "Time interval for which a client will continue to be blacklisted one it is marked so."
    ::= { clabWIFIAccessPointRadiusSettingsObjects 7 }

clabWIFIAccessPointRadiusSettingsIdentityRequestRetryInterval  OBJECT-TYPE
    SYNTAX      Unsigned32
    UNITS       "seconds"
    MAX-ACCESS  read-write
    STATUS      current
    DESCRIPTION
        "Time interval between identity request retries. A value of o (zero) disables retry interval."
    ::= { clabWIFIAccessPointRadiusSettingsObjects 8 }

clabWIFIAccessPointRadiusSettingsQuietPeriodAfterFailedAuth  OBJECT-TYPE
    SYNTAX      Unsigned32
    UNITS       "seconds"
    MAX-ACCESS  read-write
    STATUS      current
    DESCRIPTION
        "The enforced quiet period (time interval) following a failed authentication attempt. 
         A value of 0 (zero) disables quiet period."
    ::= { clabWIFIAccessPointRadiusSettingsObjects 9 }

clabWIFIWIFIEventNotif NOTIFICATION-TYPE
    OBJECTS     { 
                  clabWIFIWIFIEventNotifText,
                  clabWIFIWIFIEventNotifEventId,
                  clabWIFIWIFIEventNotifTimeStamp }
    STATUS      current
    DESCRIPTION
        "This object represents the Wi-Fi GW notification."
  ::= {clabWIFINotifications 1 }

clabWIFIWIFIEventNotifgroup OBJECT IDENTIFIER 
  ::= { clabWIFINotifications 2} 


clabWIFIWIFIEventNotifText    OBJECT-TYPE
    SYNTAX      SnmpAdminString (SIZE(0..255))
    MAX-ACCESS  accessible-for-notify
    STATUS      current
    DESCRIPTION
        "This attribute represents the Event Message of the event."
    ::= {clabWIFIWIFIEventNotifgroup 1 }

clabWIFIWIFIEventNotifEventId    OBJECT-TYPE
    SYNTAX      Unsigned32 
    MAX-ACCESS  accessible-for-notify
    STATUS      current
    DESCRIPTION
        "The identifier of the event"
    ::= {clabWIFIWIFIEventNotifgroup 2 }

clabWIFIWIFIEventNotifTimeStamp    OBJECT-TYPE
    SYNTAX      DateAndTime
    MAX-ACCESS  accessible-for-notify
    STATUS      current
    DESCRIPTION
        "Date and Time when the event was generated. (not the time when 
        the event was dispatched)."
    ::= {clabWIFIWIFIEventNotifgroup 3 }

-- Conformance Definitions
clabWIFIMibConformance OBJECT IDENTIFIER ::= { clabWIFIMib 2 }
clabWIFIMibCompliances OBJECT IDENTIFIER ::= { clabWIFIMibConformance 1 }
clabWIFIMibGroups      OBJECT IDENTIFIER ::= { clabWIFIMibConformance 2 }

clabWIFICompliance MODULE-COMPLIANCE
    STATUS      current
    DESCRIPTION
         "The compliance statement for the WiFi Interface."
    MODULE -- this MODULE
    MANDATORY-GROUPS {
            clabWIFIGroup, clabWIFINotificationsGroup
            }
    ::= { clabWIFIMibCompliances 1 }

clabWIFIGroup OBJECT-GROUP
    OBJECTS {
              clabWIFIWiFiRadioNumberOfEntries,
              clabWIFIWiFiSSIDNumberOfEntries,
              clabWIFIWiFiAccessPointNumberOfEntries,
              clabWIFIWiFiEndPointNumberOfEntries,
              clabWIFISSIDSteeringEnabled,
              clabWIFICommitSettings,
              clabWIFIRadioEnable,
              clabWIFIRadioStatus,
              clabWIFIRadioAlias,
              clabWIFIRadioName,
              clabWIFIRadioLastChange,
              clabWIFIRadioLowerLayers,
              clabWIFIRadioUpstream,
              clabWIFIRadioMaxBitRate,
              clabWIFIRadioSupportedFrequencyBands,
              clabWIFIRadioOperatingFrequencyBand,
              clabWIFIRadioSupportedStandards,
              clabWIFIRadioOperatingStandards,
              clabWIFIRadioPossibleChannels,
              clabWIFIRadioChannelsInUse,
              clabWIFIRadioChannel,
              clabWIFIRadioAutoChannelSupported,
              clabWIFIRadioAutoChannelEnable,
              clabWIFIRadioAutoChannelRefreshPeriod,
              clabWIFIRadioOperatingChannelBandwidth,
              clabWIFIRadioExtensionChannel,
              clabWIFIRadioGuardInterval,
              clabWIFIRadioMCS,
              clabWIFIRadioTransmitPowerSupported,
              clabWIFIRadioTransmitPower,
              clabWIFIRadioIEEE80211hSupported,
              clabWIFIRadioIEEE80211hEnabled,
              clabWIFIRadioRegulatoryDomain,
              clabWIFIRadioNonContiguousChannel,
              clabWIFIRadioCarrierSenseThresholdInUse,
              clabWIFIRadioRtsCtsExchange,
              clabWIFIRadioRetryLimit,
              clabWIFIRadioCCARequest,
              clabWIFIRadioRPIHistogramRequest,
              clabWIFIRadioFragmentationThreshold,
              clabWIFIRadioRTSThreshold,
              clabWIFIRadioLongRetryLimit,
              clabWIFIRadioBeaconPeriod,
              clabWIFIRadioDTIMPeriod,
              clabWIFIRadioPacketAggregationEnable,
              clabWIFIRadioBasicDataTransmitRates,
              clabWIFIRadioOperationalDataTransmitRates,
              clabWIFIRadioSupportedDataTransmitRates,
              clabWIFIRadioCarrierSenseThresholdRangeMin,
              clabWIFIRadioCarrierSenseThresholdRangeMax,
              clabWIFIRadioCCAReport,
              clabWIFIRadioRPIHistogramReport,
              clabWIFIRadioPreambleType,
              clabWIFIRadioStatsBytesSent,
              clabWIFIRadioStatsBytesReceived,
              clabWIFIRadioStatsPacketsSent,
              clabWIFIRadioStatsPacketsReceived,
              clabWIFIRadioStatsErrorsSent,
              clabWIFIRadioStatsErrorsReceived,
              clabWIFIRadioStatsDiscardPacketsSent,
              clabWIFIRadioStatsDiscardPacketsReceived,
              clabWIFIRadioStatsPLCPErrorCount,
              clabWIFIRadioStatsFCSErrorCount,
              clabWIFIRadioStatsInvalidMACCount,
              clabWIFIRadioStatsPacketsOtherReceived,
              clabWIFIRadioStatsNoise,
              clabWIFIRadioStatsFramesRetransmissionsSent,
              clabWIFIRadioStatsFramesDuplicatedReceived,
              clabWIFIRadioStatsChannelUtilization,
              clabWIFIRadioChannelWiFiDiagnosticsState,
              clabWIFIRadioChannelWiFiDiagnosticsLastRunTimestamp,
              clabWIFIRadioChannelWiFiDiagnosticsResultNumberOfEntries,
              clabWIFIRadioChannelWiFiDiagnosticsResultsBandwidth,
              clabWIFIRadioChannelWiFiDiagnosticsResultsAvailableCapacity,
              clabWIFIRadioChannelWiFiDiagnosticsResultsNonWiFi,
              clabWIFIRadioChannelWiFiDiagnosticsResultsNonWiFiClasses,
              clabWIFIRadioChannelWiFiDiagnosticsResultsFrequencyBand,
              clabWIFINeighboringWiFiDiagnosticsMode,
              clabWIFINeighboringWiFiDiagnosticsInterval,
              clabWIFINeighboringWiFiDiagnosticsState,
              clabWIFINeighboringWiFiDiagnosticsTableClear,
              clabWIFINeighboringWiFiDiagnosticsTableMaxNumberOfEntries,
              clabWIFINeighboringWiFiSSID,
              clabWIFINeighboringWiFiBSSID,
              clabWIFINeighboringWiFiMode,
              clabWIFINeighboringWiFiChannel,
              clabWIFINeighboringWiFiSignalStrength,
              clabWIFINeighboringWiFiSecurityModeEnabled,
              clabWIFINeighboringWiFiEncryptionMode,
              clabWIFINeighboringWiFiOperatingFrequencyBand,
              clabWIFINeighboringWiFiSupportedStandards,
              clabWIFINeighboringWiFiOperatingStandards,
              clabWIFINeighboringWiFiOperatingChannelBandwidth,
              clabWIFINeighboringWiFiBeaconPeriod,
              clabWIFINeighboringWiFiNoise,
              clabWIFINeighboringWiFiBasicDataTransferRates,
              clabWIFINeighboringWiFiSupportedDataTransferRates,
              clabWIFINeighboringWiFiDTIMPeriod,
              clabWIFINeighboringWiFiSidebandPosition,
              clabWIFINeighboringWiFiDiagnosticsLastRunTimestamp,
              clabWIFINeighboringWiFiDiagnosticsNonContiguousChannel,
              clabWIFINeighboringWiFiDiagnosticsResultNumberOfEntries,
              clabWIFINeighboringWiFiDiagnosticsLastRunTimestamp,
              clabWIFISSIDEnable,
              clabWIFISSIDStatus,
              clabWIFISSIDAlias,
              clabWIFISSIDName,
              clabWIFISSIDLastChange,
              clabWIFISSIDLowerLayers,
              clabWIFISSIDBSSID,
              clabWIFISSIDMACAddress,
              clabWIFISSIDSSID,
              clabWIFISSIDRowStatus,
              clabWIFISSIDFragmentationEnable,
              clabWIFISSIDPeriodicStatsNumberOfEntries,
              clabWIFISSIDStatsBytesSent,
              clabWIFISSIDStatsBytesReceived,
              clabWIFISSIDStatsPacketsSent,
              clabWIFISSIDStatsPacketsReceived,
              clabWIFISSIDStatsErrorsSent,
              clabWIFISSIDStatsErrorsReceived,
              clabWIFISSIDStatsUnicastPacketsSent,
              clabWIFISSIDStatsUnicastPacketsReceived,
              clabWIFISSIDStatsDiscardPacketsSent,
              clabWIFISSIDStatsDiscardPacketsReceived,
              clabWIFISSIDStatsMulticastPacketsSent,
              clabWIFISSIDStatsMulticastPacketsReceived,
              clabWIFISSIDStatsBroadcastPacketsSent,
              clabWIFISSIDStatsBroadcastPacketsReceived,
              clabWIFISSIDStatsUnknownProtoPacketsReceived,
              clabWIFISSIDStatsRetransCount,     
              clabWIFISSIDStatsRetryCount,     
              clabWIFISSIDStatsMultipleRetryCount,     
              clabWIFISSIDStatsACKFailureCount,     
              clabWIFISSIDStatsAggregatedPacketCount,     
              clabWIFIAccessPointEnable,
              clabWIFIAccessPointStatus,
              clabWIFIAccessPointAlias,
              clabWIFIAccessPointSSIDReference,
              clabWIFIAccessPointSSIDAdvertisementEnabled,
              clabWIFIAccessPointWMMCapability,
              clabWIFIAccessPointUAPSDCapability,
              clabWIFIAccessPointWMMEnable,
              clabWIFIAccessPointUAPSDEnable,
              clabWIFIAccessPointAssociatedDeviceNumberOfEntries,
              clabWIFIAccessPointRowStatus,
              clabWIFIAccessPointPublicAccessMode,
              clabWIFIAccessPointIsolationEnable,
              clabWIFIAccessPointMaxAssociatedDevices,
              clabWIFIAccessPointPasspointSupported,
              clabWIFIAccessPointPasspointEnabled,
              clabWIFIAccessPointInterworkingCapability,
              clabWIFIAccessPointInterworkingServiceEnabled,
              clabWIFIAccessPointAccessControlFilterEnable,
              clabWIFIAccessPointMACAddressControlEnable,
              clabWIFIAccessPointAllowedMACAddress,
              clabWIFIAccessPointClientSessionNumberOfEntries,
              clabWIFIAccessPointSecurityModesSupported,
              clabWIFIAccessPointSecurityModeEnabled,
              clabWIFIAccessPointSecurityWEPKey,
              clabWIFIAccessPointSecurityPreSharedKey,
              clabWIFIAccessPointSecurityKeyPassphrase,
              clabWIFIAccessPointSecurityRekeyingInterval,
              clabWIFIAccessPointSecurityRadiusServerIPAddrType,
              clabWIFIAccessPointSecurityRadiusServerIPAddr,
              clabWIFIAccessPointSecurityRadiusServerPort,
              clabWIFIAccessPointSecurityRadiusSecret,
              clabWIFIAccessPointSecurityRowstatus,
              clabWIFIAccessPointSecurityWEPKey2,
              clabWIFIAccessPointSecurityWEPKey3,
              clabWIFIAccessPointSecurityWEPKey4,
              clabWIFIAccessPointSecurityWEPIndex,
              clabWIFIAccessPointSecurityWEPPassPhrase,
              clabWIFIAccessPointSecurityWPAEncryption,
              clabWIFIAccessPointSecuritySecondaryRadiusServerIPAddrType,
              clabWIFIAccessPointSecuritySecondaryRadiusServerIPAddr,
              clabWIFIAccessPointSecuritySecondaryRadiusServerPort,
              clabWIFIAccessPointSecuritySecondaryRadiusSecret,
              clabWIFIAccessPointSecurityEnableManagementFrameProtection,
              clabWIFIAccessPointSecurityReset,
              clabWIFIAccessPointRadiusRetries,
              clabWIFIAccessPointSecurityLanRoutingEnabled,
              clabWIFIAccessPointWPSEnable,
              clabWIFIAccessPointWPSConfigMethodsSupported,
              clabWIFIAccessPointWPSRowStatus,
              clabWIFIAccessPointWPSSetWPSMethods,
              clabWIFIAccessPointWPSAPPin,
              clabWIFIAccessPointWPSSetWPSClientPin,
              clabWIFIAccessPointWPSConfigMethodsEnable,
              clabWIFIAssociatedDeviceMACAddress,
              clabWIFIAssociatedDeviceAuthenticationState,
              clabWIFIAssociatedDeviceLastDataDownlinkRate,
              clabWIFIAssociatedDeviceLastDataUplinkRate,
              clabWIFIAssociatedDeviceSignalStrength,
              clabWIFIAssociatedDeviceRetransmissions,
              clabWIFIAssociatedDeviceActive,
              clabWIFIAssociatedDeviceMaxPacketRetryCount,
              clabWIFIAssociatedDeviceSecurityMode,
              clabWIFIAssociatedDeviceAssociationState,
              clabWIFIPeriodicStatsDeviceMACAddress,
              clabWIFIPeriodicStatsFramesSent,
              clabWIFIPeriodicStatsDataFramesSentAck,
              clabWIFIPeriodicStatsDataFramesSentNoAck,
              clabWIFIPeriodicStatsDataFramesLost,
              clabWIFIPeriodicStatsFramesReceived,
              clabWIFIPeriodicStatsDataFramesReceived,
              clabWIFIPeriodicStatsDataFramesDuplicateReceived,
              clabWIFIPeriodicStatsProbesReceived,
              clabWIFIPeriodicStatsProbesRejected,
              clabWIFIPeriodicStatsRSSI,
              clabWIFIPeriodicStatsSNR,
              clabWIFIPeriodicStatsDisassociations,
              clabWIFIPeriodicStatsAuthenticationFailures,
              clabWIFIPeriodicStatsLastTimeAssociation,
              clabWIFIPeriodicStatsLastTimeDisassociation,
              clabWIFISSIDPolicyBlockAfterAttempts,
              clabWIFISSIDPolicyAllocatedBandwidth,
              clabWIFISSIDPolicyAuthenticationFailures,
              clabWIFISSIDPolicyNonAuthenticatedTraffic,
              clabWIFISSIDPolicyAssociationFailures,
              clabWIFISSIDPolicyStatsInterval,
              clabWIFISSIDPolicySNRThreshold,
              clabWIFISSIDPolicyANPIThreshold,
              clabWIFISSIDPolicyLowReceivedPowerThreshold,
              clabWIFISSIDPolicyLowPowerDeniedAccessThreshold,
              clabWIFISSIDPolicyLowPowerDisassociationThreshold,
              clabWIFISSIDPolicyRowStatus,
              clabWIFISSIDPolicyBeaconMcsLevelInUse,
              clabWIFISSIDPolicyBeaconMcsLevelsSupported,
              clabWIFIClientSessionsDeviceMACAddress,
              clabWIFIClientSessionsStart,
              clabWIFIClientSessionsStop,
              clabWIFIClientSessionsTerminationCode,
              clabWIFIClientSessionsTerminationMeaning,
              clabWIFIClientStatsDeviceMACAddress,
              clabWIFIClientStatsFramesSent,
              clabWIFIClientStatsDataFramesSentAck,
              clabWIFIClientStatsDataFramesSentNoAck,
              clabWIFIClientStatsDataFramesLost,
              clabWIFIClientStatsFramesReceived,
              clabWIFIClientStatsDataFramesReceived,
              clabWIFIClientStatsDataFramesDuplicateReceived,
              clabWIFIClientStatsProbesReceived,
              clabWIFIClientStatsProbesRejected,
              clabWIFIClientStatsRSSI,
              clabWIFIClientStatsSNR,
              clabWIFIClientStatsDisassociations,
              clabWIFIClientStatsAuthenticationFailures,
              clabWIFIClientStatsLastTimeAssociation,
              clabWIFIClientStatsLastTimeDisassociation,
              clabWIFIClientStatsThroughput,
              clabWIFIClientStatsPktErrorRatePerSTA,
              clabWIFIRadiusClientNASIdentifier,
              clabWIFIRadiusClientLocationPolicy,
              clabWIFIRadiusClientOperatorName,
              clabWIFIRadiusClientLocationInformation,
              clabWIFIRadiusClientLocationData,
              clabWIFIRadiusClientUsageReports,
              clabWIFIRadiusClientIntervalInterimReport,
              clabWIFIRadiusClientAPTransitionReport,
              clabWIFIRadiusClientGigawordReport,
              clabWIFIRadiusClientRowStatus,
              clabWIFIAccessPointClearAccessControlFilterTable,
              clabWIFIAccessPointAccessControlFilterAccessAllow,
              clabWIFIAccessPointAccessControlFilterMACAddress,
              clabWIFIAccessPointAccessControlFilterNumberOfEntries,
              clabWIFIAccessPointInterworkingServiceInternet,
              clabWIFIAccessPointInterworkingServiceHESSID,
              clabWIFIAccessPointInterworkingServiceAccessNetworkType,
              clabWIFIAccessPointInterworkingServiceVenueGroupCode,
              clabWIFIAccessPointInterworkingServiceVenueTypeCode,
              clabWIFIAccessPointPasspointCapabilities,
              clabWIFIAccessPointPasspointOnlineSignupSupported,
              clabWIFIAccessPointPasspointDGAFEnable,
              clabWIFIAccessPointPasspointP2PEnable,
              clabWIFIAccessPointPasspointQoSMappingEnable,
              clabWIFIAccessPointPasspointASRAEnable,
              clabWIFIAccessPointPasspointANQPDomainID,
              clabWIFIAccessPointPasspointEAPMethod,
              clabWIFIAccessPointPasspointManagementFrameProtectionEnable,
              clabWIFIAccessPointPasspointOperatorNameCountryCode,
              clabWIFIAccessPointPasspointOperatorName,
              clabWIFIAccessPointPasspointConsortiumOI,
              clabWIFIAccessPointPasspointDomainNamesDomainName,
              clabWIFIAccessPointPasspointThreeGPPNetworkMNC,
              clabWIFIAccessPointPasspointThreeGPPNetworkMCC,
              clabWIFIAccessPointPasspoint2VenueNameCountryCode,
              clabWIFIAccessPointPasspoint2VenueName,
              clabWIFIAccessPointPasspoint2NAIRealmsEncodingType,
              clabWIFIAccessPointPasspoint2NAIRealms,
              clabWIFIAccessPointPasspoint2NAIRealmsEapMethod,
              clabWIFIAccessPointPasspoint2NAIRealmsEapAuthParametersID,
              clabWIFIAccessPointPasspoint2NAIRealmsEapAuthParametersValue,
              clabWIFIAccessPointPasspoint2OSUProviderServerURI,
              clabWIFIAccessPointPasspoint2OSUProviderNAI,
              clabWIFIAccessPointPasspoint2OSUProviderNamesLanguageCode,
              clabWIFIAccessPointPasspoint2OSUProviderNamesFriendlyName,
              clabWIFIAccessPointPasspoint2OSUProviderIconFileName,
              clabWIFIAccessPointPasspoint2OSUProviderIconType,
              clabWIFIAccessPointPasspoint2OSUProviderIconWidth,
              clabWIFIAccessPointPasspoint2OSUProviderIconHeight,
              clabWIFIAccessPointPasspoint2OSUProviderIconLanguageCode,
              clabWIFIAccessPointPasspoint2OSUProviderServiceDescLanguageCode,
              clabWIFIAccessPointPasspoint2OSUProviderServiceDescription,
              clabWIFIAccessPointPasspoint2OSUProviderMethodsList,
              clabWIFIAccessPointPasspointWANMetricsLinkStatus,
              clabWIFIAccessPointPasspointWANMetricsAtCapacity,
              clabWIFIAccessPointPasspointWANMetricsDownlinkSpeed,
              clabWIFIAccessPointPasspointWANMetricsUplinkSpeed,
              clabWIFIAccessPointPasspointWANMetricsDownlinkLoad,
              clabWIFIAccessPointPasspointWANMetricsUplinkLoad,
              clabWIFIAccessPointAccountingEnable,
              clabWIFIAccessPointAccountingServerIPAddrType,
              clabWIFIAccessPointAccountingServerIPAddr,
              clabWIFIAccessPointAccountingSecondaryServerIPAddrType,
              clabWIFIAccessPointAccountingSecondaryServerIPAddr,
              clabWIFIAccessPointAccountingServerPort,
              clabWIFIAccessPointAccountingSecondaryServerPort,
              clabWIFIAccessPointAccountingSecret,
              clabWIFIAccessPointAccountingSecondarySecret,
              clabWIFIAccessPointAccountingInterimInterval,
              clabWIFIAccessPointAccountingRowStatus,
              clabWIFIAccessPointAC2AccessCategory,
              clabWIFIAccessPointAC2Alias,
              clabWIFIAccessPointAC2AIFSN,
              clabWIFIAccessPointAC2ECWMin,
              clabWIFIAccessPointAC2ECWMax,
              clabWIFIAccessPointAC2TxOpMax,
              clabWIFIAccessPointAC2AckPolicy,
              clabWIFIAccessPointAC2OutQLenHistogramIntervals,
              clabWIFIAccessPointAC2OutQLenHistogramSampleInterval,
              clabWIFIAccessPointAC2StatsBytesSent,
              clabWIFIAccessPointAC2StatsBytesReceived,
              clabWIFIAccessPointAC2StatsPacketsSent,
              clabWIFIAccessPointAC2StatsPacketsReceived,
              clabWIFIAccessPointAC2StatsErrorsSent,
              clabWIFIAccessPointAC2StatsErrorsReceived,
              clabWIFIAccessPointAC2StatsDiscardPacketsSent,
              clabWIFIAccessPointAC2StatsDiscardPacketsReceived,
              clabWIFIAccessPointAC2StatsRetransCount,
              clabWIFIAccessPointAC2StatsOutQLenHistogram,
              clabWIFIAccessPointRadiusSettingsRadiusServerRetries,
              clabWIFIAccessPointRadiusSettingsRadiusServerRequestTimeout,
              clabWIFIAccessPointRadiusSettingsPMKLifetime,
              clabWIFIAccessPointRadiusSettingsPMKCachingEnable,
              clabWIFIAccessPointRadiusSettingsPMKCachingInterval,
              clabWIFIAccessPointRadiusSettingsMaxAuthenticationAttempts,
              clabWIFIAccessPointRadiusSettingsBlacklistTableTimeout,
              clabWIFIAccessPointRadiusSettingsIdentityRequestRetryInterval,
              clabWIFIAccessPointRadiusSettingsQuietPeriodAfterFailedAuth,
              clabWIFIWIFIEventNotifText,
              clabWIFIWIFIEventNotifEventId,
              clabWIFIWIFIEventNotifTimeStamp
            }
    STATUS      current
    DESCRIPTION
             "Objects implemented in the clabWIFIGroup."
    ::= { clabWIFIMibGroups 1 }

clabWIFINotificationsGroup NOTIFICATION-GROUP
   NOTIFICATIONS { clabWIFIWIFIEventNotif }
   STATUS        current
   DESCRIPTION
           "Notifications implemented in the clabWIFINotificationsGroup."
   ::= { clabWIFIMibGroups 2}

clabDeprecatedObjectsGroup OBJECT-GROUP
    OBJECTS {
              clabWIFIRadioCarrierSenseThresholdRange,
              clabWIFIRadioStatsChanUtilization,
              clabWIFIRadioFrameAggregationLevel,
              clabWIFIRadioThroughput,
              clabWIFIRadioPktErrorRateSTA,
              clabWIFIAccessPointRetryLimit,
              clabWIFIAccessPointWPSConfigMethodsEnabled,
              clabWIFIAccessPointWPSSetWPSMethod,
              clabWIFIAccessPointAssociatedDeviceCount,
              clabWIFIAssociatedDeviceStationCount,
              clabWIFIAssociatedDeviceMaxNumOfStations,
              clabWIFIAssociatedDeviceEncryptionAlgorithm,
              clabWIFIDataRateStatsFramesSent,
              clabWIFIDataRateStatsFramesRetransmissionsSent,
              clabWIFIDataRateStatsFramesReceived,
              clabWIFIDataRateStatsFramesDuplicatedReceived,
              clabWIFIWIFICommitSettingsValue,
              clabWIFIApNeighborStatsSSID,
              clabWIFIApNeighborStatsCurrentChannel,
              clabWIFIApNeighborStatsCurrentBandwidth,
              clabWIFIApNeighborStatsRSSI,
              clabWIFIAccessPointPasspointCapabilityList,
              clabWIFIAccessPointPasspointVenueNameCountryCode,
              clabWIFIAccessPointPasspointVenueName,
              clabWIFIAccessPointPasspointNAIRealmsEncodingType,
              clabWIFIAccessPointPasspointNAIRealms,
              clabWIFIAccessPointPasspointNAIRealmsEapMethod,
              clabWIFIAccessPointPasspointNAIRealmsEapAuthParametersID,
              clabWIFIAccessPointPasspointNAIRealmsEapAuthParametersValue,
              clabWIFIAccessPointPasspointOSUProviderServerURI,
              clabWIFIAccessPointPasspointOSUProviderNAI,
              clabWIFIAccessPointPasspointOSUProviderNamesLanguageCode,
              clabWIFIAccessPointPasspointOSUProviderNamesFriendlyName,
              clabWIFIAccessPointPasspointOSUProviderIconFileName,
              clabWIFIAccessPointPasspointOSUProviderIconType,
              clabWIFIAccessPointPasspointOSUProviderIconWidth,
              clabWIFIAccessPointPasspointOSUProviderIconHeight,
              clabWIFIAccessPointPasspointOSUProviderIconLanguageCode,
              clabWIFIAccessPointPasspointOSUProviderServiceDescLanguageCode,
              clabWIFIAccessPointPasspointOSUProviderServiceDescription,
              clabWIFIAccessPointPasspointOSUProviderMethodsList,
              clabWIFIAccessPointACAccessCategory,
              clabWIFIAccessPointACAlias,
              clabWIFIAccessPointACAIFSN,
              clabWIFIAccessPointACECWMin,
              clabWIFIAccessPointACECWMax,
              clabWIFIAccessPointACTxOpMax,
              clabWIFIAccessPointACAckPolicy,
              clabWIFIAccessPointACOutQLenHistogramIntervals,
              clabWIFIAccessPointACOutQLenHistogramSampleInterval,
              clabWIFIAccessPointACStatsBytesSent,
              clabWIFIAccessPointACStatsBytesReceived,
              clabWIFIAccessPointACStatsPacketsSent,
              clabWIFIAccessPointACStatsPacketsReceived,
              clabWIFIAccessPointACStatsErrorsSent,
              clabWIFIAccessPointACStatsErrorsReceived,
              clabWIFIAccessPointACStatsDiscardPacketsSent,
              clabWIFIAccessPointACStatsDiscardPacketsReceived,
              clabWIFIAccessPointACStatsRetransCount,
              clabWIFIAccessPointACStatsOutQLenHistogram
            }
    STATUS      obsolete
    DESCRIPTION
             "A place for deprecated objects so they have a home for smilint."
    ::= { clabWIFIMibGroups 99 }

END
