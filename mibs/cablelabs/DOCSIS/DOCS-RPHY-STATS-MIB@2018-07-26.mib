DOCS-RPHY-STATS-MIB DEFINITIONS ::= BEGIN
IMPORTS
    MODULE-IDENTITY, 
    OBJECT-TYPE, 
    Unsigned32,
    Counter64
        FROM SNMPv2-SMI         -- RFC 2578
    DateAndTime,
    TEXTUAL-CONVENTION
        FROM SNMPv2-TC 
    OBJECT-GROUP, 
    MODULE-COMPLIANCE 
        FROM SNMPv2-CONF
    SnmpAdminString
        FROM SNMP-FRAMEWORK-MIB -- RFC 3411
    InterfaceIndex,
    ifIndex,
    InterfaceIndexOrZero
        FROM IF-MIB
    IfDirection
        FROM DOCS-IF3-MIB
    docsRphyRpdDevInfoUniqueId
        FROM DOCS-RPHY-MIB
    clabProjDocsis
        FROM CLAB-DEF-MIB;


docsRphyStatsMib MODULE-IDENTITY 
    LAST-UPDATED    "201807260000Z" -- July 26, 2018
    ORGANIZATION    "Cable Television Laboratories, Inc" 
    CONTACT-INFO 
         "
         Postal: Cable Television Laboratories, Inc. 
         400 Centennial Parkway 
         Louisville, Colorado 80027-1266 
         U.S.A. 
         Phone: +1 303-661-9100 
         Fax: +1 303-661-9199 
         E-mail: mibs@cablelabs.com" 
    DESCRIPTION 
        "This MIB module contains the statistics reporting objects
         for the Remote PHY CCAP Core and RPD monitoring.
         Copyright 2017-2018 Cable Television Laboratories, Inc.
         All rights reserved."
    REVISION "201807260000Z" 
    DESCRIPTION 
        "Revised per DOCS-RPHY-STATS-MIB-N-18.1936-2."
    REVISION "201804120000Z" 
    DESCRIPTION 
        "Revised per DOCS-RPHY-STATS-MIB-N-18.1895-1."
    REVISION "201711160000Z" 
    DESCRIPTION 
        "Initial version, created by R-OSSI-N-17.1848-5."
::= { clabProjDocsis 33 }


-- ---------------------------------------------------------
-- Textual Conventions
-- ---------------------------------------------------------

                         
-- ---------------------------------------------------------------------
-- Main Groups
-- ---------------------------------------------------------------------
docsRphyStatsNotifications        OBJECT IDENTIFIER ::= { docsRphyStatsMib 0}
docsRphyStatsObjects              OBJECT IDENTIFIER ::= { docsRphyStatsMib 1}
docsRphyStatsConformance          OBJECT IDENTIFIER ::= { docsRphyStatsMib 2}

docsRphyStatsRpdMibObjects        OBJECT IDENTIFIER ::= { docsRphyStatsObjects 1}
docsRphyStatsRpdDsMibObjects      OBJECT IDENTIFIER ::= { docsRphyStatsRpdMibObjects 1}
docsRphyStatsRpdUsMibObjects      OBJECT IDENTIFIER ::= { docsRphyStatsRpdMibObjects 2}
docsRphyStatsCcapMibObjects       OBJECT IDENTIFIER ::= { docsRphyStatsObjects 2}

docsRphyStatsCompliances          OBJECT IDENTIFIER ::= { docsRphyStatsConformance 1 } 
docsRphyStatsGroups               OBJECT IDENTIFIER ::= { docsRphyStatsConformance 2 }


-- ---------------------------------------------------------------------
-- Notification Objects
-- ---------------------------------------------------------------------

-- ---------------------------------------------------------------------
-- CCAP Core RPD Group Objects
-- ---------------------------------------------------------------------

-- ---------------------------------------------------------------------
-- Downstream SC-QAM Performance Statistics
-- ---------------------------------------------------------------------

docsRphyStatsRpdDsScQamPerfStatsTable OBJECT-TYPE
        SYNTAX      SEQUENCE OF DocsRphyStatsRpdDsScQamPerfStatsEntry
        MAX-ACCESS  not-accessible
        STATUS      current
        DESCRIPTION
            "This table reports statistical counters for a 
             downstream SC-QAM channel."
        ::= { docsRphyStatsRpdDsMibObjects 1 }


docsRphyStatsRpdDsScQamPerfStatsEntry OBJECT-TYPE
        SYNTAX     DocsRphyStatsRpdDsScQamPerfStatsEntry
        MAX-ACCESS not-accessible
        STATUS     current
        DESCRIPTION
            "The conceptual row of docsRphyStatsRpdDsScQamPerfStatsTable."
        INDEX { docsRphyRpdDevInfoUniqueId, docsRphyStatsRpdDsScQamPerfStatsCoreIfIndex, 
                docsRphyStatsRpdDsScQamPerfStatsDsRfPortIndex }
        ::= { docsRphyStatsRpdDsScQamPerfStatsTable 1 }


DocsRphyStatsRpdDsScQamPerfStatsEntry ::= SEQUENCE
       {
       docsRphyStatsRpdDsScQamPerfStatsCoreIfIndex            InterfaceIndex,
       docsRphyStatsRpdDsScQamPerfStatsDsRfPortIndex          Unsigned32,
       docsRphyStatsRpdDsScQamPerfStatsOutDiscards            Counter64,
       docsRphyStatsRpdDsScQamPerfStatsOutErrors              Counter64,
       docsRphyStatsRpdDsScQamPerfStatsOutPackets             Counter64,
       docsRphyStatsRpdDsScQamPerfStatsRpdDsCounterDiscTime   DateAndTime
       }

docsRphyStatsRpdDsScQamPerfStatsCoreIfIndex OBJECT-TYPE
    SYNTAX      InterfaceIndex
    MAX-ACCESS  not-accessible
    STATUS      current
    DESCRIPTION
            "This key attribute uniquely identifies
             the selected SC-QAM channel."
    ::= { docsRphyStatsRpdDsScQamPerfStatsEntry 1 }

docsRphyStatsRpdDsScQamPerfStatsDsRfPortIndex OBJECT-TYPE
    SYNTAX      Unsigned32 (0..253)
    MAX-ACCESS  not-accessible
    STATUS      current
    DESCRIPTION
            "This key attribute uniquely identifies the 
             selected CCAP Core downstream RF port."
    ::= { docsRphyStatsRpdDsScQamPerfStatsEntry 2 }

docsRphyStatsRpdDsScQamPerfStatsOutDiscards OBJECT-TYPE
    SYNTAX     Counter64
    MAX-ACCESS read-only
    STATUS     current
    DESCRIPTION
           "This attribute reports the number of outbound packets
            which were internally discarded before transmission 
            (e.g. due to lack of buffering) for the downstream
            SC-QAM channel."
    ::= { docsRphyStatsRpdDsScQamPerfStatsEntry 3 }

docsRphyStatsRpdDsScQamPerfStatsOutErrors OBJECT-TYPE
    SYNTAX     Counter64
    MAX-ACCESS read-only
    STATUS     current
    DESCRIPTION
           "This attribute reports the number of outbound packets
            that could not be transmitted because of errors for 
            the downstream SC-QAM channel."
    ::= { docsRphyStatsRpdDsScQamPerfStatsEntry 4 }

docsRphyStatsRpdDsScQamPerfStatsOutPackets OBJECT-TYPE
    SYNTAX     Counter64
    MAX-ACCESS read-only
    STATUS     current
    DESCRIPTION
           "This attribute reports the number of outbound 
            packets successfully transmitted for 
            the downstream SC-QAM channel."
    ::= { docsRphyStatsRpdDsScQamPerfStatsEntry 5 }

docsRphyStatsRpdDsScQamPerfStatsRpdDsCounterDiscTime OBJECT-TYPE
    SYNTAX     DateAndTime
    MAX-ACCESS read-only
    STATUS     current
    DESCRIPTION
           "This attribute reports the date and time at which any one or more 
            of the counters in this group were created or last reset to zero. 
            If the RPD does not acquire time of day it can report an initial 
            CounterDiscontinuityTime of Jan 1 1970. If the value returned by 
            the RPD is the initial Epoch of Jan 1 1970, the CCAP Core can convert 
            this value to the real time of day based on a calculation using 
            the RPD's reported sysUpTime."
    ::= { docsRphyStatsRpdDsScQamPerfStatsEntry 6 }

-- ---------------------------------------------------------------------
-- Downstream OFDM Performance Statistics
-- ---------------------------------------------------------------------

docsRphyStatsRpdDsOfdmPerfStatsTable OBJECT-TYPE
        SYNTAX      SEQUENCE OF DocsRphyStatsRpdDsOfdmPerfStatsEntry
        MAX-ACCESS  not-accessible
        STATUS      current
        DESCRIPTION
            "This table reports statistical counters for a 
             downstream OFDM channel."
        ::= { docsRphyStatsRpdDsMibObjects 2 }


docsRphyStatsRpdDsOfdmPerfStatsEntry OBJECT-TYPE
        SYNTAX     DocsRphyStatsRpdDsOfdmPerfStatsEntry
        MAX-ACCESS not-accessible
        STATUS     current
        DESCRIPTION
            "The conceptual row of docsRphyStatsRpdDsOfdmPerfStatsTable."
        INDEX { docsRphyRpdDevInfoUniqueId, docsRphyStatsRpdDsOfdmPerfStatsCoreIfIndex,
                docsRphyStatsRpdDsOfdmPerfStatsDsRfPortIndex}
        ::= { docsRphyStatsRpdDsOfdmPerfStatsTable 1 }


DocsRphyStatsRpdDsOfdmPerfStatsEntry ::= SEQUENCE
       {
       docsRphyStatsRpdDsOfdmPerfStatsCoreIfIndex            InterfaceIndex,
       docsRphyStatsRpdDsOfdmPerfStatsDsRfPortIndex          Unsigned32,
       docsRphyStatsRpdDsOfdmPerfStatsOutDiscards            Counter64,
       docsRphyStatsRpdDsOfdmPerfStatsOutErrors              Counter64,
       docsRphyStatsRpdDsOfdmPerfStatsOutPackets             Counter64,
       docsRphyStatsRpdDsOfdmPerfStatsRpdDsCounterDiscTime   DateAndTime
       }

docsRphyStatsRpdDsOfdmPerfStatsCoreIfIndex OBJECT-TYPE
    SYNTAX      InterfaceIndex
    MAX-ACCESS  not-accessible
    STATUS      current
    DESCRIPTION
            "This key attribute uniquely identifies
             the selected OFDM channel."
    ::= { docsRphyStatsRpdDsOfdmPerfStatsEntry 1 }

docsRphyStatsRpdDsOfdmPerfStatsDsRfPortIndex OBJECT-TYPE
    SYNTAX      Unsigned32 (0..253)
    MAX-ACCESS  not-accessible
    STATUS      current
    DESCRIPTION
            "This key attribute uniquely identifies the
             selected CCAP Core downstream RF Port."
    ::= { docsRphyStatsRpdDsOfdmPerfStatsEntry 2 }

docsRphyStatsRpdDsOfdmPerfStatsOutDiscards OBJECT-TYPE
    SYNTAX     Counter64
    MAX-ACCESS read-only
    STATUS     current
    DESCRIPTION
           "This attribute reports the number of outbound packets
            which were internally discarded before transmission 
            (e.g. due to lack of buffering) for the downstream
            OFDM channel."
    ::= { docsRphyStatsRpdDsOfdmPerfStatsEntry 3 }

docsRphyStatsRpdDsOfdmPerfStatsOutErrors OBJECT-TYPE
    SYNTAX     Counter64
    MAX-ACCESS read-only
    STATUS     current
    DESCRIPTION
           "This attribute reports the number of outbound packets
            that could not be transmitted because of errors for 
            the downstream OFDM channel."
    ::= { docsRphyStatsRpdDsOfdmPerfStatsEntry 4 }

docsRphyStatsRpdDsOfdmPerfStatsOutPackets OBJECT-TYPE
    SYNTAX     Counter64
    MAX-ACCESS read-only
    STATUS     current
    DESCRIPTION
           "This attribute reports the number of outbound 
            packets successfully transmitted for 
            the downstream OFDM channel."
    ::= { docsRphyStatsRpdDsOfdmPerfStatsEntry 5 }

docsRphyStatsRpdDsOfdmPerfStatsRpdDsCounterDiscTime OBJECT-TYPE
    SYNTAX     DateAndTime
    MAX-ACCESS read-only
    STATUS     current
    DESCRIPTION
           "This attribute reports the date and time at which any one or more 
            of the counters in this group were created or last reset to zero. 
            If the RPD does not acquire time of day it can report an initial 
            CounterDiscontinuityTime of Jan 1 1970. If the value returned by 
            the RPD is the initial Epoch of Jan 1 1970, the CCAP Core can convert 
            this value to the real time of day based on a calculation using 
            the RPD's reported sysUpTime."
    ::= { docsRphyStatsRpdDsOfdmPerfStatsEntry 6 }

-- ---------------------------------------------------------------------
-- Downstream OOB551 Performance Statistics
-- ---------------------------------------------------------------------

docsRphyStatsRpdDsOob551PerfStatsTable OBJECT-TYPE
        SYNTAX      SEQUENCE OF DocsRphyStatsRpdDsOob551PerfStatsEntry
        MAX-ACCESS  not-accessible
        STATUS      current
        DESCRIPTION
            "This table reports statistical counters for a 
             downstream channel with DEPI channel type 
             SCTE-55-1-FWD."
        ::= { docsRphyStatsRpdDsMibObjects 3 }


docsRphyStatsRpdDsOob551PerfStatsEntry OBJECT-TYPE
        SYNTAX     DocsRphyStatsRpdDsOob551PerfStatsEntry
        MAX-ACCESS not-accessible
        STATUS     current
        DESCRIPTION
            "The conceptual row of docsRphyStatsRpdDsOob551PerfStatsTable."
        INDEX { docsRphyRpdDevInfoUniqueId, docsRphyStatsRpdDsOob551PerfStatsCoreIfIndex, 
                docsRphyStatsRpdDsOob551PerfStatsDsRfPortIndex, docsRphyStatsRpdDsOob551PerfStatsFreqIndex}
        ::= { docsRphyStatsRpdDsOob551PerfStatsTable 1 }


DocsRphyStatsRpdDsOob551PerfStatsEntry ::= SEQUENCE
       {
       docsRphyStatsRpdDsOob551PerfStatsCoreIfIndex            InterfaceIndex,
       docsRphyStatsRpdDsOob551PerfStatsDsRfPortIndex          Unsigned32,
       docsRphyStatsRpdDsOob551PerfStatsFreqIndex              Unsigned32,
       docsRphyStatsRpdDsOob551PerfStatsOutDiscards            Counter64,
       docsRphyStatsRpdDsOob551PerfStatsOutErrors              Counter64,
       docsRphyStatsRpdDsOob551PerfStatsOutPackets             Counter64,
       docsRphyStatsRpdDsOob551PerfStatsRpdDsCounterDiscTime   DateAndTime
       }

docsRphyStatsRpdDsOob551PerfStatsCoreIfIndex OBJECT-TYPE
    SYNTAX      InterfaceIndex
    MAX-ACCESS  not-accessible
    STATUS      current
    DESCRIPTION
            "This key attribute uniquely identifies the 
             selected DEPI channel type SCTE-55-1-FWD."
    ::= { docsRphyStatsRpdDsOob551PerfStatsEntry 1 }

docsRphyStatsRpdDsOob551PerfStatsDsRfPortIndex OBJECT-TYPE
    SYNTAX      Unsigned32 (0..253)
    MAX-ACCESS  not-accessible
    STATUS      current
    DESCRIPTION
            "This key attribute uniquely identifies the 
             selected CCAP Core downstream RF port."
    ::= { docsRphyStatsRpdDsOob551PerfStatsEntry 2 }

docsRphyStatsRpdDsOob551PerfStatsFreqIndex OBJECT-TYPE
    SYNTAX      Unsigned32 (0..255)
    MAX-ACCESS  not-accessible
    STATUS      current
    DESCRIPTION
            "This key attribute uniquely identifies the 
             selected SCTE-55-1 FWD channel frequency."
    ::= { docsRphyStatsRpdDsOob551PerfStatsEntry 3 }

docsRphyStatsRpdDsOob551PerfStatsOutDiscards OBJECT-TYPE
    SYNTAX     Counter64
    MAX-ACCESS read-only
    STATUS     current
    DESCRIPTION
           "This attribute reports the number of outbound packets
            which were internally discarded before transmission 
            (e.g. due to lack of buffering) for the downstream
            selected DEPI channel type SCTE-55-1-FWD."
    ::= { docsRphyStatsRpdDsOob551PerfStatsEntry 4 }

docsRphyStatsRpdDsOob551PerfStatsOutErrors OBJECT-TYPE
    SYNTAX     Counter64
    MAX-ACCESS read-only
    STATUS     current
    DESCRIPTION
           "This attribute reports the number of outbound packets
            that could not be transmitted because of errors for 
            the downstream selected DEPI channel type SCTE-55-1-FWD."
    ::= { docsRphyStatsRpdDsOob551PerfStatsEntry 5 }

docsRphyStatsRpdDsOob551PerfStatsOutPackets OBJECT-TYPE
    SYNTAX     Counter64
    MAX-ACCESS read-only
    STATUS     current
    DESCRIPTION
           "This attribute reports the number of outbound 
            packets successfully transmitted for 
            the downstream selected DEPI channel type SCTE-55-1-FWD."
    ::= { docsRphyStatsRpdDsOob551PerfStatsEntry 6 }

docsRphyStatsRpdDsOob551PerfStatsRpdDsCounterDiscTime OBJECT-TYPE
    SYNTAX     DateAndTime
    MAX-ACCESS read-only
    STATUS     current
    DESCRIPTION
           "This attribute reports the date and time at which any one or more 
            of the counters in this group were created or last reset to zero. 
            If the RPD does not acquire time of day it can report an initial 
            CounterDiscontinuityTime of Jan 1 1970. If the value returned by 
            the RPD is the initial Epoch of Jan 1 1970, the CCAP Core can convert 
            this value to the real time of day based on a calculation using 
            the RPD's reported sysUpTime."
    ::= { docsRphyStatsRpdDsOob551PerfStatsEntry 7 }

-- ---------------------------------------------------------------------
-- Downstream OOB552 Performance Statistics
-- ---------------------------------------------------------------------

docsRphyStatsRpdDsOob552PerfStatsTable OBJECT-TYPE
        SYNTAX      SEQUENCE OF DocsRphyStatsRpdDsOob552PerfStatsEntry
        MAX-ACCESS  not-accessible
        STATUS      current
        DESCRIPTION
            "This table reports statistical counters for a 
             downstream channel with DEPI channel type 
             SCTE-55-2-FWD."
        ::= { docsRphyStatsRpdDsMibObjects 4 }


docsRphyStatsRpdDsOob552PerfStatsEntry OBJECT-TYPE
        SYNTAX     DocsRphyStatsRpdDsOob552PerfStatsEntry
        MAX-ACCESS not-accessible
        STATUS     current
        DESCRIPTION
            "The conceptual row of docsRphyStatsRpdDsOob552PerfStatsTable."
        INDEX { docsRphyRpdDevInfoUniqueId, docsRphyStatsRpdDsOob552PerfStatsCoreIfIndex,
                docsRphyStatsRpdDsOob552PerfStatsModuleIndex, docsRphyStatsRpdDsOob552PerfStatsDsRfPortIndex}
        ::= { docsRphyStatsRpdDsOob552PerfStatsTable 1 }


DocsRphyStatsRpdDsOob552PerfStatsEntry ::= SEQUENCE
       {
       docsRphyStatsRpdDsOob552PerfStatsCoreIfIndex            InterfaceIndex,
       docsRphyStatsRpdDsOob552PerfStatsModuleIndex            Unsigned32,
       docsRphyStatsRpdDsOob552PerfStatsDsRfPortIndex          Unsigned32,
       docsRphyStatsRpdDsOob552PerfStatsOutDiscards            Counter64,
       docsRphyStatsRpdDsOob552PerfStatsOutErrors              Counter64,
       docsRphyStatsRpdDsOob552PerfStatsOutPackets             Counter64,
       docsRphyStatsRpdDsOob552PerfStatsRpdDsCounterDiscTime   DateAndTime
       }

docsRphyStatsRpdDsOob552PerfStatsCoreIfIndex OBJECT-TYPE
    SYNTAX      InterfaceIndex
    MAX-ACCESS  not-accessible
    STATUS      current
    DESCRIPTION
            "This key attribute uniquely identifies the 
             selected DEPI channel type SCTE-55-2-FWD."
    ::= { docsRphyStatsRpdDsOob552PerfStatsEntry 1 }

docsRphyStatsRpdDsOob552PerfStatsModuleIndex OBJECT-TYPE
    SYNTAX      Unsigned32 (0..255)
    MAX-ACCESS  not-accessible
    STATUS      current
    DESCRIPTION
            "This key attribute uniquely identifies the 
             selected SCTE 55-2 Forward Module."
    ::= { docsRphyStatsRpdDsOob552PerfStatsEntry 2 }

docsRphyStatsRpdDsOob552PerfStatsDsRfPortIndex OBJECT-TYPE
    SYNTAX      Unsigned32 (0..253)
    MAX-ACCESS  not-accessible
    STATUS      current
    DESCRIPTION
            "This key attribute uniquely identifies the 
             selected CCAP Core downstream RF port."
    ::= { docsRphyStatsRpdDsOob552PerfStatsEntry 3 }

docsRphyStatsRpdDsOob552PerfStatsOutDiscards OBJECT-TYPE
    SYNTAX     Counter64
    MAX-ACCESS read-only
    STATUS     current
    DESCRIPTION
           "This attribute reports the number of outbound packets
            which were internally discarded before transmission 
            (e.g. due to lack of buffering) for the downstream
            selected DEPI channel type SCTE-55-2-FWD."
    ::= { docsRphyStatsRpdDsOob552PerfStatsEntry 4 }

docsRphyStatsRpdDsOob552PerfStatsOutErrors OBJECT-TYPE
    SYNTAX     Counter64
    MAX-ACCESS read-only
    STATUS     current
    DESCRIPTION
           "This attribute reports the number of outbound packets
            that could not be transmitted because of errors for 
            the downstream selected DEPI channel type SCTE-55-2-FWD."
    ::= { docsRphyStatsRpdDsOob552PerfStatsEntry 5 }

docsRphyStatsRpdDsOob552PerfStatsOutPackets OBJECT-TYPE
    SYNTAX     Counter64
    MAX-ACCESS read-only
    STATUS     current
    DESCRIPTION
           "This attribute reports the number of outbound 
            packets successfully transmitted for 
            the downstream selected DEPI channel type SCTE-55-2-FWD."
    ::= { docsRphyStatsRpdDsOob552PerfStatsEntry 6 }

docsRphyStatsRpdDsOob552PerfStatsRpdDsCounterDiscTime OBJECT-TYPE
    SYNTAX     DateAndTime
    MAX-ACCESS read-only
    STATUS     current
    DESCRIPTION
           "This attribute reports the date and time at which any one or more 
            of the counters in this group were created or last reset to zero. 
            If the RPD does not acquire time of day it can report an initial 
            CounterDiscontinuityTime of Jan 1 1970. If the value returned by 
            the RPD is the initial Epoch of Jan 1 1970, the CCAP Core can convert 
            this value to the real time of day based on a calculation using 
            the RPD's reported sysUpTime."
    ::= { docsRphyStatsRpdDsOob552PerfStatsEntry 7 }

-- ---------------------------------------------------------------------
-- Downstream NDF Performance Statistics
-- ---------------------------------------------------------------------

docsRphyStatsRpdDsNdfPerfStatsTable OBJECT-TYPE
        SYNTAX      SEQUENCE OF DocsRphyStatsRpdDsNdfPerfStatsEntry
        MAX-ACCESS  not-accessible
        STATUS      current
        DESCRIPTION
            "This table reports statistical counters for a 
             downstream channel with DEPI channel type NDF
             per the RPD Channel Selector table in [DEPI]."
        ::= { docsRphyStatsRpdDsMibObjects 5 }


docsRphyStatsRpdDsNdfPerfStatsEntry OBJECT-TYPE
        SYNTAX     DocsRphyStatsRpdDsNdfPerfStatsEntry
        MAX-ACCESS not-accessible
        STATUS     current
        DESCRIPTION
            "The conceptual row of docsRphyStatsRpdDsNdfPerfStatsTable."
        INDEX { docsRphyRpdDevInfoUniqueId, docsRphyStatsRpdDsNdfPerfStatsCoreIfIndex, 
                docsRphyStatsRpdDsNdfPerfStatsDsRfPortIndex}
        ::= { docsRphyStatsRpdDsNdfPerfStatsTable 1 }


DocsRphyStatsRpdDsNdfPerfStatsEntry ::= SEQUENCE
       {
       docsRphyStatsRpdDsNdfPerfStatsCoreIfIndex            InterfaceIndex,
       docsRphyStatsRpdDsNdfPerfStatsDsRfPortIndex          Unsigned32,
       docsRphyStatsRpdDsNdfPerfStatsOutDiscards            Counter64,
       docsRphyStatsRpdDsNdfPerfStatsOutErrors              Counter64,
       docsRphyStatsRpdDsNdfPerfStatsOutPackets             Counter64,
       docsRphyStatsRpdDsNdfPerfStatsRpdDsCounterDiscTime   DateAndTime
       }

docsRphyStatsRpdDsNdfPerfStatsCoreIfIndex OBJECT-TYPE
    SYNTAX      InterfaceIndex
    MAX-ACCESS  not-accessible
    STATUS      current
    DESCRIPTION
            "This key attribute uniquely identifies the 
             selected DEPI channel type NDF."
    ::= { docsRphyStatsRpdDsNdfPerfStatsEntry 1 }

docsRphyStatsRpdDsNdfPerfStatsDsRfPortIndex OBJECT-TYPE
    SYNTAX      Unsigned32 (0..253)
    MAX-ACCESS  not-accessible
    STATUS      current
    DESCRIPTION
            "This key attribute uniquely identifies the 
             selected CCAP Core downstream RF port."
    ::= { docsRphyStatsRpdDsNdfPerfStatsEntry 2 }

docsRphyStatsRpdDsNdfPerfStatsOutDiscards OBJECT-TYPE
    SYNTAX     Counter64
    MAX-ACCESS read-only
    STATUS     current
    DESCRIPTION
           "This attribute reports the number of outbound packets
            which were internally discarded before transmission 
            (e.g. due to lack of buffering) for the downstream
            selected DEPI channel type NDF."
    ::= { docsRphyStatsRpdDsNdfPerfStatsEntry 3 }

docsRphyStatsRpdDsNdfPerfStatsOutErrors OBJECT-TYPE
    SYNTAX     Counter64
    MAX-ACCESS read-only
    STATUS     current
    DESCRIPTION
           "This attribute reports the number of outbound packets
            that could not be transmitted because of errors for 
            the downstream selected DEPI channel type NDF."
    ::= { docsRphyStatsRpdDsNdfPerfStatsEntry 4 }

docsRphyStatsRpdDsNdfPerfStatsOutPackets OBJECT-TYPE
    SYNTAX     Counter64
    MAX-ACCESS read-only
    STATUS     current
    DESCRIPTION
           "This attribute reports the number of outbound 
            packets successfully transmitted for 
            the downstream selected DEPI channel type NDF."
    ::= { docsRphyStatsRpdDsNdfPerfStatsEntry 5 }

docsRphyStatsRpdDsNdfPerfStatsRpdDsCounterDiscTime OBJECT-TYPE
    SYNTAX     DateAndTime
    MAX-ACCESS read-only
    STATUS     current
    DESCRIPTION
           "This attribute reports the date and time at which any one or more 
            of the counters in this group were created or last reset to zero. 
            If the RPD does not acquire time of day it can report an initial 
            CounterDiscontinuityTime of Jan 1 1970. If the value returned by 
            the RPD is the initial Epoch of Jan 1 1970, the CCAP Core can convert 
            this value to the real time of day based on a calculation using 
            the RPD's reported sysUpTime."
    ::= { docsRphyStatsRpdDsNdfPerfStatsEntry 6 }

-- ---------------------------------------------------------------------
-- Downstream OFDM PLC Performance Statistics
-- ---------------------------------------------------------------------

docsRphyStatsRpdDsOfdmPlcPerfStatsTable OBJECT-TYPE
        SYNTAX      SEQUENCE OF DocsRphyStatsRpdDsOfdmPlcPerfStatsEntry
        MAX-ACCESS  not-accessible
        STATUS      current
        DESCRIPTION
            "This table reports statistical counters for
             the PLC sub-channel of a downstream OFDM channel."
        ::= { docsRphyStatsRpdDsMibObjects 6 }


docsRphyStatsRpdDsOfdmPlcPerfStatsEntry OBJECT-TYPE
        SYNTAX     DocsRphyStatsRpdDsOfdmPlcPerfStatsEntry
        MAX-ACCESS not-accessible
        STATUS     current
        DESCRIPTION
            "The conceptual row of docsRphyStatsRpdDsOfdmPlcPerfStatsTable."
        AUGMENTS { docsRphyStatsRpdDsOfdmPerfStatsEntry }
        ::= { docsRphyStatsRpdDsOfdmPlcPerfStatsTable 1 }


DocsRphyStatsRpdDsOfdmPlcPerfStatsEntry ::= SEQUENCE
       {
       docsRphyStatsRpdDsOfdmPlcPerfStatsOutDiscards            Counter64,
       docsRphyStatsRpdDsOfdmPlcPerfStatsOutErrors              Counter64,
       docsRphyStatsRpdDsOfdmPlcPerfStatsOutPackets             Counter64,
       docsRphyStatsRpdDsOfdmPlcPerfStatsRpdDsCounterDiscTime   DateAndTime
       }

docsRphyStatsRpdDsOfdmPlcPerfStatsOutDiscards OBJECT-TYPE
    SYNTAX     Counter64
    MAX-ACCESS read-only
    STATUS     current
    DESCRIPTION
           "This attribute reports the number of outbound packets
            which were internally discarded before transmission 
            (e.g. due to lack of buffering) for the PLC sub-channel 
            of a downstream OFDM channel."
    ::= { docsRphyStatsRpdDsOfdmPlcPerfStatsEntry 1 }

docsRphyStatsRpdDsOfdmPlcPerfStatsOutErrors OBJECT-TYPE
    SYNTAX     Counter64
    MAX-ACCESS read-only
    STATUS     current
    DESCRIPTION
           "This attribute reports the number of outbound packets
            that could not be transmitted because of errors for
            the PLC sub-channel of a downstream OFDM channel."
    ::= { docsRphyStatsRpdDsOfdmPlcPerfStatsEntry 2 }

docsRphyStatsRpdDsOfdmPlcPerfStatsOutPackets OBJECT-TYPE
    SYNTAX     Counter64
    MAX-ACCESS read-only
    STATUS     current
    DESCRIPTION
           "This attribute reports the number of outbound 
            packets successfully transmitted for 
            the PLC sub-channel of a downstream OFDM channel."
    ::= { docsRphyStatsRpdDsOfdmPlcPerfStatsEntry 3 }

docsRphyStatsRpdDsOfdmPlcPerfStatsRpdDsCounterDiscTime OBJECT-TYPE
    SYNTAX     DateAndTime
    MAX-ACCESS read-only
    STATUS     current
    DESCRIPTION
           "This attribute reports the date and time at which any one or more 
            of the counters in this group were created or last reset to zero. 
            If the RPD does not acquire time of day it can report an initial 
            CounterDiscontinuityTime of Jan 1 1970. If the value returned by 
            the RPD is the initial Epoch of Jan 1 1970, the CCAP Core can convert 
            this value to the real time of day based on a calculation using 
            the RPD's reported sysUpTime."
    ::= { docsRphyStatsRpdDsOfdmPlcPerfStatsEntry 4 }

-- ---------------------------------------------------------------------
-- Downstream OFDM Profile Performance Statistics
-- ---------------------------------------------------------------------

docsRphyStatsRpdDsOfdmProfilePerfStatsTable OBJECT-TYPE
        SYNTAX      SEQUENCE OF DocsRphyStatsRpdDsOfdmProfilePerfStatsEntry
        MAX-ACCESS  not-accessible
        STATUS      current
        DESCRIPTION
            "This table reports statistical counters for profiles
             for a downstream OFDM channel."
        ::= { docsRphyStatsRpdDsMibObjects 7 }


docsRphyStatsRpdDsOfdmProfilePerfStatsEntry OBJECT-TYPE
        SYNTAX     DocsRphyStatsRpdDsOfdmProfilePerfStatsEntry
        MAX-ACCESS not-accessible
        STATUS     current
        DESCRIPTION
            "The conceptual row of docsRphyStatsRpdDsOfdmProfilePerfStatsTable."
        INDEX { docsRphyRpdDevInfoUniqueId, docsRphyStatsRpdDsOfdmPerfStatsCoreIfIndex,
                docsRphyStatsRpdDsOfdmPerfStatsDsRfPortIndex, 
                docsRphyStatsRpdDsOfdmProfilePerfStatsProfileIndex }
        ::= { docsRphyStatsRpdDsOfdmProfilePerfStatsTable 1 }


DocsRphyStatsRpdDsOfdmProfilePerfStatsEntry ::= SEQUENCE
       {
       docsRphyStatsRpdDsOfdmProfilePerfStatsProfileIndex    Unsigned32,
       docsRphyStatsRpdDsOfdmProfilePerfStatsOutCodewords    Counter64
       }

docsRphyStatsRpdDsOfdmProfilePerfStatsProfileIndex OBJECT-TYPE
    SYNTAX      Unsigned32 (0..15)
    MAX-ACCESS  not-accessible
    STATUS      current
    DESCRIPTION
            "This key attribute uniquely identifies a
             profile on the selected OFDM channel."
    ::= { docsRphyStatsRpdDsOfdmProfilePerfStatsEntry 1 }

docsRphyStatsRpdDsOfdmProfilePerfStatsOutCodewords OBJECT-TYPE
    SYNTAX     Counter64
    MAX-ACCESS read-only
    STATUS     current
    DESCRIPTION
           "This attribute reports the number of 
            transmitted LDPC codewords for the profile."
    ::= { docsRphyStatsRpdDsOfdmProfilePerfStatsEntry 2 }

-- ---------------------------------------------------------------------
-- Upstream OFDMA Performance Statistics
-- ---------------------------------------------------------------------

docsRphyStatsRpdUsOfdmaChanPerfStatsTable OBJECT-TYPE
        SYNTAX      SEQUENCE OF DocsRphyStatsRpdUsOfdmaChanPerfStatsEntry
        MAX-ACCESS  not-accessible
        STATUS      current
        DESCRIPTION
            "This table reports statistical counters for an
             upstream OFDMA channel."
        ::= { docsRphyStatsRpdUsMibObjects 1 }


docsRphyStatsRpdUsOfdmaChanPerfStatsEntry OBJECT-TYPE
        SYNTAX     DocsRphyStatsRpdUsOfdmaChanPerfStatsEntry
        MAX-ACCESS not-accessible
        STATUS     current
        DESCRIPTION
            "The conceptual row of docsRphyStatsRpdUsOfdmaChanPerfStatsTable."
        INDEX { docsRphyRpdDevInfoUniqueId, docsRphyStatsRpdUsOfdmaChanPerfStatsCoreIfIndex,
                docsRphyStatsRpdUsOfdmaChanPerfStatsUsRfPortIndex}
        ::= { docsRphyStatsRpdUsOfdmaChanPerfStatsTable 1 }


DocsRphyStatsRpdUsOfdmaChanPerfStatsEntry ::= SEQUENCE
       {
       docsRphyStatsRpdUsOfdmaChanPerfStatsCoreIfIndex            InterfaceIndex,
       docsRphyStatsRpdUsOfdmaChanPerfStatsUsRfPortIndex          Unsigned32,
       docsRphyStatsRpdUsOfdmaChanPerfStatsProbeGrants            Counter64,
       docsRphyStatsRpdUsOfdmaChanPerfStatsHcsErrors	          Counter64,
       docsRphyStatsRpdUsOfdmaChanPerfStatsLateMaps		  Counter64,
       docsRphyStatsRpdUsOfdmaChanPerfStatsIllegalMaps		  Counter64,
       docsRphyStatsRpdUsOfdmaChanPerfStatsDiscardedRequests      Counter64,
       docsRphyStatsRpdUsOfdmaChanPerfStatsRpdUsCounterDiscTime   DateAndTime
       }

docsRphyStatsRpdUsOfdmaChanPerfStatsCoreIfIndex OBJECT-TYPE
    SYNTAX      InterfaceIndex
    MAX-ACCESS  not-accessible
    STATUS      current
    DESCRIPTION
            "This key attribute uniquely identifies 
             the selected OFDMA channel."
    ::= { docsRphyStatsRpdUsOfdmaChanPerfStatsEntry 1 }

docsRphyStatsRpdUsOfdmaChanPerfStatsUsRfPortIndex OBJECT-TYPE
    SYNTAX      Unsigned32 (0..253)
    MAX-ACCESS  not-accessible
    STATUS      current
    DESCRIPTION
            "This key attribute uniquely identifies the 
             selected CCAP Core upstream RF port. "
    ::= { docsRphyStatsRpdUsOfdmaChanPerfStatsEntry 2 }

docsRphyStatsRpdUsOfdmaChanPerfStatsProbeGrants OBJECT-TYPE
    SYNTAX     Counter64
    MAX-ACCESS read-only
    STATUS     current
    DESCRIPTION
           "This attribute reports the number of
            Probe Grants on the upstream OFDMA channel."
    ::= { docsRphyStatsRpdUsOfdmaChanPerfStatsEntry 3 }

docsRphyStatsRpdUsOfdmaChanPerfStatsHcsErrors OBJECT-TYPE
    SYNTAX     Counter64
    MAX-ACCESS read-only
    STATUS     current
    DESCRIPTION
           "This attribute reports the number of bursts with detected HCS error 
            in the DOCSIS header for the upstream OFDMA channel."
    ::= { docsRphyStatsRpdUsOfdmaChanPerfStatsEntry 4 }

docsRphyStatsRpdUsOfdmaChanPerfStatsLateMaps OBJECT-TYPE
    SYNTAX     Counter64
    MAX-ACCESS read-only
    STATUS     current
    DESCRIPTION
           "This attribute reports the number of late MAP messages
            for the upstream OFDMA channel. "
    ::= { docsRphyStatsRpdUsOfdmaChanPerfStatsEntry 5 }

docsRphyStatsRpdUsOfdmaChanPerfStatsIllegalMaps OBJECT-TYPE
    SYNTAX     Counter64
    MAX-ACCESS read-only
    STATUS     current
    DESCRIPTION
           "This attribute reports the number MAP messages 
            with detected errors, other than late error,
            for the upstream OFDMA channel."
    ::= { docsRphyStatsRpdUsOfdmaChanPerfStatsEntry 6 }

docsRphyStatsRpdUsOfdmaChanPerfStatsDiscardedRequests OBJECT-TYPE
    SYNTAX     Counter64
    MAX-ACCESS read-only
    STATUS     current
    DESCRIPTION
           "This attribute reports the number of bandwidth requests
            that were discarded by the RPD
            for the upstream OFDMA channel."
    ::= { docsRphyStatsRpdUsOfdmaChanPerfStatsEntry 7 }


docsRphyStatsRpdUsOfdmaChanPerfStatsRpdUsCounterDiscTime OBJECT-TYPE
    SYNTAX     DateAndTime
    MAX-ACCESS read-only
    STATUS     current
    DESCRIPTION
           "This attribute reports the date and time at which any one or more 
            of the counters in this group were created or last reset to zero. 
            If the RPD does not acquire time of day it can report an initial 
            CounterDiscontinuityTime of Jan 1 1970. If the value returned by 
            the RPD is the initial Epoch of Jan 1 1970, the CCAP Core can convert 
            this value to the real time of day based on a calculation using 
            the RPD's reported sysUpTime."
    ::= { docsRphyStatsRpdUsOfdmaChanPerfStatsEntry 8 }

-- ---------------------------------------------------------------------
-- Upstream SC-QAM Performance Statistics
-- ---------------------------------------------------------------------

docsRphyStatsRpdUsScQamChanPerfStatsTable OBJECT-TYPE
        SYNTAX      SEQUENCE OF DocsRphyStatsRpdUsScQamChanPerfStatsEntry
        MAX-ACCESS  not-accessible
        STATUS      current
        DESCRIPTION
            "This table reports statistical counters for an
             upstream SC-QAM channel."
        ::= { docsRphyStatsRpdUsMibObjects 2 }


docsRphyStatsRpdUsScQamChanPerfStatsEntry OBJECT-TYPE
        SYNTAX     DocsRphyStatsRpdUsScQamChanPerfStatsEntry
        MAX-ACCESS not-accessible
        STATUS     current
        DESCRIPTION
            "The conceptual row of docsRphyStatsRpdUsScQamChanPerfStatsTable."
        INDEX { docsRphyRpdDevInfoUniqueId, docsRphyStatsRpdUsScQamChanPerfStatsCoreIfIndex,
                docsRphyStatsRpdUsScQamChanPerfStatsUsRfPortIndex }
        ::= { docsRphyStatsRpdUsScQamChanPerfStatsTable 1 }


DocsRphyStatsRpdUsScQamChanPerfStatsEntry ::= SEQUENCE
       {
       docsRphyStatsRpdUsScQamChanPerfStatsCoreIfIndex            InterfaceIndex,
       docsRphyStatsRpdUsScQamChanPerfStatsUsRfPortIndex          Unsigned32,
       docsRphyStatsRpdUsScQamChanPerfStatsChanSnr                Unsigned32,
       docsRphyStatsRpdUsScQamChanPerfStatsHcsErrors	          Counter64,
       docsRphyStatsRpdUsScQamChanPerfStatsLateMaps		  Counter64,
       docsRphyStatsRpdUsScQamChanPerfStatsIllegalMaps		  Counter64,
       docsRphyStatsRpdUsScQamChanPerfStatsDiscardedRequests      Counter64,
       docsRphyStatsRpdUsScQamChanPerfStatsRpdUsCounterDiscTime   DateAndTime
       }

docsRphyStatsRpdUsScQamChanPerfStatsCoreIfIndex OBJECT-TYPE
    SYNTAX      InterfaceIndex
    MAX-ACCESS  not-accessible
    STATUS      current
    DESCRIPTION
            "This key attribute uniquely identifies 
             the selected SC-QAM channel."
    ::= { docsRphyStatsRpdUsScQamChanPerfStatsEntry 1 }

docsRphyStatsRpdUsScQamChanPerfStatsUsRfPortIndex OBJECT-TYPE
    SYNTAX      Unsigned32 (0..253)
    MAX-ACCESS  not-accessible
    STATUS      current
    DESCRIPTION
            "This key attribute uniquely identifies the 
             selected CCAP Core upstream RF port."
    ::= { docsRphyStatsRpdUsScQamChanPerfStatsEntry 2 }

docsRphyStatsRpdUsScQamChanPerfStatsChanSnr OBJECT-TYPE
    SYNTAX     Unsigned32 (0..65535)
    UNITS      "TenthdB"
    MAX-ACCESS read-only
    STATUS     current
    DESCRIPTION
           "This attribute reports the average SNR for
            the selected SC-QAM channel."
    ::= { docsRphyStatsRpdUsScQamChanPerfStatsEntry 3 }

docsRphyStatsRpdUsScQamChanPerfStatsHcsErrors OBJECT-TYPE
    SYNTAX     Counter64
    MAX-ACCESS read-only
    STATUS     current
    DESCRIPTION
           "This attribute reports the number of bursts with detected HCS error 
            in the DOCSIS header for the upstream SC-QAM channel."
    ::= { docsRphyStatsRpdUsScQamChanPerfStatsEntry 4 }

docsRphyStatsRpdUsScQamChanPerfStatsLateMaps OBJECT-TYPE
    SYNTAX     Counter64
    MAX-ACCESS read-only
    STATUS     current
    DESCRIPTION
           "This attribute reports the number of late MAP messages
            for the upstream SC-QAM channel. "
    ::= { docsRphyStatsRpdUsScQamChanPerfStatsEntry 5 }

docsRphyStatsRpdUsScQamChanPerfStatsIllegalMaps OBJECT-TYPE
    SYNTAX     Counter64
    MAX-ACCESS read-only
    STATUS     current
    DESCRIPTION
           "This attribute reports the number MAP messages 
            with detected errors, other than late error,
            for the upstream SC-QAM channel."
    ::= { docsRphyStatsRpdUsScQamChanPerfStatsEntry 6 }

docsRphyStatsRpdUsScQamChanPerfStatsDiscardedRequests OBJECT-TYPE
    SYNTAX     Counter64
    MAX-ACCESS read-only
    STATUS     current
    DESCRIPTION
           "This attribute reports the number of bandwidth requests
            that were discarded by the RPD
            for the upstream SC-QAM channel."
    ::= { docsRphyStatsRpdUsScQamChanPerfStatsEntry 7 }


docsRphyStatsRpdUsScQamChanPerfStatsRpdUsCounterDiscTime OBJECT-TYPE
    SYNTAX     DateAndTime
    MAX-ACCESS read-only
    STATUS     current
    DESCRIPTION
           "This attribute reports the date and time at which any one or more 
            of the counters in this group were created or last reset to zero. 
            If the RPD does not acquire time of day it can report an initial 
            CounterDiscontinuityTime of Jan 1 1970. If the value returned by 
            the RPD is the initial Epoch of Jan 1 1970, the CCAP Core can convert 
            this value to the real time of day based on a calculation using 
            the RPD's reported sysUpTime."
    ::= { docsRphyStatsRpdUsScQamChanPerfStatsEntry 8 }

-- ---------------------------------------------------------------------
-- Upstream OFDMA LOW IUC Performance Statistics
-- ---------------------------------------------------------------------

docsRphyStatsRpdUsOfdmaLowIucPerfStatsTable OBJECT-TYPE
        SYNTAX      SEQUENCE OF DocsRphyStatsRpdUsOfdmaLowIucPerfStatsEntry
        MAX-ACCESS  not-accessible
        STATUS      current
        DESCRIPTION
            "This table reports statistical counters for IUCs 1, 2 and 3
             of an upstream OFDMA channel."
        ::= { docsRphyStatsRpdUsMibObjects 3 }


docsRphyStatsRpdUsOfdmaLowIucPerfStatsEntry OBJECT-TYPE
        SYNTAX     DocsRphyStatsRpdUsOfdmaLowIucPerfStatsEntry
        MAX-ACCESS not-accessible
        STATUS     current
        DESCRIPTION
            "The conceptual row of docsRphyStatsRpdUsOfdmaLowIucPerfStatsTable."
        INDEX { docsRphyRpdDevInfoUniqueId, docsRphyStatsRpdUsOfdmaChanPerfStatsCoreIfIndex,
                docsRphyStatsRpdUsOfdmaChanPerfStatsUsRfPortIndex,
                docsRphyStatsRpdUsOfdmaLowIucPerfStatsUsIuc}
        ::= { docsRphyStatsRpdUsOfdmaLowIucPerfStatsTable 1 }


DocsRphyStatsRpdUsOfdmaLowIucPerfStatsEntry ::= SEQUENCE
       {
       	docsRphyStatsRpdUsOfdmaLowIucPerfStatsUsIuc			Unsigned32,
	docsRphyStatsRpdUsOfdmaLowIucPerfStatsNumPredecodePass		Counter64,
	docsRphyStatsRpdUsOfdmaLowIucPerfStatsNumPostdecodePass		Counter64,
	docsRphyStatsRpdUsOfdmaLowIucPerfStatsNumPostdecodeFail		Counter64,
	docsRphyStatsRpdUsOfdmaLowIucPerfStatsUnicastOpportunities	Counter64,
	docsRphyStatsRpdUsOfdmaLowIucPerfStatsUnicastOpCollisions	Counter64,	
	docsRphyStatsRpdUsOfdmaLowIucPerfStatsUnicastOpNoEnergy		Counter64,
	docsRphyStatsRpdUsOfdmaLowIucPerfStatsUnicastOpErrors		Counter64,
	docsRphyStatsRpdUsOfdmaLowIucPerfStatsMulticastOpportunities	Counter64,
	docsRphyStatsRpdUsOfdmaLowIucPerfStatsMulticastOpCollisions	Counter64,
	docsRphyStatsRpdUsOfdmaLowIucPerfStatsMulticastOpNoEnergy	Counter64,
	docsRphyStatsRpdUsOfdmaLowIucPerfStatsMulticastOpErrors		Counter64
       }

docsRphyStatsRpdUsOfdmaLowIucPerfStatsUsIuc OBJECT-TYPE
    SYNTAX      Unsigned32 (0..255)
    MAX-ACCESS  not-accessible
    STATUS      current
    DESCRIPTION
            "This key attribute provides an index in the form of 
             the IUC for which the statistical counters will 
             be stored."
    ::= { docsRphyStatsRpdUsOfdmaLowIucPerfStatsEntry 1 }

docsRphyStatsRpdUsOfdmaLowIucPerfStatsNumPredecodePass OBJECT-TYPE
    SYNTAX     Counter64
    MAX-ACCESS read-only
    STATUS     current
    DESCRIPTION
           "This attribute reports the number of LDPC codewords
            for the selected IUC that passed pre-decode syndrome check."
    ::= { docsRphyStatsRpdUsOfdmaLowIucPerfStatsEntry 2 }

docsRphyStatsRpdUsOfdmaLowIucPerfStatsNumPostdecodePass OBJECT-TYPE
    SYNTAX     Counter64
    MAX-ACCESS read-only
    STATUS     current
    DESCRIPTION
           "This attribute reports the number of LDPC codewords 
            for the selected IUC that passed post-decode syndrome check."
    ::= { docsRphyStatsRpdUsOfdmaLowIucPerfStatsEntry 3 }

docsRphyStatsRpdUsOfdmaLowIucPerfStatsNumPostdecodeFail OBJECT-TYPE
    SYNTAX     Counter64
    MAX-ACCESS read-only
    STATUS     current
    DESCRIPTION
           "This attribute reports the number of received LDPC codewords
            for the selected IUC that failed post-decode syndrome check."
    ::= { docsRphyStatsRpdUsOfdmaLowIucPerfStatsEntry 4 }

docsRphyStatsRpdUsOfdmaLowIucPerfStatsUnicastOpportunities OBJECT-TYPE
    SYNTAX     Counter64
    MAX-ACCESS read-only
    STATUS     current
    DESCRIPTION
           "This attribute reports the total number of unicast transmission
            opportunities for the selected IUC. Unicast opportunities are 
            counted for SIDs in range 0x0001-0x3dff."
    ::= { docsRphyStatsRpdUsOfdmaLowIucPerfStatsEntry 5 }

docsRphyStatsRpdUsOfdmaLowIucPerfStatsUnicastOpCollisions OBJECT-TYPE
    SYNTAX     Counter64
    MAX-ACCESS read-only
    STATUS     current
    DESCRIPTION
           "This attribute reports the total number of detected collisions
            on unicast transmission opportunities for the selected IUC."
    ::= { docsRphyStatsRpdUsOfdmaLowIucPerfStatsEntry 6 }

docsRphyStatsRpdUsOfdmaLowIucPerfStatsUnicastOpNoEnergy OBJECT-TYPE
    SYNTAX     Counter64
    MAX-ACCESS read-only
    STATUS     current
    DESCRIPTION
           "This attribute reports the number of unicast transmission
            opportunities with no energy for the selected IUC."
    ::= { docsRphyStatsRpdUsOfdmaLowIucPerfStatsEntry 7 }

docsRphyStatsRpdUsOfdmaLowIucPerfStatsUnicastOpErrors OBJECT-TYPE
    SYNTAX     Counter64
    MAX-ACCESS read-only
    STATUS     current
    DESCRIPTION
           "This attribute reports the number of unicast transmission
            opportunities with detected PHY errors for the selected IUC."
    ::= { docsRphyStatsRpdUsOfdmaLowIucPerfStatsEntry 8 }

docsRphyStatsRpdUsOfdmaLowIucPerfStatsMulticastOpportunities OBJECT-TYPE
    SYNTAX     Counter64
    MAX-ACCESS read-only
    STATUS     current
    DESCRIPTION
           "This attribute reports the total number of multicast transmission
            opportunities for the selected IUC. Multicast opportunities are 
            counted for SIDs in range 0x0001-0x3dff."
    ::= { docsRphyStatsRpdUsOfdmaLowIucPerfStatsEntry 9 }

docsRphyStatsRpdUsOfdmaLowIucPerfStatsMulticastOpCollisions OBJECT-TYPE
    SYNTAX     Counter64
    MAX-ACCESS read-only
    STATUS     current
    DESCRIPTION
           "This attribute reports the total number of detected collisions
            on multicast transmission opportunities for the selected IUC."
    ::= { docsRphyStatsRpdUsOfdmaLowIucPerfStatsEntry 10 }

docsRphyStatsRpdUsOfdmaLowIucPerfStatsMulticastOpNoEnergy OBJECT-TYPE
    SYNTAX     Counter64
    MAX-ACCESS read-only
    STATUS     current
    DESCRIPTION
           "This attribute reports the number of multicast transmission
            opportunities with no energy for the selected IUC."
    ::= { docsRphyStatsRpdUsOfdmaLowIucPerfStatsEntry 11 }

docsRphyStatsRpdUsOfdmaLowIucPerfStatsMulticastOpErrors OBJECT-TYPE
    SYNTAX     Counter64
    MAX-ACCESS read-only
    STATUS     current
    DESCRIPTION
           "This attribute reports the number of multicast transmission
            opportunities with detected PHY errors for the selected IUC."
    ::= { docsRphyStatsRpdUsOfdmaLowIucPerfStatsEntry 12 }

-- ---------------------------------------------------------------------
-- Upstream OFDMA HIGH IUC Performance Statistics
-- ---------------------------------------------------------------------

docsRphyStatsRpdUsOfdmaHighIucPerfStatsTable OBJECT-TYPE
        SYNTAX      SEQUENCE OF DocsRphyStatsRpdUsOfdmaHighIucPerfStatsEntry
        MAX-ACCESS  not-accessible
        STATUS      current
        DESCRIPTION
            "This table reports reports the statistical counters for
             IUCs 4, 5, 6, 9, 10, 11, 12 and 13 of an OFDMA channel."
        ::= { docsRphyStatsRpdUsMibObjects 4 }


docsRphyStatsRpdUsOfdmaHighIucPerfStatsEntry OBJECT-TYPE
        SYNTAX     DocsRphyStatsRpdUsOfdmaHighIucPerfStatsEntry
        MAX-ACCESS not-accessible
        STATUS     current
        DESCRIPTION
            "The conceptual row of docsRphyStatsRpdUsOfdmaHighIucPerfStatsTable."
        INDEX { docsRphyRpdDevInfoUniqueId, docsRphyStatsRpdUsOfdmaChanPerfStatsCoreIfIndex,
                docsRphyStatsRpdUsOfdmaChanPerfStatsUsRfPortIndex,   
                docsRphyStatsRpdUsOfdmaHighIucPerfStatsUsIuc}
        ::= { docsRphyStatsRpdUsOfdmaHighIucPerfStatsTable 1 }


DocsRphyStatsRpdUsOfdmaHighIucPerfStatsEntry ::= SEQUENCE
       {
       	docsRphyStatsRpdUsOfdmaHighIucPerfStatsUsIuc			Unsigned32,
        docsRphyStatsRpdUsOfdmaHighIucPerfStatsAverageMer               Counter64,
	docsRphyStatsRpdUsOfdmaHighIucPerfStatsNumPredecodePass		Counter64,
	docsRphyStatsRpdUsOfdmaHighIucPerfStatsNumPostdecodePass	Counter64,
	docsRphyStatsRpdUsOfdmaHighIucPerfStatsNumPostdecodeFail	Counter64,
	docsRphyStatsRpdUsOfdmaHighIucPerfStatsScheduledGrants		Counter64,
        docsRphyStatsRpdUsOfdmaHighIucPerfStatsNoEnergyBursts		Counter64,
        docsRphyStatsRpdUsOfdmaHighIucPerfStatsNoPreambleBursts		Counter64,
        docsRphyStatsRpdUsOfdmaHighIucPerfStatsErrorBursts		Counter64
       }

docsRphyStatsRpdUsOfdmaHighIucPerfStatsUsIuc OBJECT-TYPE
    SYNTAX      Unsigned32 (0..255)
    MAX-ACCESS  not-accessible
    STATUS      current
    DESCRIPTION
            "This key attribute provides an index in the form of 
             the IUC for which the statistical counters will 
             be stored."
    ::= { docsRphyStatsRpdUsOfdmaHighIucPerfStatsEntry 1 }

docsRphyStatsRpdUsOfdmaHighIucPerfStatsAverageMer OBJECT-TYPE
    SYNTAX     Counter64
    MAX-ACCESS read-only
    STATUS     current
    DESCRIPTION
           "This attribute reports the average MER value 
            for the selected IUC."
    ::= { docsRphyStatsRpdUsOfdmaHighIucPerfStatsEntry 2 }

docsRphyStatsRpdUsOfdmaHighIucPerfStatsNumPredecodePass OBJECT-TYPE
    SYNTAX     Counter64
    MAX-ACCESS read-only
    STATUS     current
    DESCRIPTION
           "This attribute reports the number of LDPC codewords
            for the selected IUC that passed pre-decode syndrome check."
    ::= { docsRphyStatsRpdUsOfdmaHighIucPerfStatsEntry 3 }

docsRphyStatsRpdUsOfdmaHighIucPerfStatsNumPostdecodePass OBJECT-TYPE
    SYNTAX     Counter64
    MAX-ACCESS read-only
    STATUS     current
    DESCRIPTION
           "This attribute reports the number of LDPC codewords 
            for the selected IUC that passed post-decode syndrome check."
    ::= { docsRphyStatsRpdUsOfdmaHighIucPerfStatsEntry 4 }

docsRphyStatsRpdUsOfdmaHighIucPerfStatsNumPostdecodeFail OBJECT-TYPE
    SYNTAX     Counter64
    MAX-ACCESS read-only
    STATUS     current
    DESCRIPTION
           "This attribute reports the number of received LDPC codewords
            for the selected IUC that failed post-decode syndrome check."
    ::= { docsRphyStatsRpdUsOfdmaHighIucPerfStatsEntry 5 }

docsRphyStatsRpdUsOfdmaHighIucPerfStatsScheduledGrants OBJECT-TYPE
    SYNTAX     Counter64
    MAX-ACCESS read-only
    STATUS     current
    DESCRIPTION
           "This attribute reports the number of scheduled
            grants for the selected IUC."
    ::= { docsRphyStatsRpdUsOfdmaHighIucPerfStatsEntry 6 }

docsRphyStatsRpdUsOfdmaHighIucPerfStatsNoEnergyBursts OBJECT-TYPE
    SYNTAX     Counter64
    MAX-ACCESS read-only
    STATUS     current
    DESCRIPTION
           "This attribute reports the number of bursts
            with no energy detected for the selected IUC."
    ::= { docsRphyStatsRpdUsOfdmaHighIucPerfStatsEntry 7 }

docsRphyStatsRpdUsOfdmaHighIucPerfStatsNoPreambleBursts OBJECT-TYPE
    SYNTAX     Counter64
    MAX-ACCESS read-only
    STATUS     current
    DESCRIPTION
           "This attribute reports the number of bursts 
            no preamble detected for the selected IUC."
    ::= { docsRphyStatsRpdUsOfdmaHighIucPerfStatsEntry 8 }

docsRphyStatsRpdUsOfdmaHighIucPerfStatsErrorBursts OBJECT-TYPE
    SYNTAX     Counter64
    MAX-ACCESS read-only
    STATUS     current
    DESCRIPTION
           "This attribute reports the number of bursts received
            with errors other than 'no energy' or 'no preamble' 
            for the selected IUC."
    ::= { docsRphyStatsRpdUsOfdmaHighIucPerfStatsEntry 9 }

-- ---------------------------------------------------------------------
-- Upstream SC-QAM LOW IUC Performance Statistics
-- ---------------------------------------------------------------------

docsRphyStatsRpdUsScQamLowIucPerfStatsTable OBJECT-TYPE
        SYNTAX      SEQUENCE OF DocsRphyStatsRpdUsScQamLowIucPerfStatsEntry
        MAX-ACCESS  not-accessible
        STATUS      current
        DESCRIPTION
            "This table reports statistical counters for IUCs 1, 2 and 3
             of an upstream SC-QAM channel."
        ::= { docsRphyStatsRpdUsMibObjects 5 }


docsRphyStatsRpdUsScQamLowIucPerfStatsEntry OBJECT-TYPE
        SYNTAX     DocsRphyStatsRpdUsScQamLowIucPerfStatsEntry
        MAX-ACCESS not-accessible
        STATUS     current
        DESCRIPTION
            "The conceptual row of docsRphyStatsRpdUsScQamLowIucPerfStatsTable."
        INDEX { docsRphyRpdDevInfoUniqueId, docsRphyStatsRpdUsScQamChanPerfStatsCoreIfIndex,
                docsRphyStatsRpdUsScQamChanPerfStatsUsRfPortIndex,
                docsRphyStatsRpdUsScQamLowIucPerfStatsUsIuc}
        ::= { docsRphyStatsRpdUsScQamLowIucPerfStatsTable 1 }


DocsRphyStatsRpdUsScQamLowIucPerfStatsEntry ::= SEQUENCE
       {
       	docsRphyStatsRpdUsScQamLowIucPerfStatsUsIuc			Unsigned32,
	docsRphyStatsRpdUsScQamLowIucPerfStatsGoodFecCw			Counter64,
	docsRphyStatsRpdUsScQamLowIucPerfStatsCorrectedFecCw		Counter64,
	docsRphyStatsRpdUsScQamLowIucPerfStatsUncorrectedFecCw		Counter64,
	docsRphyStatsRpdUsScQamLowIucPerfStatsUnicastOpportunities	Counter64,
	docsRphyStatsRpdUsScQamLowIucPerfStatsUnicastOpCollisions	Counter64,	
	docsRphyStatsRpdUsScQamLowIucPerfStatsUnicastOpNoEnergy		Counter64,
	docsRphyStatsRpdUsScQamLowIucPerfStatsUnicastOpErrors		Counter64,
	docsRphyStatsRpdUsScQamLowIucPerfStatsMulticastOpportunities	Counter64,
	docsRphyStatsRpdUsScQamLowIucPerfStatsMulticastOpCollisions	Counter64,
	docsRphyStatsRpdUsScQamLowIucPerfStatsMulticastOpNoEnergy	Counter64,
	docsRphyStatsRpdUsScQamLowIucPerfStatsMulticastOpErrors		Counter64
       }

docsRphyStatsRpdUsScQamLowIucPerfStatsUsIuc OBJECT-TYPE
    SYNTAX      Unsigned32 (0..255)
    MAX-ACCESS  not-accessible
    STATUS      current
    DESCRIPTION
            "This key attribute provides an index in the form of 
             the IUC for which the statistical counters will 
             be stored."
    ::= { docsRphyStatsRpdUsScQamLowIucPerfStatsEntry 1 }

docsRphyStatsRpdUsScQamLowIucPerfStatsGoodFecCw OBJECT-TYPE
    SYNTAX     Counter64
    MAX-ACCESS read-only
    STATUS     current
    DESCRIPTION
           "This attribute reports the number of good FEC 
            codewords for the selected IUC."
    ::= { docsRphyStatsRpdUsScQamLowIucPerfStatsEntry 2 }

docsRphyStatsRpdUsScQamLowIucPerfStatsCorrectedFecCw OBJECT-TYPE
    SYNTAX     Counter64
    MAX-ACCESS read-only
    STATUS     current
    DESCRIPTION
           "This attribute reports the number of corrected
            FEC codewords for the selected IUC. "
    ::= { docsRphyStatsRpdUsScQamLowIucPerfStatsEntry 3 }

docsRphyStatsRpdUsScQamLowIucPerfStatsUncorrectedFecCw OBJECT-TYPE
    SYNTAX     Counter64
    MAX-ACCESS read-only
    STATUS     current
    DESCRIPTION
           "This attribute reports the number of uncorrected
            FEC codewords for the selected IUC."
    ::= { docsRphyStatsRpdUsScQamLowIucPerfStatsEntry 4 }

docsRphyStatsRpdUsScQamLowIucPerfStatsUnicastOpportunities OBJECT-TYPE
    SYNTAX     Counter64
    MAX-ACCESS read-only
    STATUS     current
    DESCRIPTION
           "This attribute reports the total number of unicast transmission
            opportunities for the selected IUC. Unicast opportunities are 
            counted for SIDs in range 0x0001-0x3dff."
    ::= { docsRphyStatsRpdUsScQamLowIucPerfStatsEntry 5 }

docsRphyStatsRpdUsScQamLowIucPerfStatsUnicastOpCollisions OBJECT-TYPE
    SYNTAX     Counter64
    MAX-ACCESS read-only
    STATUS     current
    DESCRIPTION
           "This attribute reports the total number of detected collisions
            on unicast transmission opportunities for the selected IUC."
    ::= { docsRphyStatsRpdUsScQamLowIucPerfStatsEntry 6 }

docsRphyStatsRpdUsScQamLowIucPerfStatsUnicastOpNoEnergy OBJECT-TYPE
    SYNTAX     Counter64
    MAX-ACCESS read-only
    STATUS     current
    DESCRIPTION
           "This attribute reports the number of unicast transmission
            opportunities with no energy for the selected IUC."
    ::= { docsRphyStatsRpdUsScQamLowIucPerfStatsEntry 7 }

docsRphyStatsRpdUsScQamLowIucPerfStatsUnicastOpErrors OBJECT-TYPE
    SYNTAX     Counter64
    MAX-ACCESS read-only
    STATUS     current
    DESCRIPTION
           "This attribute reports the number of unicast transmission
            opportunities with detected PHY errors for the selected IUC."
    ::= { docsRphyStatsRpdUsScQamLowIucPerfStatsEntry 8 }

docsRphyStatsRpdUsScQamLowIucPerfStatsMulticastOpportunities OBJECT-TYPE
    SYNTAX     Counter64
    MAX-ACCESS read-only
    STATUS     current
    DESCRIPTION
           "This attribute reports the total number of multicast transmission
            opportunities for the selected IUC. Multicast opportunities are 
            counted for SIDs in range 0x0001-0x3dff."
    ::= { docsRphyStatsRpdUsScQamLowIucPerfStatsEntry 9 }

docsRphyStatsRpdUsScQamLowIucPerfStatsMulticastOpCollisions OBJECT-TYPE
    SYNTAX     Counter64
    MAX-ACCESS read-only
    STATUS     current
    DESCRIPTION
           "This attribute reports the total number of detected collisions
            on multicast transmission opportunities for the selected IUC."
    ::= { docsRphyStatsRpdUsScQamLowIucPerfStatsEntry 10 }

docsRphyStatsRpdUsScQamLowIucPerfStatsMulticastOpNoEnergy OBJECT-TYPE
    SYNTAX     Counter64
    MAX-ACCESS read-only
    STATUS     current
    DESCRIPTION
           "This attribute reports the number of multicast transmission
            opportunities with no energy for the selected IUC."
    ::= { docsRphyStatsRpdUsScQamLowIucPerfStatsEntry 11 }

docsRphyStatsRpdUsScQamLowIucPerfStatsMulticastOpErrors OBJECT-TYPE
    SYNTAX     Counter64
    MAX-ACCESS read-only
    STATUS     current
    DESCRIPTION
           "This attribute reports the number of multicast transmission
            opportunities with detected PHY errors for the selected IUC."
    ::= { docsRphyStatsRpdUsScQamLowIucPerfStatsEntry 12 }

-- ---------------------------------------------------------------------
-- Upstream SC-QAM HIGH IUC Performance Statistics
-- ---------------------------------------------------------------------

docsRphyStatsRpdUsScQamHighIucPerfStatsTable OBJECT-TYPE
        SYNTAX      SEQUENCE OF DocsRphyStatsRpdUsScQamHighIucPerfStatsEntry
        MAX-ACCESS  not-accessible
        STATUS      current
        DESCRIPTION
            "This table reports reports the statistical counters for
             IUCs 4, 5, 6, 9, 10, 11, 12 and 13 of an upstream 
             SC-QAM channel."
        ::= { docsRphyStatsRpdUsMibObjects 6 }


docsRphyStatsRpdUsScQamHighIucPerfStatsEntry OBJECT-TYPE
        SYNTAX     DocsRphyStatsRpdUsScQamHighIucPerfStatsEntry
        MAX-ACCESS not-accessible
        STATUS     current
        DESCRIPTION
            "The conceptual row of docsRphyStatsRpdUsScQamHighIucPerfStatsTable."
        INDEX { docsRphyRpdDevInfoUniqueId, docsRphyStatsRpdUsScQamChanPerfStatsCoreIfIndex,
                docsRphyStatsRpdUsScQamChanPerfStatsUsRfPortIndex,
                docsRphyStatsRpdUsScQamHighIucPerfStatsUsIuc}
        ::= { docsRphyStatsRpdUsScQamHighIucPerfStatsTable 1 }


DocsRphyStatsRpdUsScQamHighIucPerfStatsEntry ::= SEQUENCE
       {
       	docsRphyStatsRpdUsScQamHighIucPerfStatsUsIuc			Unsigned32,
	docsRphyStatsRpdUsScQamHighIucPerfStatsGoodFecCw		Counter64,
	docsRphyStatsRpdUsScQamHighIucPerfStatsCorrectedFecCw		Counter64,
	docsRphyStatsRpdUsScQamHighIucPerfStatsUncorrectedFecCw		Counter64,
	docsRphyStatsRpdUsScQamHighIucPerfStatsScheduledGrants		Counter64,
        docsRphyStatsRpdUsScQamHighIucPerfStatsNoEnergyBursts		Counter64,
        docsRphyStatsRpdUsScQamHighIucPerfStatsNoPreambleBursts		Counter64,
        docsRphyStatsRpdUsScQamHighIucPerfStatsErrorBursts		Counter64
       }

docsRphyStatsRpdUsScQamHighIucPerfStatsUsIuc OBJECT-TYPE
    SYNTAX      Unsigned32 (0..255)
    MAX-ACCESS  not-accessible
    STATUS      current
    DESCRIPTION
            "This key attribute provides an index in the form of 
             the IUC for which the statistical counters will 
             be stored."
    ::= { docsRphyStatsRpdUsScQamHighIucPerfStatsEntry 1 }

docsRphyStatsRpdUsScQamHighIucPerfStatsGoodFecCw OBJECT-TYPE
    SYNTAX     Counter64
    MAX-ACCESS read-only
    STATUS     current
    DESCRIPTION
           "This attribute reports the number of good FEC 
            codewords for the selected IUC."
    ::= { docsRphyStatsRpdUsScQamHighIucPerfStatsEntry 2 }

docsRphyStatsRpdUsScQamHighIucPerfStatsCorrectedFecCw OBJECT-TYPE
    SYNTAX     Counter64
    MAX-ACCESS read-only
    STATUS     current
    DESCRIPTION
           "This attribute reports the number of corrected
            FEC codewords for the selected IUC. "
    ::= { docsRphyStatsRpdUsScQamHighIucPerfStatsEntry 3 }

docsRphyStatsRpdUsScQamHighIucPerfStatsUncorrectedFecCw OBJECT-TYPE
    SYNTAX     Counter64
    MAX-ACCESS read-only
    STATUS     current
    DESCRIPTION
           "This attribute reports the number of uncorrected
            FEC codewords for the selected IUC."
    ::= { docsRphyStatsRpdUsScQamHighIucPerfStatsEntry 4 }

docsRphyStatsRpdUsScQamHighIucPerfStatsScheduledGrants OBJECT-TYPE
    SYNTAX     Counter64
    MAX-ACCESS read-only
    STATUS     current
    DESCRIPTION
           "This attribute reports the number of scheduled
            grants for the selected IUC."
    ::= { docsRphyStatsRpdUsScQamHighIucPerfStatsEntry 5 }

docsRphyStatsRpdUsScQamHighIucPerfStatsNoEnergyBursts OBJECT-TYPE
    SYNTAX     Counter64
    MAX-ACCESS read-only
    STATUS     current
    DESCRIPTION
           "This attribute reports the number of bursts
            with no energy detected for the selected IUC."
    ::= { docsRphyStatsRpdUsScQamHighIucPerfStatsEntry 6 }

docsRphyStatsRpdUsScQamHighIucPerfStatsNoPreambleBursts OBJECT-TYPE
    SYNTAX     Counter64
    MAX-ACCESS read-only
    STATUS     current
    DESCRIPTION
           "This attribute reports the number of bursts 
            no preamble detected for the selected IUC."
    ::= { docsRphyStatsRpdUsScQamHighIucPerfStatsEntry 7 }

docsRphyStatsRpdUsScQamHighIucPerfStatsErrorBursts OBJECT-TYPE
    SYNTAX     Counter64
    MAX-ACCESS read-only
    STATUS     current
    DESCRIPTION
           "This attribute reports the number of bursts received
            with errors other than 'no energy' or 'no preamble' 
            for the selected IUC."
    ::= { docsRphyStatsRpdUsScQamHighIucPerfStatsEntry 8 }


-- ---------------------------------------------------------------------
-- CCAP Core Group Objects
-- ---------------------------------------------------------------------

-- ---------------------------------------------------------------------
-- TBD Table
-- ---------------------------------------------------------------------

    
-- ---------------------------------------------------------
-- Conformance definitions 
-- ---------------------------------------------------------

docsRphyStatsCompliance MODULE-COMPLIANCE 
     STATUS current 
     DESCRIPTION 
          "The compliance statement for CCAP Core and RPD Statistical monitoring features."

MODULE -- docsRphyStatsMib
        
-- conditionally mandatory groups

GROUP docsRphyStatsRpdGroup 
        DESCRIPTION
            "Group of objects applicable to RPDs only.
            These objects are implemented on the CCAP Core
            but are derived from the RPD via the GCP protocol."
            
-- conditionally optional groups


::= { docsRphyStatsCompliances 1}


docsRphyStatsRpdGroup OBJECT-GROUP
        OBJECTS {
                    docsRphyStatsRpdDsScQamPerfStatsOutDiscards,
                    docsRphyStatsRpdDsScQamPerfStatsOutErrors,
                    docsRphyStatsRpdDsScQamPerfStatsOutPackets,
                    docsRphyStatsRpdDsScQamPerfStatsRpdDsCounterDiscTime,

                    docsRphyStatsRpdDsOfdmPerfStatsOutDiscards,
                    docsRphyStatsRpdDsOfdmPerfStatsOutErrors,
                    docsRphyStatsRpdDsOfdmPerfStatsOutPackets,
                    docsRphyStatsRpdDsOfdmPerfStatsRpdDsCounterDiscTime,

                    docsRphyStatsRpdDsOob551PerfStatsOutDiscards,
                    docsRphyStatsRpdDsOob551PerfStatsOutErrors,
                    docsRphyStatsRpdDsOob551PerfStatsOutPackets,
                    docsRphyStatsRpdDsOob551PerfStatsRpdDsCounterDiscTime,

                    docsRphyStatsRpdDsOob552PerfStatsOutDiscards,
                    docsRphyStatsRpdDsOob552PerfStatsOutErrors,
                    docsRphyStatsRpdDsOob552PerfStatsOutPackets,
                    docsRphyStatsRpdDsOob552PerfStatsRpdDsCounterDiscTime,

                    docsRphyStatsRpdDsNdfPerfStatsOutDiscards,
                    docsRphyStatsRpdDsNdfPerfStatsOutErrors,
                    docsRphyStatsRpdDsNdfPerfStatsOutPackets,
                    docsRphyStatsRpdDsNdfPerfStatsRpdDsCounterDiscTime,

                    docsRphyStatsRpdDsOfdmPlcPerfStatsOutDiscards,
                    docsRphyStatsRpdDsOfdmPlcPerfStatsOutErrors,
                    docsRphyStatsRpdDsOfdmPlcPerfStatsOutPackets,
                    docsRphyStatsRpdDsOfdmPlcPerfStatsRpdDsCounterDiscTime,

                    docsRphyStatsRpdDsOfdmProfilePerfStatsOutCodewords,

		    docsRphyStatsRpdUsOfdmaChanPerfStatsProbeGrants,
                    docsRphyStatsRpdUsOfdmaChanPerfStatsHcsErrors,
                    docsRphyStatsRpdUsOfdmaChanPerfStatsLateMaps,
                    docsRphyStatsRpdUsOfdmaChanPerfStatsIllegalMaps,
                    docsRphyStatsRpdUsOfdmaChanPerfStatsDiscardedRequests,
                    docsRphyStatsRpdUsOfdmaChanPerfStatsRpdUsCounterDiscTime,

                    docsRphyStatsRpdUsScQamChanPerfStatsChanSnr,
                    docsRphyStatsRpdUsScQamChanPerfStatsHcsErrors,
                    docsRphyStatsRpdUsScQamChanPerfStatsLateMaps,
                    docsRphyStatsRpdUsScQamChanPerfStatsIllegalMaps,
                    docsRphyStatsRpdUsScQamChanPerfStatsDiscardedRequests,
                    docsRphyStatsRpdUsScQamChanPerfStatsRpdUsCounterDiscTime,

                    docsRphyStatsRpdUsOfdmaLowIucPerfStatsNumPredecodePass,
	            docsRphyStatsRpdUsOfdmaLowIucPerfStatsNumPostdecodePass,
	            docsRphyStatsRpdUsOfdmaLowIucPerfStatsNumPostdecodeFail,
	            docsRphyStatsRpdUsOfdmaLowIucPerfStatsUnicastOpportunities,
	            docsRphyStatsRpdUsOfdmaLowIucPerfStatsUnicastOpCollisions,	
	            docsRphyStatsRpdUsOfdmaLowIucPerfStatsUnicastOpNoEnergy,
	            docsRphyStatsRpdUsOfdmaLowIucPerfStatsUnicastOpErrors,
	            docsRphyStatsRpdUsOfdmaLowIucPerfStatsMulticastOpportunities,
	            docsRphyStatsRpdUsOfdmaLowIucPerfStatsMulticastOpCollisions,
	            docsRphyStatsRpdUsOfdmaLowIucPerfStatsMulticastOpNoEnergy,
	            docsRphyStatsRpdUsOfdmaLowIucPerfStatsMulticastOpErrors,

                    docsRphyStatsRpdUsOfdmaHighIucPerfStatsAverageMer,                    
                    docsRphyStatsRpdUsOfdmaHighIucPerfStatsNumPredecodePass,
		    docsRphyStatsRpdUsOfdmaHighIucPerfStatsNumPostdecodePass,
	            docsRphyStatsRpdUsOfdmaHighIucPerfStatsNumPostdecodeFail,
	            docsRphyStatsRpdUsOfdmaHighIucPerfStatsScheduledGrants,
                    docsRphyStatsRpdUsOfdmaHighIucPerfStatsNoEnergyBursts,
                    docsRphyStatsRpdUsOfdmaHighIucPerfStatsNoPreambleBursts,
                    docsRphyStatsRpdUsOfdmaHighIucPerfStatsErrorBursts,

                    docsRphyStatsRpdUsScQamLowIucPerfStatsGoodFecCw,
	            docsRphyStatsRpdUsScQamLowIucPerfStatsCorrectedFecCw,
	            docsRphyStatsRpdUsScQamLowIucPerfStatsUncorrectedFecCw,
	            docsRphyStatsRpdUsScQamLowIucPerfStatsUnicastOpportunities,
	            docsRphyStatsRpdUsScQamLowIucPerfStatsUnicastOpCollisions,	
	            docsRphyStatsRpdUsScQamLowIucPerfStatsUnicastOpNoEnergy,
	            docsRphyStatsRpdUsScQamLowIucPerfStatsUnicastOpErrors,
	            docsRphyStatsRpdUsScQamLowIucPerfStatsMulticastOpportunities,
	            docsRphyStatsRpdUsScQamLowIucPerfStatsMulticastOpCollisions,
	            docsRphyStatsRpdUsScQamLowIucPerfStatsMulticastOpNoEnergy,
	            docsRphyStatsRpdUsScQamLowIucPerfStatsMulticastOpErrors,

                    docsRphyStatsRpdUsScQamHighIucPerfStatsGoodFecCw,
	            docsRphyStatsRpdUsScQamHighIucPerfStatsCorrectedFecCw,
	            docsRphyStatsRpdUsScQamHighIucPerfStatsUncorrectedFecCw,
	            docsRphyStatsRpdUsScQamHighIucPerfStatsScheduledGrants,
                    docsRphyStatsRpdUsScQamHighIucPerfStatsNoEnergyBursts,
                    docsRphyStatsRpdUsScQamHighIucPerfStatsNoPreambleBursts,
                    docsRphyStatsRpdUsScQamHighIucPerfStatsErrorBursts
        }
        STATUS      current
        DESCRIPTION
            "Group of objects implemented in CCAP Cores which
            represent RPD managed objects derived via the GCP 
            protocol."
        ::= { docsRphyStatsGroups 1 }
        END
