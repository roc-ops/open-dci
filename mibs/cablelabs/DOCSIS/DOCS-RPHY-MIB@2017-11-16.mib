DOCS-RPHY-MIB DEFINITIONS ::= BEGIN
IMPORTS
    MODULE-IDENTITY, 
    OBJECT-TYPE, 
    Unsigned32,
    Gauge32,
    Counter32,
    Counter64,
    Integer32
        FROM SNMPv2-SMI         -- RFC 2578
    TruthValue, 
    MacAddress,
    TimeStamp,
    AutonomousType,
    DateAndTime,
    PhysAddress,
    TEXTUAL-CONVENTION
        FROM SNMPv2-TC 
    OBJECT-GROUP, 
    MODULE-COMPLIANCE 
        FROM SNMPv2-CONF
    SnmpAdminString
        FROM SNMP-FRAMEWORK-MIB -- RFC 3411
    InetAddressType,
    InetAddress,
    InetPortNumber,
    InetVersion,
    InetAddressPrefixLength
        FROM INET-ADDRESS-MIB   -- RFC 4001
    UUIDorZero
        FROM UUID-TC-MIB        -- RFC 6933
    IANAPhysicalClass
        FROM IANA-ENTITY-MIB    -- RFC 6933
    IANAifType                               
        FROM IANAifType-MIB
    PhysicalIndex,
    PhysicalIndexOrZero
        FROM ENTITY-MIB         -- RFC 6933
    EntitySensorDataType,
    EntitySensorDataScale,
    EntitySensorPrecision,
    EntitySensorValue,
    EntitySensorStatus
        FROM ENTITY-SENSOR-MIB  -- RFC 3433
    IpAddressOriginTC,
    IpAddressStatusTC,
    Ipv6AddressIfIdentifierTC
        FROM IP-MIB             -- RFC 4293
    InterfaceIndex,
    ifIndex,
    InterfaceIndexOrZero
        FROM IF-MIB
    IfDirection,
    docsIf3CmtsCmRegStatusId
        FROM DOCS-IF3-MIB
    clabProjDocsis
        FROM CLAB-DEF-MIB
    DocsX509ASN1DEREncodedCertificate
        FROM DOCS-IETF-BPI2-MIB;


docsRphyMib MODULE-IDENTITY 
    LAST-UPDATED    "201711160000Z" -- November 16, 2017
    ORGANIZATION    "Cable Television Laboratories, Inc" 
    CONTACT-INFO 
         "
         Postal: Cable Television Laboratories, Inc. 
         400 Centennial Parkway 
         Louisville, Colorado 80027-1266 
         U.S.A. 
         Phone: +1 303-661-9100 
         Fax: +1 303-661-9199 
         E-mail: mibs@cablelabs.com" 
    DESCRIPTION 
        "This MIB module contains the management objects for
         the Remote PHY Device (RPD) management.
         Copyright 2016-2017 Cable Television Laboratories, Inc.
         All rights reserved."
    REVISION "201711160000Z" -- November 16, 2017
    DESCRIPTION 
        "Revised Version includes ECN
         DOCS-RPHY-MIB-N-17.1812-4."
    REVISION "201708100000Z" -- August 10, 2017
    DESCRIPTION 
        "Revised Version includes ECN
         DOCS-RPHY-MIB-N-17.1780-3." 
    REVISION "201704130000Z" -- April 13, 2017
    DESCRIPTION 
        "Revised Version includes ECN
         DOCS-RPHY-MIB-N-17.1711-4."
	REVISION "201612150000Z" -- December 15, 2016
    DESCRIPTION 
        "Revised Version includes ECN
         DOCS-RPHY-MIB-N-16.1680-2."
    REVISION "201609290000Z" -- September 29, 2016
    DESCRIPTION 
        "Revised Version includes ECN
         DOCS-RPHY-MIB-N-16.1561-4."
    REVISION "201604210000Z" -- April 21, 2016
    DESCRIPTION 
        "Initial version, created by R-OSSI-N-16.1461-3."
::= { clabProjDocsis 30 }


-- ---------------------------------------------------------
-- Textual Conventions
-- ---------------------------------------------------------

OperStatusType ::= TEXTUAL-CONVENTION
     STATUS      current
     DESCRIPTION
         "This data type represents the status of the 
          pseudowire from the point of view of the specific 
          reporting entity.
          
          Values are as follows:
             'other' 
                 indicates a vendor-specific operational status.
             'up'         
                 indicates that the pseudowire is ready to pass packets.
             'down' 
                 indicates that pseudowire signaling is not yet finished, 
                 or indications available at the service level indicate 
                 that the pseudowire is not passing packets.
             'testing' 
                 indicates that AdminStatus at the pseudowire level is 
                 set to test.
             'dormant' 
                 indicates that the pseudowire is not in a condition to 
                 pass packets but is in a 'pending' state, waiting for 
                 some external event.
             'notPresent' 
                 indicates that some component is missing to accomplish 
                 the setup of the pseudowire.  It can be a configuration 
                 error, incomplete configuration, or a missing H/W 
                 component.
             'lowerLayerDown' 
                 indicates one or more of the lower-layer 
                 interfaces responsible for running the underlying PSN
                 is not in OperStatus 'up' state."

     SYNTAX      INTEGER {
                          other(0),
                          up(1),
                          down(2),
                          testing(3),
                          dormant(4),
                          notPresent(5),
                          lowerLayerDown(6)
                        }


RphyChannelType ::= TEXTUAL-CONVENTION
     STATUS      current
     DESCRIPTION
         "This data type indicates the type of RPHY channel."
     REFERENCE
        "DOCSIS DCA MHAv2 Remote PHY Specification
         CM-SP-R-PHY-I04-160512, RfChannelType TLV Section."
     SYNTAX      INTEGER {
                          other(0),
                          dsScQam(1),
                          dsOfdm(2),
                          ndf(3),
                          scte551Fwd(4),
                          usAtdma(5),
                          usOfdma(6),
                          reserved(7),
                          ndr(8),
                          scte551Ret(9)                                                                                                                           
                         }

RphyEventSeverityType ::= TEXTUAL-CONVENTION
     STATUS      current
     DESCRIPTION
         "This data type indicates the severity level of an RPD 
         event."
     REFERENCE
        "DOCSIS DCA MHAv2 Remote PHY OSS Interface Specification
         CM-SP-R-OSSI-I04-160923, Section 9."
     SYNTAX      INTEGER {
                             emergency(0),
                             alert(1),
                             critical(2),
                             error(3),
                             warning(4),
                             notice(5),
                             information(6),
                             debug(7)                                                                                                                      
                         }
                         
-- ---------------------------------------------------------------------
-- Main Groups
-- ---------------------------------------------------------------------
docsRphyNotifications        OBJECT IDENTIFIER ::= { docsRphyMib 0}
docsRphyObjects              OBJECT IDENTIFIER ::= { docsRphyMib 1}
docsRphyConformance          OBJECT IDENTIFIER ::= { docsRphyMib 2}

docsRphyRpdDevMibObjects     OBJECT IDENTIFIER ::= { docsRphyObjects 1}
docsRphyRpdIfMibObjects      OBJECT IDENTIFIER ::= { docsRphyObjects 2}

docsRphyRpdIpMibObjects      OBJECT IDENTIFIER ::= { docsRphyObjects 3}
docsRphyCcapMibObjects       OBJECT IDENTIFIER ::= { docsRphyObjects 4}

docsRphyCcapSecMibObjects    OBJECT IDENTIFIER ::= { docsRphyObjects 5}

docsRphyCmtsCmStatMibObjects   OBJECT IDENTIFIER ::= { docsRphyObjects 6}


docsRphyRpdIpIcmpMibObjects  OBJECT IDENTIFIER ::= { docsRphyRpdIpMibObjects 9 }

docsRphyCompliances          OBJECT IDENTIFIER ::= { docsRphyConformance 1 } 
docsRphyGroups               OBJECT IDENTIFIER ::= { docsRphyConformance 2 } 



-- ---------------------------------------------------------------------
-- Notification Objects
-- ---------------------------------------------------------------------

-- ---------------------------------------------------------------------
-- RPD Group Objects
-- ---------------------------------------------------------------------
   		
-- ---------------------------------------------------------------------
-- RPD Info Table
-- ---------------------------------------------------------------------

docsRphyRpdDevInfoTable OBJECT-TYPE
        SYNTAX      SEQUENCE OF DocsRphyRpdDevInfoEntry
        MAX-ACCESS  not-accessible
        STATUS      current
        DESCRIPTION
            "This table identifies the RPD for which the details
             and statistics are being provided."
        ::= { docsRphyRpdDevMibObjects 1 }


docsRphyRpdDevInfoEntry OBJECT-TYPE
        SYNTAX     DocsRphyRpdDevInfoEntry
        MAX-ACCESS not-accessible
        STATUS     current
        DESCRIPTION
            "The conceptual row of docsRphyRpdDevInfoTable."
        INDEX { docsRphyRpdDevInfoUniqueId }
        ::= { docsRphyRpdDevInfoTable 1 }


DocsRphyRpdDevInfoEntry ::= SEQUENCE
       {
       docsRphyRpdDevInfoUniqueId              MacAddress,
       docsRphyRpdDevInfoSysUpTime             TimeStamp,
       docsRphyRpdDevInfoNumCrashFilesAvail    Unsigned32	
       }
        
docsRphyRpdDevInfoUniqueId OBJECT-TYPE
        SYNTAX      MacAddress
        MAX-ACCESS  not-accessible 
        STATUS      current 
        DESCRIPTION 
            "This attribute specifies a globally unique 6-byte 
             identifier for the RPD.  By convention, an RPD SHOULD use 
             the MAC address of the lowest numbered Ethernet port 
             facing the CIN."
        ::= { docsRphyRpdDevInfoEntry 1 }


docsRphyRpdDevInfoSysUpTime OBJECT-TYPE
        SYNTAX      TimeStamp
        MAX-ACCESS  read-only
        STATUS      current
        DESCRIPTION 
            "This attribute is the time (in hundredths of a second) 
             since the RPD was last re-initialized. This value is 
             reported by the RPD."
        ::= { docsRphyRpdDevInfoEntry 2 }

docsRphyRpdDevInfoNumCrashFilesAvail OBJECT-TYPE
        SYNTAX      Unsigned32
        MAX-ACCESS  read-only
        STATUS      current
        DESCRIPTION 
            "This attribute provides the number of crash files."
        ::= { docsRphyRpdDevInfoEntry 3 }


-- ---------------------------------------------------------------------
-- RPD Identification Table
-- ---------------------------------------------------------------------

docsRphyRpdDevIdentificationTable OBJECT-TYPE
        SYNTAX      SEQUENCE OF DocsRphyRpdDevIdentificationEntry
        MAX-ACCESS  not-accessible
        STATUS      current
        DESCRIPTION
            "This table provides data that uniquely identifies the RPD."
        ::= { docsRphyRpdDevMibObjects 2 }


docsRphyRpdDevIdentificationEntry OBJECT-TYPE
        SYNTAX     DocsRphyRpdDevIdentificationEntry
        MAX-ACCESS not-accessible
        STATUS     current
        DESCRIPTION
            "The conceptual row of docsRphyRpdDevIdentificationTable."
        INDEX { docsRphyRpdDevInfoUniqueId }
        ::= { docsRphyRpdDevIdentificationTable 1 }


DocsRphyRpdDevIdentificationEntry ::= SEQUENCE
       {
       docsRphyRpdDevIdVendorName           		SnmpAdminString,
       docsRphyRpdDevIdVendorId             		Unsigned32,
       docsRphyRpdDevIdModelNum             		SnmpAdminString,
       docsRphyRpdDevIdSerialNum            		SnmpAdminString,
       docsRphyRpdDevIdDeviceAlias          		SnmpAdminString,
       docsRphyRpdDevIdDeviceDescr          		SnmpAdminString,
       docsRphyRpdDevIdHwRev                		SnmpAdminString,
       docsRphyRpdDevIdCurrSwVer            		SnmpAdminString,
       docsRphyRpdDevIdBootRomVer           		SnmpAdminString,
       docsRphyRpdDevIdUsBurstRcvrVendorId  		Unsigned32,
       docsRphyRpdDevIdUsBurstRcvrModelNum  		SnmpAdminString,
       docsRphyRpdDevIdUsBurstRcvrDrivVer   		SnmpAdminString,
       docsRphyRpdDevIdUsBurstRcvrSerialNum 		SnmpAdminString,
       docsRphyRpdDevIdRcpProtocolVer       		SnmpAdminString,
       docsRphyRpdDevIdRcpSchemaVer         		SnmpAdminString,
       docsRphyRpdDevIdCurrSwImageLastUpdate  		DateAndTime,		      
       docsRphyRpdDevIdCurrSwImageName  		SnmpAdminString,
       docsRphyRpdDevIdCurrSwImageServerType  		InetAddressType,
       docsRphyRpdDevIdCurrSwImageServerAddress		InetAddress
       }
        
docsRphyRpdDevIdVendorName OBJECT-TYPE
        SYNTAX      SnmpAdminString
        MAX-ACCESS  read-only 
        STATUS      current 
        DESCRIPTION 
            "This attribute identifies the RPD manufacturer. 
             The format is vendor proprietary."
        ::= { docsRphyRpdDevIdentificationEntry 1 }


docsRphyRpdDevIdVendorId OBJECT-TYPE
        SYNTAX      Unsigned32 (0..65535)
        MAX-ACCESS  read-only
        STATUS      current
        DESCRIPTION 
            "This attribute is the IANA-assigned SMI Network Management 
             Private Enterprise Code of the vendor, as specified in
             RFC 5612."
        ::= { docsRphyRpdDevIdentificationEntry 2 }

docsRphyRpdDevIdModelNum OBJECT-TYPE
        SYNTAX      SnmpAdminString
        MAX-ACCESS  read-only 
        STATUS      current 
        DESCRIPTION 
            "This attribute is the model name and number used by the 
             vendor to identify the RPD. The format is vendor 
             proprietary."
        ::= { docsRphyRpdDevIdentificationEntry 3 }

docsRphyRpdDevIdSerialNum OBJECT-TYPE
        SYNTAX      SnmpAdminString (SIZE(0..16))
        MAX-ACCESS  read-only 
        STATUS      current 
        DESCRIPTION 
            "This attribute is the serial number of the RPD. 
             The format is vendor proprietary."
        ::= { docsRphyRpdDevIdentificationEntry 4 }
        
docsRphyRpdDevIdDeviceAlias OBJECT-TYPE
        SYNTAX      SnmpAdminString
        MAX-ACCESS  read-only 
        STATUS      current 
        DESCRIPTION 
            "This attribute reports the device name assigned by the 
             operator and represents a 'handle' for the RPD."
        ::= { docsRphyRpdDevIdentificationEntry 5 }
        
docsRphyRpdDevIdDeviceDescr OBJECT-TYPE
        SYNTAX      SnmpAdminString
        MAX-ACCESS  read-only 
        STATUS      current 
        DESCRIPTION 
            "This attribute is a short text description of the RPD
             provided by the RPD manufacturer."
        ::= { docsRphyRpdDevIdentificationEntry 6 }
        
docsRphyRpdDevIdHwRev OBJECT-TYPE
        SYNTAX      SnmpAdminString
        MAX-ACCESS  read-only 
        STATUS      current 
        DESCRIPTION 
            "This attribute is the revision number of the hardware 
             of the RPD. The format is vendor proprietary."
        ::= { docsRphyRpdDevIdentificationEntry 7 }
        
docsRphyRpdDevIdCurrSwVer OBJECT-TYPE
        SYNTAX      SnmpAdminString
        MAX-ACCESS  read-only 
        STATUS      current 
        DESCRIPTION 
            "This attribute is the version number of the software 
             currently running on the RPD. The format is vendor 
             proprietary."
        ::= { docsRphyRpdDevIdentificationEntry 8 }
        
docsRphyRpdDevIdBootRomVer OBJECT-TYPE
        SYNTAX      SnmpAdminString
        MAX-ACCESS  read-only 
        STATUS      current 
        DESCRIPTION 
            "This attribute reports the version number of the boot 
             ROM currently installed on the RPD. The format is 
             vendor proprietary."
        ::= { docsRphyRpdDevIdentificationEntry 9 }
        
docsRphyRpdDevIdUsBurstRcvrVendorId OBJECT-TYPE
        SYNTAX      Unsigned32 (0..65535)
        MAX-ACCESS  read-only 
        STATUS      current 
        DESCRIPTION 
            "This attribute reports the IANA-assigned SMI Network 
             Management Private Enterprise Code of the RPD's US burst 
             receiver manufacturer, as specified in RFC 5612."
        ::= { docsRphyRpdDevIdentificationEntry 10 }
        
docsRphyRpdDevIdUsBurstRcvrModelNum OBJECT-TYPE
        SYNTAX      SnmpAdminString (SIZE(3..16))
        MAX-ACCESS  read-only 
        STATUS      current 
        DESCRIPTION 
            "This attribute reports the model number used by the vendor 
             to identify the RPD's US burst receiver. The format is 
             vendor proprietary."
        ::= { docsRphyRpdDevIdentificationEntry 11 }
        
docsRphyRpdDevIdUsBurstRcvrDrivVer OBJECT-TYPE
        SYNTAX      SnmpAdminString (SIZE(3..16))
        MAX-ACCESS  read-only 
        STATUS      current 
        DESCRIPTION 
            "This attribute reports the driver version of the RPD's 
             US burst receiver. The format is vendor proprietary."
        ::= { docsRphyRpdDevIdentificationEntry 12 }
        
docsRphyRpdDevIdUsBurstRcvrSerialNum OBJECT-TYPE
        SYNTAX      SnmpAdminString (SIZE(5..16))
        MAX-ACCESS  read-only 
        STATUS      current 
        DESCRIPTION 
            "This attribute reports the serial number of the RPD's 
             US burst receiver. The format is vendor proprietary."
        ::= { docsRphyRpdDevIdentificationEntry 13 }
        
docsRphyRpdDevIdRcpProtocolVer OBJECT-TYPE
        SYNTAX      SnmpAdminString (SIZE(3..32))
        MAX-ACCESS  read-only 
        STATUS      current 
        DESCRIPTION 
            "This attribute reports the version of the RCP protocol 
             supported by the RPD."
        ::= { docsRphyRpdDevIdentificationEntry 14 }
        
docsRphyRpdDevIdRcpSchemaVer OBJECT-TYPE
        SYNTAX      SnmpAdminString (SIZE(5..32))
        MAX-ACCESS  read-only 
        STATUS      current 
        DESCRIPTION 
            "This attribute reports the version of the RCP schema 
             supported by the RPD."
	 ::= { docsRphyRpdDevIdentificationEntry 15 }

docsRphyRpdDevIdCurrSwImageLastUpdate OBJECT-TYPE
        SYNTAX      DateAndTime		      
        MAX-ACCESS  read-only 
        STATUS      current 
        DESCRIPTION 
            "This attribute reports the most recent date and time the 
             software image currently running on the RPD was updated. 
             The RPD preserves the value of this attribute across reboots."
	 ::= { docsRphyRpdDevIdentificationEntry 16 }


docsRphyRpdDevIdCurrSwImageName OBJECT-TYPE
        SYNTAX      SnmpAdminString
        MAX-ACCESS  read-only 
        STATUS      current 
        DESCRIPTION 
            "This attribute reports the name of the software image currently
             running on the RPD. The RPD preserves the value of this 
             attribute across reboots."
	::= { docsRphyRpdDevIdentificationEntry 17 }

docsRphyRpdDevIdCurrSwImageServerType OBJECT-TYPE
        SYNTAX      InetAddressType
        MAX-ACCESS  read-only 
        STATUS      current 
        DESCRIPTION 
            "This attribute reports the server internet address type of 
	     the software image currently running on the RPD. The RPD
	     preserves the value of this attribute across reboots."
	::= { docsRphyRpdDevIdentificationEntry 18 }

docsRphyRpdDevIdCurrSwImageServerAddress OBJECT-TYPE
        SYNTAX      InetAddress
        MAX-ACCESS  read-only 
        STATUS      current 
        DESCRIPTION 
            "This attribute reports the Internet address of the server 
             from which the software image currently running on the RPD 
             was downloaded. The RPD preserves the value of this 
             attribute across reboots."
	 ::= { docsRphyRpdDevIdentificationEntry 19 }


-- ---------------------------------------------------------------------
-- RPD Location Table
-- ---------------------------------------------------------------------

docsRphyRpdDevLocationTable OBJECT-TYPE
        SYNTAX      SEQUENCE OF DocsRphyRpdDevLocationEntry
        MAX-ACCESS  not-accessible
        STATUS      current
        DESCRIPTION
            "This table provides location details for the RPD. The 
             values are populated via a management interface or other 
             automatic mechanisms (e.g. GPS)."
        ::= { docsRphyRpdDevMibObjects 3 }


docsRphyRpdDevLocationEntry OBJECT-TYPE
        SYNTAX     DocsRphyRpdDevLocationEntry
        MAX-ACCESS not-accessible
        STATUS     current
        DESCRIPTION
            "The conceptual row of docsRphyRpdDevLocationTable."
        INDEX { docsRphyRpdDevInfoUniqueId }
        ::= { docsRphyRpdDevLocationTable 1 }


DocsRphyRpdDevLocationEntry ::= SEQUENCE
       {
       docsRphyRpdDevLocationDescr              SnmpAdminString,
       docsRphyRpdDevLocationLatitude           SnmpAdminString,
       docsRphyRpdDevLocationLongitude          SnmpAdminString
       }
        
docsRphyRpdDevLocationDescr OBJECT-TYPE
        SYNTAX      SnmpAdminString (SIZE(0..255))
        MAX-ACCESS  read-only 
        STATUS      current 
        DESCRIPTION 
            "This attribute is short text description of where the RPD
             has been installed, such as a street address. The format 
             is specific to the operator."
        ::= { docsRphyRpdDevLocationEntry 1 }


docsRphyRpdDevLocationLatitude OBJECT-TYPE
        SYNTAX      SnmpAdminString (SIZE(9))
        MAX-ACCESS  read-only
        STATUS      current
        DESCRIPTION 
            "This attribute is the latitudinal coordinate of the RPD 
             location, expressed as a 6-byte long string as described
             in ISO 6709-2008 (6 digit degrees, minutes, 
             seconds: +/-DDMMSS.S). For  example: -750015.1"
        ::= { docsRphyRpdDevLocationEntry 2 }
        
docsRphyRpdDevLocationLongitude OBJECT-TYPE
        SYNTAX      SnmpAdminString (SIZE(10))
        MAX-ACCESS  read-only
        STATUS      current
        DESCRIPTION 
            "This attribute is the longitudinal coordinate of the RPD 
             location, expressed as a 7-byte long string as described 
             in ISO 6709-2008 (7 digits degrees, minutes, 
             seconds: +/-DDDMMSS.S).  For example: -0750015.1"
        ::= { docsRphyRpdDevLocationEntry 3 }
        
-- ---------------------------------------------------------------------
-- RPD Cores Connected Table
-- ---------------------------------------------------------------------

docsRphyRpdDevCoresConnectedTable OBJECT-TYPE
        SYNTAX      SEQUENCE OF DocsRphyRpdDevCoresConnectedEntry
        MAX-ACCESS  not-accessible
        STATUS      current
        DESCRIPTION
            "This table provides a list of CCAP-Cores to which the RPD
             is authenticated, including the CCAP-Core on which the MIB 
             is polled. For each CCAP-Core entry, the RPD indicates if 
             that CCAP-Core is the principal Core. These values are 
             provided by the CCAP-Core on initialization."
        ::= { docsRphyRpdDevMibObjects 4 }


docsRphyRpdDevCoresConnectedEntry OBJECT-TYPE
        SYNTAX     DocsRphyRpdDevCoresConnectedEntry
        MAX-ACCESS not-accessible
        STATUS     current
        DESCRIPTION
            "The conceptual row of docsRphyRpdDevCoresConnectedTable."
        INDEX { docsRphyRpdDevInfoUniqueId, docsRphyRpdDevCoresConnectedCoreId }
        ::= { docsRphyRpdDevCoresConnectedTable 1 }


DocsRphyRpdDevCoresConnectedEntry ::= SEQUENCE
       {
       docsRphyRpdDevCoresConnectedCoreId              MacAddress,
       docsRphyRpdDevCoresConnectedAddressType         InetAddressType,
       docsRphyRpdDevCoresConnectedAddress             InetAddress,
       docsRphyRpdDevCoresConnectedIsPrincipal         TruthValue,
       docsRphyRpdDevCoresConnectedName                SnmpAdminString,
       docsRphyRpdDevCoresConnectedVendorId            Unsigned32,
       docsRphyRpdDevCoresConnectedCoreMode            INTEGER,
       docsRphyRpdDevCoresConnectedInitConfigComplete  TruthValue,
       docsRphyRpdDevCoresConnectedCoreFunction        BITS
       }
        
docsRphyRpdDevCoresConnectedCoreId OBJECT-TYPE
        SYNTAX      MacAddress
        MAX-ACCESS  not-accessible 
        STATUS      current 
        DESCRIPTION 
            "This attribute provides the MAC address of the CCAP-Core
             identified in the row entry and acts as a key."
        ::= { docsRphyRpdDevCoresConnectedEntry 1 }


docsRphyRpdDevCoresConnectedAddressType OBJECT-TYPE
        SYNTAX      InetAddressType
        MAX-ACCESS  read-only
        STATUS      current
        DESCRIPTION 
            "This attribute specifies the IP address 
             type for docsRphyRpdDevCoresConnectedAddress."
        ::= { docsRphyRpdDevCoresConnectedEntry 2 }
        
docsRphyRpdDevCoresConnectedAddress OBJECT-TYPE
        SYNTAX      InetAddress
        MAX-ACCESS  read-only
        STATUS      current
        DESCRIPTION 
            "This attribute provides the IPv4 or IPv6 address 
             of the CCAP-Core."
        ::= { docsRphyRpdDevCoresConnectedEntry 3 }
        
docsRphyRpdDevCoresConnectedIsPrincipal OBJECT-TYPE
        SYNTAX      TruthValue
        MAX-ACCESS  read-only
        STATUS      current
        DESCRIPTION 
            "This attribute indicates if the CCAP-Core is the
             principal core. If true, this attribute indicates 
             that this CCAP-Core is the principal core."
        ::= { docsRphyRpdDevCoresConnectedEntry 4 }
        
docsRphyRpdDevCoresConnectedName OBJECT-TYPE
        SYNTAX      SnmpAdminString
        MAX-ACCESS  read-only
        STATUS      current
        DESCRIPTION 
            "This attribute provides the name of the CCAP-Core 
             as conveyed to the RPD."
        ::= { docsRphyRpdDevCoresConnectedEntry 5 }
        
docsRphyRpdDevCoresConnectedVendorId OBJECT-TYPE
        SYNTAX      Unsigned32 (0..65535)
        MAX-ACCESS  read-only
        STATUS      current
        DESCRIPTION 
            "This attribute provides the IANA-assigned SMI Network 
             Management Private Enterprise Code of the vendor, as 
             specified in RFC 1700."
        ::= { docsRphyRpdDevCoresConnectedEntry 6 }

docsRphyRpdDevCoresConnectedCoreMode OBJECT-TYPE
        SYNTAX      INTEGER {
                             active(1),
                             backup(2),
                             notActing(3),
                             decisionPending(4),
                             outOfService(5),
                             contactPending(6)
                             }
        MAX-ACCESS  read-only
        STATUS      current
        DESCRIPTION 
            "This attribute identifies in which Principal Core 
             operation mode the Core is currently functioning. 
             
             active: Core functioning as the active Principal Core

             backup: Core is a backup Principal Core

             notActing: Core is not functioning as a Principal Core

             decisionPending: Core requires further information to make 
             a decision on acting for or redirecting the RPD

             outOfService: RPD has lost its connection to the Core

             contactPending: RPD has not yet connected to the Core"
	  ::= { docsRphyRpdDevCoresConnectedEntry 7 }

docsRphyRpdDevCoresConnectedInitConfigComplete OBJECT-TYPE
        SYNTAX      TruthValue
        MAX-ACCESS  read-only
        STATUS      current
        DESCRIPTION 
            "This attribute reports whether the Core has indicated
             that its initial configuration of the RPD is complete."
        ::= { docsRphyRpdDevCoresConnectedEntry 8 }

docsRphyRpdDevCoresConnectedCoreFunction OBJECT-TYPE
        SYNTAX      BITS {
                          principal(0),
                          docsis(1),
                          broadcastVideo(2),
                          narrowcastVideo(3), 
                          scte55d1Oob(4), 
                          scte55d2Oob(5), 
			  ndf(6), 
                          ndr(7)
                         }
        MAX-ACCESS  read-only
        STATUS      current
        DESCRIPTION 
            "This attribute reports the operational functions that this Core provides.

	     principal: Core operates as a Principal Core 

	     docsis: Core provides DOCSIS services
 
             broadcastVideo: Core provides broadcast video services
 
             narrowcastVideo: Core provides narrowcast video services
 
             scte55d1Oob: Core provides SCTE 55-1 OOB services
 
             scte55d2Oob: Core provides SCTE 55-2 OOB services
 
             ndf: Core provides narrowband digital forward services
 
             ndr: Core provides narrowband digital return services"
        ::= { docsRphyRpdDevCoresConnectedEntry 9 }
        
-- ---------------------------------------------------------------------
-- RPD Capabilities Table
-- ---------------------------------------------------------------------

docsRphyRpdDevCapabilitiesTable OBJECT-TYPE
        SYNTAX      SEQUENCE OF DocsRphyRpdDevCapabilitiesEntry
        MAX-ACCESS  not-accessible
        STATUS      current
        DESCRIPTION
            "This table provides information about the principal 
             capabilities and constraints of the RPD."
        ::= { docsRphyRpdDevMibObjects 5 }


docsRphyRpdDevCapabilitiesEntry OBJECT-TYPE
        SYNTAX     DocsRphyRpdDevCapabilitiesEntry
        MAX-ACCESS not-accessible
        STATUS     current
        DESCRIPTION
            "The conceptual row of docsRphyRpdDevCapabilitiesTable."
        INDEX { docsRphyRpdDevInfoUniqueId }
        ::= { docsRphyRpdDevCapabilitiesTable 1 }


DocsRphyRpdDevCapabilitiesEntry ::= SEQUENCE
       {
       docsRphyRpdDevCapabNumDsPorts                 Unsigned32,
       docsRphyRpdDevCapabNumUsPorts                 Unsigned32,
       docsRphyRpdDevCapabNumTenGeNsPorts            Unsigned32,
       docsRphyRpdDevCapabNumOneGeNsPorts            Unsigned32,
       docsRphyRpdDevCapabNumDsScQamChans            Unsigned32,
       docsRphyRpdDevCapabNumDsOfdmChans             Unsigned32,
       docsRphyRpdDevCapabNumUsScQamChans            Unsigned32,
       docsRphyRpdDevCapabNumUsOfdmaChans            Unsigned32,
       docsRphyRpdDevCapabNumDsOob55d1Chans          Unsigned32,
       docsRphyRpdDevCapabNumUsOob55d1Chans          Unsigned32,
       docsRphyRpdDevCapabNumDsOob55d2Modules        Unsigned32,
       docsRphyRpdDevCapabNumUsOob55d2Demods         Unsigned32,
       docsRphyRpdDevCapabNumNdfChans                Unsigned32,
       docsRphyRpdDevCapabNumNdrChans                Unsigned32,
       docsRphyRpdDevCapabNumDsPspFlowsPerChan       Unsigned32,
       docsRphyRpdDevCapabNumUsPspFlowsPerChan       Unsigned32,
       docsRphyRpdDevCapabNumAsynchVideoChans        Unsigned32,
       docsRphyRpdDevCapabNumCwToneGens              Unsigned32,
       docsRphyRpdDevCapabLowestCwToneFreq           Unsigned32,
       docsRphyRpdDevCapabHighestCwToneFreq          Unsigned32,
       docsRphyRpdDevCapabMaxPwrDedCwTone            Unsigned32,
       docsRphyRpdDevCapabQamAsPilot                 TruthValue,
       docsRphyRpdDevCapabSupportsUdpEncap           TruthValue,
       docsRphyRpdDevCapabSupportsFlowTags           TruthValue,
       docsRphyRpdDevCapabSupportsFreqTilt           TruthValue,
       docsRphyRpdDevCapabMaxTiltValue               Unsigned32,
       docsRphyRpdDevCapabBufferDepthMonAlertSupp    BITS,
       docsRphyRpdDevCapabBufferDepthCfgSupp         BITS,
       docsRphyRpdDevCapabRpdUcdProcTime             Unsigned32,
       docsRphyRpdDevCapabRpdUcdChgNullGrtTime       Unsigned32,
       docsRphyRpdDevCapabMultiSectionTimingMerRep   INTEGER,
       docsRphyRpdDevCapabMinPwrDedCwTone	     Integer32,
       docsRphyRpdDevCapabMaxPwrQamCwTone	     Unsigned32,
       docsRphyRpdDevCapabMinPwrQamCwTone	     Integer32,
       docsRphyRpdDevCapabSupportsOpticalNodeRf      Unsigned32,
       docsRphyRpdDevCapabMaxDsFrequency 	     Unsigned32,
       docsRphyRpdDevCapabMinDsFrequency	     Unsigned32,
       docsRphyRpdDevCapabMaxBasePwr 		     Unsigned32, 
       docsRphyRpdDevCapabMinTiltValue 		     Integer32,
       docsRphyRpdDevCapabMinPwrAdjustScQam 	     Integer32,
       docsRphyRpdDevCapabMaxPwrAdjustScQam 	     Unsigned32,
       docsRphyRpdDevCapabMinPwrAdjustOfdm 	     Integer32,
       docsRphyRpdDevCapabMaxPwrAdjustOfdm	     Unsigned32,
       docsRphyRpdDevCapabVspSelector		     SnmpAdminString,
       docsRphyRpdDevCapabMinBaseUsPowerTarLevel     Integer32,
       docsRphyRpdDevCapabMaxBaseUsPowerTarLevel     Integer32,
       docsRphyRpdDevCapabMinTarRxPowerAdjustScqam   Integer32,
       docsRphyRpdDevCapabMaxTarRxPowerAdjustScqam   Integer32,
       docsRphyRpdDevCapabMinTarRxPowerAdjustOfdma   Integer32,
       docsRphyRpdDevCapabMaxTarRxPowerAdjustOfdma   Integer32,
       docsRphyRpdDevCapabMinTarRxPowerAdjustNdr     Integer32,
       docsRphyRpdDevCapabMaxTarRxPowerAdjustNdr     Integer32
       }
        
docsRphyRpdDevCapabNumDsPorts OBJECT-TYPE
        SYNTAX      Unsigned32 (0..65535)
        MAX-ACCESS  read-only
        STATUS      current
        DESCRIPTION 
            "This attribute provides the number of downstream 
             unidirectional RF ports available on the RPD."
        ::= { docsRphyRpdDevCapabilitiesEntry 1 }
        
docsRphyRpdDevCapabNumUsPorts OBJECT-TYPE
        SYNTAX      Unsigned32 (0..65535)
        MAX-ACCESS  read-only
        STATUS      current
        DESCRIPTION 
            "This attribute provides the number of upstream 
             unidirectional RF ports available on the RPD."
        ::= { docsRphyRpdDevCapabilitiesEntry 2 }
        
docsRphyRpdDevCapabNumTenGeNsPorts OBJECT-TYPE
        SYNTAX      Unsigned32 (0..65535)
        MAX-ACCESS  read-only
        STATUS      current
        DESCRIPTION 
            "This attribute provides the number of 10 Gigabit 
             Ethernet ports supported by the RPD."
        ::= { docsRphyRpdDevCapabilitiesEntry 3 }
        
docsRphyRpdDevCapabNumOneGeNsPorts OBJECT-TYPE
        SYNTAX      Unsigned32 (0..65535)
        MAX-ACCESS  read-only
        STATUS      current
        DESCRIPTION 
            "This attribute provides the number 1 Gigabit 
             Ethernet ports supported by the RPD."
        ::= { docsRphyRpdDevCapabilitiesEntry 4 }
        
docsRphyRpdDevCapabNumDsScQamChans OBJECT-TYPE
        SYNTAX      Unsigned32 (0..65535)
        MAX-ACCESS  read-only
        STATUS      current
        DESCRIPTION 
            "This attribute provides the number of downstream 
             SC-QAM channels supported per downstream RF port."
        ::= { docsRphyRpdDevCapabilitiesEntry 5 }
        
docsRphyRpdDevCapabNumDsOfdmChans OBJECT-TYPE
        SYNTAX      Unsigned32 (0..65535)
        MAX-ACCESS  read-only
        STATUS      current
        DESCRIPTION 
            "This attribute provides the number of downstream 
             DOCSIS 3.1 channels supported per downstream RF port."
        ::= { docsRphyRpdDevCapabilitiesEntry 6 }
        
docsRphyRpdDevCapabNumUsScQamChans OBJECT-TYPE
        SYNTAX      Unsigned32 (0..65535)
        MAX-ACCESS  read-only
        STATUS      current
        DESCRIPTION 
            "This attribute provides the number of upstream 
             SC-QAM channels supported per upstream RF port."
        ::= { docsRphyRpdDevCapabilitiesEntry 7 }
        
docsRphyRpdDevCapabNumUsOfdmaChans OBJECT-TYPE
        SYNTAX      Unsigned32 (0..65535)
        MAX-ACCESS  read-only
        STATUS      current
        DESCRIPTION 
            "This attribute provides the number of upstream 
             DOCSIS 3.1 channels supported per upstream RF port."
        ::= { docsRphyRpdDevCapabilitiesEntry 8 }
        
docsRphyRpdDevCapabNumDsOob55d1Chans OBJECT-TYPE
        SYNTAX      Unsigned32 (0..65535)
        MAX-ACCESS  read-only
        STATUS      current
        DESCRIPTION 
            "This object represents the number of SCTE-55-1 forward 
            (downstream) channels per DS RF port supported by the RPD. 
            The RPD MUST report a value of 1 when it supports a single 
            SCTE 55-1 forward channel per DS RF port. The RPD MUST report 
            a value of 2 when it supports two SCTE 55-1 forward channels 
            per DS RF port."
        ::= { docsRphyRpdDevCapabilitiesEntry 9 }
        
docsRphyRpdDevCapabNumUsOob55d1Chans OBJECT-TYPE
        SYNTAX      Unsigned32 (0..65535)
        MAX-ACCESS  read-only
        STATUS      current
        DESCRIPTION 
            "This attribute provides the number of upstream
             SCTE 55-1 channels supported per upstream RF port."
        ::= { docsRphyRpdDevCapabilitiesEntry 10 }
        
docsRphyRpdDevCapabNumDsOob55d2Modules OBJECT-TYPE
        SYNTAX      Unsigned32 (0..65535)
        MAX-ACCESS  read-only
        STATUS      current
        DESCRIPTION 
            "This attribute provides the number of SCTE 55-2 modules 
             supported."
        ::= { docsRphyRpdDevCapabilitiesEntry 11 }
        
docsRphyRpdDevCapabNumUsOob55d2Demods OBJECT-TYPE
        SYNTAX      Unsigned32 (0..65535)
        MAX-ACCESS  read-only
        STATUS      current
        DESCRIPTION 
            "This attribute provides the number of upstream demodulators 
             per SCTE 55-2 modules supported."
        ::= { docsRphyRpdDevCapabilitiesEntry 12 }
        
docsRphyRpdDevCapabNumNdfChans OBJECT-TYPE
        SYNTAX      Unsigned32 (0..65535)
        MAX-ACCESS  read-only
        STATUS      current
        DESCRIPTION 
            "This attribute provides the number of narrowband digital
             forward channels supported per downstream RF port."
        ::= { docsRphyRpdDevCapabilitiesEntry 13 }
        
docsRphyRpdDevCapabNumNdrChans OBJECT-TYPE
        SYNTAX      Unsigned32 (0..65535)
        MAX-ACCESS  read-only
        STATUS      current
        DESCRIPTION 
            "This attribute provides the number of narrowband digital
             return channels supported per upstream RF port."
        ::= { docsRphyRpdDevCapabilitiesEntry 14 }
              
docsRphyRpdDevCapabNumDsPspFlowsPerChan OBJECT-TYPE
        SYNTAX      Unsigned32 (0..255)
        MAX-ACCESS  read-only
        STATUS      current
        DESCRIPTION 
            "This attribute provides the number of distinct PSP flows
             supported by the RPD on downstream data pseudowires."
        ::= { docsRphyRpdDevCapabilitiesEntry 15 }
        
docsRphyRpdDevCapabNumUsPspFlowsPerChan OBJECT-TYPE
        SYNTAX      Unsigned32 (0..255)
        MAX-ACCESS  read-only
        STATUS      current
        DESCRIPTION 
            "This attribute provides the number of distinct PSP flows
             supported by the RPD on upstream data pseudowires."
        ::= { docsRphyRpdDevCapabilitiesEntry 16 }
        
docsRphyRpdDevCapabNumAsynchVideoChans OBJECT-TYPE
        SYNTAX      Unsigned32 (0..255)
        MAX-ACCESS  read-only
        STATUS      current
        DESCRIPTION 
            "This attribute provides the number of asynchronous 
             MPEG video channels supported per downstream RF port."
        ::= { docsRphyRpdDevCapabilitiesEntry 17 }
        
docsRphyRpdDevCapabNumCwToneGens OBJECT-TYPE
        SYNTAX      Unsigned32 (0..255)
        MAX-ACCESS  read-only
        STATUS      current
        DESCRIPTION 
            "This attribute provides the number of CW tone generators
             supported per downstream RF port."
        ::= { docsRphyRpdDevCapabilitiesEntry 18 }
        
docsRphyRpdDevCapabLowestCwToneFreq OBJECT-TYPE
        SYNTAX      Unsigned32
        UNITS       "Hz"
        MAX-ACCESS  read-only
        STATUS      current
        DESCRIPTION 
            "This attribute provides the lowest frequency supported
             by the CW tone generators."
        ::= { docsRphyRpdDevCapabilitiesEntry 19 }
        
docsRphyRpdDevCapabHighestCwToneFreq OBJECT-TYPE
        SYNTAX      Unsigned32
        UNITS       "Hz"
        MAX-ACCESS  read-only
        STATUS      current
        DESCRIPTION 
            "This attribute provides the highest frequency supported
             by the CW tone generators."
        ::= { docsRphyRpdDevCapabilitiesEntry 20 }
        
docsRphyRpdDevCapabMaxPwrDedCwTone OBJECT-TYPE
        SYNTAX      Unsigned32 (0..65535)
        UNITS       "TenthdB"
        MAX-ACCESS  read-only
        STATUS      current
        DESCRIPTION 
            "The attribute allows the RPD to inform the CCAP Core what 
             is the maximum power level relative to the RF Port's BasePower 
             that is supported by its dedicated CW tone generators."
        ::= { docsRphyRpdDevCapabilitiesEntry 21 }
        
docsRphyRpdDevCapabQamAsPilot OBJECT-TYPE
        SYNTAX      TruthValue
        MAX-ACCESS  read-only
        STATUS      current
        DESCRIPTION 
            "This attribute indicates if a QAM channel can be configured
             as a CW tone. A value of true indicates a QAM channel can 
             be configured as a CW tone. A value of false indicates a 
             QAM channel cannot be configured as a CW tone."
        ::= { docsRphyRpdDevCapabilitiesEntry 22 }
        
docsRphyRpdDevCapabSupportsUdpEncap OBJECT-TYPE
        SYNTAX      TruthValue
        MAX-ACCESS  read-only
        STATUS      current
        DESCRIPTION 
            "This attribute reports whether the RPD supports UDP 
             encapsulation on L2TPv3 pseudowires. A value of true 
             indicates the RPD supports UDP encapsulation on L2TPv3 
             pseudowires. A value of false indicates the RPD does not 
             support UDP encapsulation on L2TPv3 pseudowires."
        ::= { docsRphyRpdDevCapabilitiesEntry 23 }

docsRphyRpdDevCapabSupportsFlowTags OBJECT-TYPE
        SYNTAX      TruthValue
        MAX-ACCESS  read-only
        STATUS      current
        DESCRIPTION 
            "This attribute indicates Flow Tags support capability. If 
             the attribute returns a value of true, the RPD supports 
             Flow Tags on OFDMA channels. A Flow Tag is a 32-bit 
             identifier of a MAC hardware resource (typically a Service 
             Flow). The Flow Tag can be assigned to the scheduled SID by 
             the CCAP Core. The RPD provides Flow Tags in UEPI headers 
             for OFDMA channels. If the attribute returns a value of 
             false, the RPD does not support Flow Tags."
        ::= { docsRphyRpdDevCapabilitiesEntry 24 }
        
docsRphyRpdDevCapabSupportsFreqTilt OBJECT-TYPE
        SYNTAX      TruthValue
        MAX-ACCESS  read-only
        STATUS      current
        DESCRIPTION 
            "This attribute indicates Frequency Tilt support capability. 
             If the attribute returns a value of true, the RPD supports 
             Frequency Tilt settings on DS RF Ports. If the attribute 
             returns a value of false, the RPD does not support 
             Frequency Tilt settings."
        ::= { docsRphyRpdDevCapabilitiesEntry 25 }
        
docsRphyRpdDevCapabMaxTiltValue OBJECT-TYPE
        SYNTAX      Unsigned32 (0..65535)
        MAX-ACCESS  read-only
        STATUS      current
        DESCRIPTION 
            "This attribute indicates the maximum value of tilt settings that 
             the RPD supports."
        ::= { docsRphyRpdDevCapabilitiesEntry 26 }
        
docsRphyRpdDevCapabBufferDepthMonAlertSupp OBJECT-TYPE
        SYNTAX      BITS {
                          ofdmChannels(0),
                          scQamDocsisChannels(1),
                          scQamVideoChannels(2),
                          ndfChannels(3),
                          scte551Channels(4),
                          scte552Channels(5)
                         }
        MAX-ACCESS  read-only
        STATUS      current
        DESCRIPTION 
            "This attribute indicates buffer depth monitoring alert 
             supported by the RPD.  For each bit set to 1, the RPD 
             is capable of monitoring buffer depth on the corresponding 
             types of downstream channels."
        ::= { docsRphyRpdDevCapabilitiesEntry 27 }
        
docsRphyRpdDevCapabBufferDepthCfgSupp OBJECT-TYPE
        SYNTAX      BITS {
                          ofdmChannels(0),
                          scQamDocsisChannels(1)
                         }
        MAX-ACCESS  read-only
        STATUS      current
        DESCRIPTION 
            "This attribute indicates configuration of the output buffer 
             depth supported by the RPD.  This capability is only 
             applicable to DOCSIS downstream channels. For each bit set 
             to 1, the RPD is capable of configuring output buffer depth 
             of the corresponding types of downstream channels."
        ::= { docsRphyRpdDevCapabilitiesEntry 28 }
        
docsRphyRpdDevCapabRpdUcdProcTime OBJECT-TYPE
        SYNTAX      Unsigned32 (0..65535)
        MAX-ACCESS  read-only
        STATUS      current
        DESCRIPTION 
            "This attribute indicates the minimum interval needed by the 
             RPD to process a UCD message received via GCP. This 
             interval is equivalent to CM UCD processing time defined in 
             MULPIv3.1 but its duration can be longer. The maximum value 
             of the RPD UCD Processing time is 50000 usec. The minimum 
             value RPD UCD Processing time is equal to CM UCD processing 
             time (1500 usec for each changed SC-QAM channel or 2000 usec 
             for each changed upstream OFDMA channel) defined in 
             MULPIv3.1."
        ::= { docsRphyRpdDevCapabilitiesEntry 29 }
        
docsRphyRpdDevCapabRpdUcdChgNullGrtTime OBJECT-TYPE
        SYNTAX      Unsigned32 (0..65535)
        MAX-ACCESS  read-only
        STATUS      current
        DESCRIPTION 
            "This attribute indicates the minimum Null grant interval 
             needed by the RPD in the first MAP with incremented UCD 
             change count. The RPD uses the Null grant in the first 
             MAP Message to programs registers of its burst receiver 
             during this interval. The maximum value of the RPD UCD 
             Change Null Grant Time is 4000 usec for each changed channel.
             The minimum value of the RPD UCD Change Null Grant Time is 
             defined in MULPIv3.1."
        ::= { docsRphyRpdDevCapabilitiesEntry 30 }
        
docsRphyRpdDevCapabMultiSectionTimingMerRep OBJECT-TYPE
        SYNTAX      INTEGER {
                             notSupported(0),
                             supportType1(1),
                             supportType2(2)
                             }
        MAX-ACCESS  read-only
        STATUS      current
        DESCRIPTION 
            "This attribute indicates whether the RPD supports 
             Multi-Section Timing and MER reporting as opposed to just 
             reporting a single average Timing and MER.  More detail 
             is documented in the UEPI Probe Pseudowire format of 
             R-UEPI.
             
             notSupported: The RPD does not support Multi-Section Timing 
             and MER Reporting
             
             supportType1: The RPD supports equally spaced 
             non-overlapping sections
             
             supportType2: The RPD supports fully flexible sections and 
             spacing of non-overlapping sections."
	 ::= { docsRphyRpdDevCapabilitiesEntry 31 }

docsRphyRpdDevCapabMinPwrDedCwTone OBJECT-TYPE
	 SYNTAX  Integer32 (-32768..32767)
	 UNITS "TenthDB"
	 MAX-ACCESS  read-only
	 STATUS  current
	 DESCRIPTION
	     "The object allows the RPD to inform the CCAP Core what is
	      the minimum power level relative to the RF Port's BasePower
	      that is supported by its dedicated CW tone generators. "
	 ::= { docsRphyRpdDevCapabilitiesEntry 32 }

docsRphyRpdDevCapabMaxPwrQamCwTone OBJECT-TYPE
	 SYNTAX	    Unsigned32 (0..65535)
	 UNITS "TenthDB"
	 MAX-ACCESS  read-only
	 STATUS  current
	 DESCRIPTION
	     "The object allows the RPD to inform the CCAP Core what is
	      the maximum power level setting relative to the RF Port's
	      BasePower that is supported by its QAM channels operating
	      as CW tone generators."
	 ::= { docsRphyRpdDevCapabilitiesEntry 33 }


docsRphyRpdDevCapabMinPwrQamCwTone OBJECT-TYPE
	 SYNTAX  Integer32 (-32768..32767)
	 UNITS "TenthDB"
	 MAX-ACCESS  read-only
	 STATUS  current
	 DESCRIPTION
	     "The object allows the RPD to inform the CCAP Core what is
	      the minimum power level setting relative to the RF Port's
	      BasePower that is supported by its QAM channels operating
	      as CW tone generators."
	 ::= { docsRphyRpdDevCapabilitiesEntry 34 }
     


docsRphyRpdDevCapabSupportsOpticalNodeRf OBJECT-TYPE
	 SYNTAX  Unsigned32 (0..255)
	 MAX-ACCESS  read-only
	 STATUS  current
	 DESCRIPTION
	     "This atribute allows the RPD to indicate whether it supports
	      the RF technology associated with optical node."
	 ::= {docsRphyRpdDevCapabilitiesEntry 35 }
 
     

docsRphyRpdDevCapabMaxDsFrequency OBJECT-TYPE
	 SYNTAX  Unsigned32
	 UNITS "Hz"
	 MAX-ACCESS  read-only
	 STATUS  current
	 DESCRIPTION
	     "This attribute reports the maximum frequency of any downstream
	      signal that the RPD supports on its DS RF port. This attribute
	      defines the highest frequency of the encompassed spectrum of the
	      highest frequency downstream channel or OOB signal."
	 ::= { docsRphyRpdDevCapabilitiesEntry 36 }

docsRphyRpdDevCapabMinDsFrequency OBJECT-TYPE
	 SYNTAX  Unsigned32
	 UNITS "Hz"
	 MAX-ACCESS  read-only
	 STATUS  current
	 DESCRIPTION
	     "This attribute reports the minimum frequency of any downstream
	      signal that the RPD supports on its DS RF port. . This attribute
	      defines the lowest frequency of the encompassed spectrum of the
	      lowest frequency downstream channel or OOB signal."
	 ::= { docsRphyRpdDevCapabilitiesEntry 37 }



docsRphyRpdDevCapabMaxBasePwr OBJECT-TYPE
	 SYNTAX  Unsigned32 (0..65535)
	 UNITS "TenthDB"
	 MAX-ACCESS  read-only
	 STATUS  current
	 DESCRIPTION
	     "This attribute reports the maximum power level setting that the
RPD supports for downstream RF port."
	 ::= { docsRphyRpdDevCapabilitiesEntry 38  }

     
     
docsRphyRpdDevCapabMinTiltValue OBJECT-TYPE
	 SYNTAX  Integer32 (-32768..32767)
	 UNITS "TenthDB"
	 MAX-ACCESS  read-only
	 STATUS  current
	 DESCRIPTION
	     "This attribute reports the minimum value of the tilt setting that
	      the RPD supports. Note that the RPD can report this value as a
	      negative number."
	 ::= {  docsRphyRpdDevCapabilitiesEntry 39 }


docsRphyRpdDevCapabMinPwrAdjustScQam OBJECT-TYPE
	 SYNTAX  Integer32 (-32768..32767)
	 UNITS "TenthDB"
	 MAX-ACCESS  read-only
	 STATUS  current
	 DESCRIPTION
	     "This attribute reports the minimum power adjustment value that the
RPD supports for downstream SC-QAM channels."
	 ::= { docsRphyRpdDevCapabilitiesEntry 40 }

docsRphyRpdDevCapabMaxPwrAdjustScQam OBJECT-TYPE
	 SYNTAX  Unsigned32 (0..65535)
	 UNITS "TenthDB"
	 MAX-ACCESS  read-only
	 STATUS  current
	 DESCRIPTION
	     "This attribute reports the maximum power adjustment that the RPD
	      supports for downstream SC-QAM channel."
	 ::= { docsRphyRpdDevCapabilitiesEntry 41 }


docsRphyRpdDevCapabMinPwrAdjustOfdm OBJECT-TYPE
	 SYNTAX  Integer32  (-32768..32767)
	 UNITS "TenthDB"
	 MAX-ACCESS  read-only
	 STATUS  current
	 DESCRIPTION
	     "This attribute reports the minimum power adjustment value that the
	      RPD supports for downstream OFDM channels."
	 ::= { docsRphyRpdDevCapabilitiesEntry 42 }

     
docsRphyRpdDevCapabMaxPwrAdjustOfdm OBJECT-TYPE
	 SYNTAX  Unsigned32 (0..65535)
	 UNITS "TenthDB"
	 MAX-ACCESS  read-only
	 STATUS  current
	 DESCRIPTION
	     "This attribute reports the maximum power adjustment that the RPD
	      supports for downstream OFDM channels."
	  ::= {  docsRphyRpdDevCapabilitiesEntry 43 }

docsRphyRpdDevCapabVspSelector OBJECT-TYPE
	 SYNTAX  SnmpAdminString
	 MAX-ACCESS  read-only
	 STATUS  current
	 DESCRIPTION
	     "This attribute contains the Vendor-Specific Pre-configuration 
              (VSP) Selector advertised by the RPD, defined as a human 
              readable string. This attribute is used by the Principal 
              CCAP Core to match the RPD to VSP configuration maintained 
              on the CCAP Core and to deliver VSP configuration to the RPD 
              during initialization. If the RPD does not support VSP the 
              RPD communicates VSP as a zero-length string."
	 ::= {  docsRphyRpdDevCapabilitiesEntry 44 }

docsRphyRpdDevCapabMinBaseUsPowerTarLevel OBJECT-TYPE
	 SYNTAX  Integer32 (-32768..32767)  
	 UNITS "TenthdBmV"
	 MAX-ACCESS  read-only
	 STATUS  current
	 DESCRIPTION
	     "This attribute reports the minimum value of the base target power 
              reference level for upstream signals received on all upstream channels
              on an RF port that the RPD supports."
	 ::= { docsRphyRpdDevCapabilitiesEntry 45 }

docsRphyRpdDevCapabMaxBaseUsPowerTarLevel OBJECT-TYPE
	 SYNTAX  Integer32 (-32768..32767)  
	 UNITS "TenthdBmV"
	 MAX-ACCESS  read-only
	 STATUS  current
	 DESCRIPTION
	     "This attribute reports the maximum value of the base target power
              reference level for upstream signals received on all upstream channels
              on an RF port that the RPD supports."
	 ::= { docsRphyRpdDevCapabilitiesEntry 46 }

docsRphyRpdDevCapabMinTarRxPowerAdjustScqam OBJECT-TYPE
	 SYNTAX  Integer32 (-32768..32767)  
	 UNITS "TenthdB"
	 MAX-ACCESS  read-only
	 STATUS  current
	 DESCRIPTION
	     "This attribute reports the minimum power adjustment
              to the base target power level that the RPD supports
              for SC-QAM channels."
	 ::= { docsRphyRpdDevCapabilitiesEntry 47 }

docsRphyRpdDevCapabMaxTarRxPowerAdjustScqam OBJECT-TYPE
	 SYNTAX  Integer32 (-32768..32767)  
	 UNITS "TenthdB"
	 MAX-ACCESS  read-only
	 STATUS  current
	 DESCRIPTION
	     "This attribute reports the maximum power adjustment
              to the base target power level that the RPD supports
              for SC-QAM channels."
	 ::= { docsRphyRpdDevCapabilitiesEntry 48 }

docsRphyRpdDevCapabMinTarRxPowerAdjustOfdma OBJECT-TYPE
	 SYNTAX  Integer32 (-32768..32767)  
	 UNITS "TenthdB"
	 MAX-ACCESS  read-only
	 STATUS  current
	 DESCRIPTION
	     "This attribute reports the minimum power adjustment
              to the base target power level that the RPD supports
              for OFDMA channels."
	 ::= { docsRphyRpdDevCapabilitiesEntry 49 }

docsRphyRpdDevCapabMaxTarRxPowerAdjustOfdma OBJECT-TYPE
	 SYNTAX  Integer32 (-32768..32767)  
	 UNITS "TenthdB"
	 MAX-ACCESS  read-only
	 STATUS  current
	 DESCRIPTION
	     "This attribute reports the maximum power adjustment
              to the base target power level that the RPD supports
              for OFDMA channels."
	 ::= { docsRphyRpdDevCapabilitiesEntry 50 }

docsRphyRpdDevCapabMinTarRxPowerAdjustNdr OBJECT-TYPE
	 SYNTAX  Integer32 (-32768..32767)  
	 UNITS "TenthdB"
	 MAX-ACCESS  read-only
	 STATUS  current
	 DESCRIPTION
	     "This attribute reports the minimum power adjustment
              to the base target power level that the RPD supports
              for NDR channels."
	 ::= { docsRphyRpdDevCapabilitiesEntry 51 }

docsRphyRpdDevCapabMaxTarRxPowerAdjustNdr OBJECT-TYPE
	 SYNTAX  Integer32 (-32768..32767)  
	 UNITS "TenthdB"
	 MAX-ACCESS  read-only
	 STATUS  current
	 DESCRIPTION
	     "This attribute reports the maximum power adjustment
              to the base target power level that the RPD supports
              for NDR channels."
	 ::= { docsRphyRpdDevCapabilitiesEntry 52 }

       
-- ---------------------------------------------------------------------
-- RPD Channel Reachability Table
-- ---------------------------------------------------------------------

docsRphyRpdDevChanReachabilityTable OBJECT-TYPE
        SYNTAX      SEQUENCE OF DocsRphyRpdDevChanReachabilityEntry
        MAX-ACCESS  not-accessible
        STATUS      current
        DESCRIPTION
            "This table provides RPD channel reachability constraints. 
             In some RPD implementations, an Ethernet interface might 
             not have connectivity to all channels on a port of the RPD.
             This table is only populated if reachability constraints 
             exist on the RPD."
        ::= { docsRphyRpdDevMibObjects 6 }


docsRphyRpdDevChanReachabilityEntry OBJECT-TYPE
        SYNTAX     DocsRphyRpdDevChanReachabilityEntry
        MAX-ACCESS not-accessible
        STATUS     current
        DESCRIPTION
            "The conceptual row of docsRphyRpdDevChanReachabilityTable."
        INDEX { docsRphyRpdDevInfoUniqueId,
                docsRphyRpdDevChanReachabilityEnetPortIndex,
                docsRphyRpdDevChanReachabilityRfPortIndex,
                docsRphyRpdDevChanReachabilityChanType,
                docsRphyRpdDevChanReachabilityStartChanIndex }
        ::= { docsRphyRpdDevChanReachabilityTable 1 }


DocsRphyRpdDevChanReachabilityEntry ::= SEQUENCE
       {
       docsRphyRpdDevChanReachabilityEnetPortIndex       Unsigned32,
       docsRphyRpdDevChanReachabilityRfPortIndex         Unsigned32,
       docsRphyRpdDevChanReachabilityChanType            RphyChannelType,
       docsRphyRpdDevChanReachabilityStartChanIndex      Unsigned32,
       docsRphyRpdDevChanReachabilityEndChanIndex        Unsigned32
       }
        
docsRphyRpdDevChanReachabilityEnetPortIndex OBJECT-TYPE
        SYNTAX      Unsigned32 (0..255)
        MAX-ACCESS  not-accessible 
        STATUS      current 
        DESCRIPTION 
            "This attribute identifies the Ethernet port on the RPD
             that has the connectivity constraint."
        ::= { docsRphyRpdDevChanReachabilityEntry 1 }


docsRphyRpdDevChanReachabilityRfPortIndex OBJECT-TYPE
        SYNTAX      Unsigned32 (0..255)
        MAX-ACCESS  not-accessible
        STATUS      current
        DESCRIPTION 
            "This attribute identifies the RF port with which the 
             Ethernet port has a connectivity constraint."
        ::= { docsRphyRpdDevChanReachabilityEntry 2 }
        
docsRphyRpdDevChanReachabilityChanType OBJECT-TYPE
        SYNTAX      RphyChannelType
        MAX-ACCESS  not-accessible
        STATUS      current
        DESCRIPTION 
            "This attribute identifies the type of channel that is supported
             within the specified channel index range on this RF port from the 
             specified Ethernet interface. A row entry will be created for each 
             channel type with a constraint. Absence of a row for a channel type 
             means there is no constraint for that channel type."
        ::= { docsRphyRpdDevChanReachabilityEntry 3 }
        
docsRphyRpdDevChanReachabilityStartChanIndex OBJECT-TYPE
        SYNTAX      Unsigned32 (0..255)
        MAX-ACCESS  not-accessible
        STATUS      current
        DESCRIPTION 
            "This attribute identifies the first channel of the 
             specified channel type in the range of channels that 
             does not have connectivity to the specified Ethernet port."
        ::= { docsRphyRpdDevChanReachabilityEntry 4 }
        
docsRphyRpdDevChanReachabilityEndChanIndex OBJECT-TYPE
        SYNTAX      Unsigned32 (0..255)
        MAX-ACCESS  read-only
        STATUS      current
        DESCRIPTION 
            "This attribute identifies the last channel of the 
             specified channel type in the range of channels that 
             does not have connectivity to the specified Ethernet port."
        ::= { docsRphyRpdDevChanReachabilityEntry 5 }
        
        
-- ---------------------------------------------------------------------
-- RPD DS/US RF Port Allocation Table
-- ---------------------------------------------------------------------

docsRphyRpdDevDsUsRfPortAllocTable OBJECT-TYPE
        SYNTAX      SEQUENCE OF DocsRphyRpdDevDsUsRfPortAllocEntry
        MAX-ACCESS  not-accessible
        STATUS      current
        DESCRIPTION
            "This table provides the allocation status for the 
             downstream channel resources on the RPD on a per DS RF port 
             basis as well as for the upstream channel resources on a 
             per US RF port basis."
        ::= { docsRphyRpdDevMibObjects 7 }


docsRphyRpdDevDsUsRfPortAllocEntry OBJECT-TYPE
        SYNTAX     DocsRphyRpdDevDsUsRfPortAllocEntry
        MAX-ACCESS not-accessible
        STATUS     current
        DESCRIPTION
            "The conceptual row of docsRphyRpdDevDsUsRfPortAllocTable."
        INDEX { docsRphyRpdDevInfoUniqueId, 
                docsRphyRpdDevDsUsRfPortAllocIndex, 
                docsRphyRpdDevDsUsRfPortAllocDirection }
        ::= { docsRphyRpdDevDsUsRfPortAllocTable 1 }


DocsRphyRpdDevDsUsRfPortAllocEntry ::= SEQUENCE
       {
       docsRphyRpdDevDsUsRfPortAllocIndex              Unsigned32,
       docsRphyRpdDevDsUsRfPortAllocDirection          IfDirection,
       docsRphyRpdDevDsUsRfPortAllocScQamChans         Unsigned32,
       docsRphyRpdDevDsUsRfPortAllocOfdmChans          Unsigned32,
       docsRphyRpdDevDsUsRfPortAllocOob551Chans        Unsigned32,
       docsRphyRpdDevDsUsRfPortAllocNdChans            Unsigned32
       }
        
docsRphyRpdDevDsUsRfPortAllocIndex OBJECT-TYPE
        SYNTAX      Unsigned32 (0..255)
        MAX-ACCESS  not-accessible 
        STATUS      current 
        DESCRIPTION 
            "This attribute provides the index of the downstream or
             upstream RF port for which resource allocation is being 
             reported."
        ::= { docsRphyRpdDevDsUsRfPortAllocEntry 1 }
        
docsRphyRpdDevDsUsRfPortAllocDirection OBJECT-TYPE
        SYNTAX      IfDirection
        MAX-ACCESS  not-accessible 
        STATUS      current 
        DESCRIPTION 
            "This attribute indicates whether the allocation
             applies to the upstream or downstream RF Port."
        ::= { docsRphyRpdDevDsUsRfPortAllocEntry 2 }

docsRphyRpdDevDsUsRfPortAllocScQamChans OBJECT-TYPE
        SYNTAX      Unsigned32 (0..65535)
        MAX-ACCESS  read-only
        STATUS      current
        DESCRIPTION 
            "This attribute provides the number of allocated SC-QAM
             channels on this RF port."
        ::= { docsRphyRpdDevDsUsRfPortAllocEntry 3 }
        
docsRphyRpdDevDsUsRfPortAllocOfdmChans OBJECT-TYPE
        SYNTAX      Unsigned32 (0..65535)
        MAX-ACCESS  read-only
        STATUS      current
        DESCRIPTION 
            "This attribute provides the number of allocated DOCSIS 3.1
             channels on this RF port."
        ::= { docsRphyRpdDevDsUsRfPortAllocEntry 4 }
        
docsRphyRpdDevDsUsRfPortAllocOob551Chans OBJECT-TYPE
        SYNTAX      Unsigned32 (0..65535)
        MAX-ACCESS  read-only
        STATUS      current
        DESCRIPTION 
            "This attribute provides the number of allocated SCTE 55-1
             channels on this RF port."
        ::= { docsRphyRpdDevDsUsRfPortAllocEntry 5 }
        
docsRphyRpdDevDsUsRfPortAllocNdChans OBJECT-TYPE
        SYNTAX      Unsigned32 (0..65535)
        MAX-ACCESS  read-only
        STATUS      current
        DESCRIPTION 
            "This attribute provides the number of allocated narrowband
             digital forward channels (for DS RF Ports) or narrowband
             digital return channels (for US RF Ports) on this RF port."
        ::= { docsRphyRpdDevDsUsRfPortAllocEntry 6 }
  
-- ---------------------------------------------------------
-- RPD L2TP Session Info Table 
-- ---------------------------------------------------------
                 
docsRphyRpdDevL2tpSessionInfoTable OBJECT-TYPE
    SYNTAX      SEQUENCE OF DocsRphyRpdDevL2tpSessionInfoEntry
    MAX-ACCESS  not-accessible
    STATUS      current
    DESCRIPTION
            "This table provides details about each tunnel 
             session between the RPD and each CCAP Core with which the 
             RPD is associated from the RPD's point of view
             The attributes in this table are used to create an entry 
             for each L2TPv3 tunnel (session) terminated at an R-PHY 
             entity (RPD)."
    ::= { docsRphyRpdDevMibObjects 8 }

docsRphyRpdDevL2tpSessionInfoEntry OBJECT-TYPE
    SYNTAX      DocsRphyRpdDevL2tpSessionInfoEntry
    MAX-ACCESS  not-accessible
    STATUS      current
    DESCRIPTION
            "The conceptual row of docsRphyRpdDevL2tpSessionInfoTable.
             A row entry is created for every session the RPD 
             terminates and there may be entries for sessions with 
             different CCAP-Cores if the RPD is connected with one 
             or more auxiliary cores."
    INDEX { docsRphyRpdDevInfoUniqueId,
            docsRphyRpdDevL2tpSessionInfoSessionIpAddrType,
            docsRphyRpdDevL2tpSessionInfoCcapLcceIpAddr,
            docsRphyRpdDevL2tpSessionInfoRpdLcceIpAddr,
            docsRphyRpdDevL2tpSessionInfoDirection,
            docsRphyRpdDevL2tpSessionInfoL2tpSessionId }
    ::= { docsRphyRpdDevL2tpSessionInfoTable 1 }

DocsRphyRpdDevL2tpSessionInfoEntry ::= SEQUENCE
    {
    docsRphyRpdDevL2tpSessionInfoSessionIpAddrType     InetAddressType,
    docsRphyRpdDevL2tpSessionInfoCcapLcceIpAddr        InetAddress,
    docsRphyRpdDevL2tpSessionInfoRpdLcceIpAddr         InetAddress,
    docsRphyRpdDevL2tpSessionInfoDirection             INTEGER,
    docsRphyRpdDevL2tpSessionInfoL2tpSessionId         Unsigned32,
    docsRphyRpdDevL2tpSessionInfoCoreId                MacAddress,
    docsRphyRpdDevL2tpSessionInfoConnCtrlID            Unsigned32,
    docsRphyRpdDevL2tpSessionInfoUdpPort               InetPortNumber,
    docsRphyRpdDevL2tpSessionInfoDescr                 SnmpAdminString,
    docsRphyRpdDevL2tpSessionInfoSessionType           INTEGER,
    docsRphyRpdDevL2tpSessionInfoSessionSubType        INTEGER,
    docsRphyRpdDevL2tpSessionInfoMaxPayload            Unsigned32,
    docsRphyRpdDevL2tpSessionInfoPathPayload           Unsigned32,
    docsRphyRpdDevL2tpSessionInfoRpdIfMtu              Unsigned32,
    docsRphyRpdDevL2tpSessionInfoCoreIfMtu             Unsigned32,
    docsRphyRpdDevL2tpSessionInfoErrorCode             INTEGER,
    docsRphyRpdDevL2tpSessionInfoCreationTime          TimeStamp,
    docsRphyRpdDevL2tpSessionInfoOperStatus            OperStatusType,
    docsRphyRpdDevL2tpSessionInfoLocalStatus           BITS,
    docsRphyRpdDevL2tpSessionInfoLastChange            TimeStamp
    }

docsRphyRpdDevL2tpSessionInfoSessionIpAddrType OBJECT-TYPE
    SYNTAX      InetAddressType
    MAX-ACCESS  not-accessible
    STATUS      current
    DESCRIPTION 
            "This key attribute indicates whether the IP address
             provided in the CcapLcceIpAddress and RpdLcceIpAddr 
             attributes are IPv4 or IPv6."
    ::= { docsRphyRpdDevL2tpSessionInfoEntry 1 }

docsRphyRpdDevL2tpSessionInfoCcapLcceIpAddr OBJECT-TYPE
    SYNTAX      InetAddress
    MAX-ACCESS  not-accessible
    STATUS      current
    DESCRIPTION 
            "This key attribute provides the LCCE IP address on the
             CCAP Core of the session detailed in the instance. As
             reported by the RPD for a static multicast session, 
             this attribute is zero for an any source multicast and 
             the source IP for Source Specific Multicast (SSM)."
    ::= { docsRphyRpdDevL2tpSessionInfoEntry 2 }

docsRphyRpdDevL2tpSessionInfoRpdLcceIpAddr OBJECT-TYPE
    SYNTAX      InetAddress
    MAX-ACCESS  not-accessible
    STATUS      current
    DESCRIPTION 
            "This key attribute reports the remote-side
             RPD LCCE IP address of the session detailed
             in the instance."
    ::= { docsRphyRpdDevL2tpSessionInfoEntry 3 }
    
docsRphyRpdDevL2tpSessionInfoDirection OBJECT-TYPE
    SYNTAX      INTEGER {
                           forward(0),
                           return(1)
                        }
    MAX-ACCESS  not-accessible
    STATUS      current
    DESCRIPTION 
            "This key attribute reports the direction of the session detailed in the instance.  
             Valid values include:
             'forward' - Forward (downstream) direction toward the RPD.
             'return' -  Return (upstream) direction toward the CCAP Core."
    ::= { docsRphyRpdDevL2tpSessionInfoEntry 4 }

docsRphyRpdDevL2tpSessionInfoL2tpSessionId OBJECT-TYPE
    SYNTAX      Unsigned32
    MAX-ACCESS  not-accessible
    STATUS      current
    DESCRIPTION 
            "This key attribute reports the value of the 
            L2TPv3 session ID transmitted or received on 
            the session. "
    ::= { docsRphyRpdDevL2tpSessionInfoEntry 5 }
    
docsRphyRpdDevL2tpSessionInfoCoreId OBJECT-TYPE
    SYNTAX      MacAddress
    MAX-ACCESS  read-only
    STATUS      current
    DESCRIPTION 
            "This attribute provides the MAC address of the CCAP Core 
             with which this session terminates. The CCAP Core sends its
             MAC address to the RPD periodically via the DOCSIS SYNC MAC
             Message in the Source Address field."
    ::= { docsRphyRpdDevL2tpSessionInfoEntry 6 }
    
docsRphyRpdDevL2tpSessionInfoConnCtrlID OBJECT-TYPE
    SYNTAX      Unsigned32
    MAX-ACCESS  read-only
    STATUS      current
    DESCRIPTION 
            "This attribute indicates the control connection
             identifier (CCID) for this session."
    ::= { docsRphyRpdDevL2tpSessionInfoEntry 7 }
    
docsRphyRpdDevL2tpSessionInfoUdpPort OBJECT-TYPE
    SYNTAX      InetPortNumber
    MAX-ACCESS  read-only
    STATUS      current
    DESCRIPTION 
            "This attribute provides the UDP Port reported by the RPD
             when the DEPI session uses L2TPv3 Header Over
             UDP. This attribute reports a value of 0 when the session 
             is running with the L2TPv3 Session IP Header. 
             This port number is negotiated between the CCAP Core and 
             the RPD according to the L2TPv3 RFC."
    ::= { docsRphyRpdDevL2tpSessionInfoEntry 8 }
    
docsRphyRpdDevL2tpSessionInfoDescr OBJECT-TYPE
    SYNTAX      SnmpAdminString
    MAX-ACCESS  read-only
    STATUS      current
    DESCRIPTION 
            "This attribute provides an ASCII string constructed with
             the form:
             
             RemoteEndId=(pp:mmm:ccc), ...  
                  { repeated for multiple endpoints } 

             where
             pp is the 0-based port num signaled in the RemoteEndId AVP
             mmm is the channel-type enum value from the RemoteEndId AVP 
             ccc is the channel number from the RemoteEndId AVP."
    ::= { docsRphyRpdDevL2tpSessionInfoEntry 9 }
    
docsRphyRpdDevL2tpSessionInfoSessionType OBJECT-TYPE
    SYNTAX      INTEGER {
                           psp(1),
                           mpt(2)
                        }
    MAX-ACCESS  read-only
    STATUS      current
    DESCRIPTION 
            "This attribute specifies whether the session is an MPT 
             session or PSP session."
    ::= { docsRphyRpdDevL2tpSessionInfoEntry 10 }
    
docsRphyRpdDevL2tpSessionInfoSessionSubType OBJECT-TYPE
    SYNTAX      INTEGER {
                           mptLegacy(1),
                           pspLegacy(2),
                           mcm(3),
                           pspDepiMultichannel(4),
                           pspUepiScQam(5),
                           pspUepiOfdma(6),
                           pspBwReqScQam(7),
                           pspBwReqOfdma(8),
                           pspProbe(9),
                           pspRngReqScQam(10),
                           pspRngReqOfdma(11),
                           pspMapScQam(12),
                           pspMapOfdma(13),
                           pspSpecman(14),
                           pspPnm(15),
                           psp551Fwd(16),
                           psp551Ret(17),
                           psp552Fwd(18),
                           psp552Ret(19),
                           pspNdf(20),
                           pspNdr(21)
                        }
    MAX-ACCESS  read-only
    STATUS      current
    DESCRIPTION 
            "This attribute specifies the type of DEPI MPT or DEPI 
             PSP session."
    ::= { docsRphyRpdDevL2tpSessionInfoEntry 11 }

docsRphyRpdDevL2tpSessionInfoMaxPayload OBJECT-TYPE
    SYNTAX      Unsigned32
    MAX-ACCESS  read-only
    STATUS      current
    DESCRIPTION 
            "This attribute indicates the maximum MTU negotiated between
             the CCAP Core and the RPD during the session establishment 
             process. It considers the header subtractions as indicated 
             in the DEPI specification."
    REFERENCE
            "DEPI specification, Signaling
             DEPI specification Annex A."
    ::= { docsRphyRpdDevL2tpSessionInfoEntry 12 }

docsRphyRpdDevL2tpSessionInfoPathPayload OBJECT-TYPE
    SYNTAX      Unsigned32
    MAX-ACCESS  read-only
    STATUS      current
    DESCRIPTION 
            "This attribute indicates the maximum MTU traversing the CIN
             from CCAP Core to the RPD. This is calculated by the CCAP 
             Core by procedures such as MTU discovery as described in 
             the DEPI specification."
    REFERENCE
            "DEPI specification, Network MTU"
    ::= { docsRphyRpdDevL2tpSessionInfoEntry 13 }
    
docsRphyRpdDevL2tpSessionInfoRpdIfMtu OBJECT-TYPE
    SYNTAX      Unsigned32
    MAX-ACCESS  read-only
    STATUS      current
    DESCRIPTION 
            "This attribute provides the RPD's CIN interface MTU and is
             read as the value of the following L2TPV3 AVP transmitted 
             by the RPD during session setup:
             
             DEPI Downstream PW          UEPI Upstream PW
             DEPI Remote MTU AVP (ICRP)  UEPI Remote MTU AVP (ICRP)."
    ::= { docsRphyRpdDevL2tpSessionInfoEntry 14 }
    
docsRphyRpdDevL2tpSessionInfoCoreIfMtu OBJECT-TYPE
    SYNTAX      Unsigned32
    MAX-ACCESS  read-only
    STATUS      current
    DESCRIPTION 
            "This attribute provides the CCAP Core's CIN interface MTU
             and is read as the value of the following L2TPv3 AVP as 
             received by the device during session setup:
             
             DEPI Downstream PW          UEPI Upstream PW
             DEPI Local MTU AVP (ICRQ)   UEPI Local MTU AVP (ICRQ)."
    ::= { docsRphyRpdDevL2tpSessionInfoEntry 15 }

docsRphyRpdDevL2tpSessionInfoErrorCode OBJECT-TYPE
    SYNTAX      INTEGER {
                          none(1),
                          invalidMACInterfaceValue(2),
                          invalidInterfaceValue(3),
                          noResourcesForInterfaceIndex(4),
                          l2tpv3Error(5),
                          ifAdminStatusSetToDown(6)
                        }
    MAX-ACCESS  read-only
    STATUS      current
    DESCRIPTION 
            "The error code raised when the session is in an error
            state. 
            'invalidMACInterfaceValue'  
               Indicates wrong assignment of the CCAP Core MAC interface
               ifIndex.
            'invalidInterfaceValue'  
               Indicates wrong assignment of the CCAP Core Downstream 
               interface ifIndex
            'noResourcesForInterfaceIfIndex' 
               Indicates the CCAP Core has no more resources to
               assign a session to this entry.
            'l2tpv3Error'
               An L2TPv3 StopCCN or CDN message was issued 
            'ifAdminStatusSetToDown'
               Indicates the ifAdminStatus was set to down and the
               session was torn down."
    ::= { docsRphyRpdDevL2tpSessionInfoEntry 16 }

docsRphyRpdDevL2tpSessionInfoCreationTime OBJECT-TYPE
    SYNTAX      TimeStamp
    MAX-ACCESS  read-only
    STATUS      current
    DESCRIPTION 
            "The attribute contains the sysUptime when the entry was 
             turned active."
    ::= { docsRphyRpdDevL2tpSessionInfoEntry 17 }
    
docsRphyRpdDevL2tpSessionInfoOperStatus OBJECT-TYPE
    SYNTAX      OperStatusType
    MAX-ACCESS  read-only
    STATUS      current
    DESCRIPTION 
            "This attribute provides the current status of the 
             pseudowire from the point of view of the specific 
             reporting entity (RPD).For static psuedowires,
             the only values that the RPD can report are 'up' and 
             'down'. 
             These values are conveyed to the Core via the 
             RpdCircuitStatus TLV (TLV 59.1.3)."
    ::= { docsRphyRpdDevL2tpSessionInfoEntry 18 }

docsRphyRpdDevL2tpSessionInfoLocalStatus OBJECT-TYPE
    SYNTAX      BITS {
                      other(0),
                      pwNotForwarding(1), 
                      servicePwRxFault(2), 
                      servicePwTxFault(3), 
                      psnPwRxFault(4), 
                      psnPwTxFault(5)
    }
    MAX-ACCESS  read-only
    STATUS      current
    DESCRIPTION 
            "The attribute provides the status of the pseudowire 
             in the local node. If the 'other' bit is set, it indicates
             that an additional vendor-specific status is reported. 
             If none of the bits are set, it indicates no faults are 
             reported."
    ::= { docsRphyRpdDevL2tpSessionInfoEntry 19 }
    
docsRphyRpdDevL2tpSessionInfoLastChange OBJECT-TYPE
    SYNTAX      TimeStamp
    MAX-ACCESS  read-only
    STATUS      current
    DESCRIPTION 
            "The attribute provides the value of sysUpTime 
             when the session entered its current OperStatus 
             state from the point of view of the specific 
             reporting entity (RPD)."
    ::= { docsRphyRpdDevL2tpSessionInfoEntry 20 }
    
-- ---------------------------------------------------------
-- RPD L2TP Session Statistics Table 
-- ---------------------------------------------------------
                 
docsRphyRpdDevL2tpSessionStatsTable OBJECT-TYPE
    SYNTAX      SEQUENCE OF DocsRphyRpdDevL2tpSessionStatsEntry
    MAX-ACCESS  not-accessible
    STATUS      current
    DESCRIPTION
            "This table provides statistics about each tunnel 
             session between the RPD and each CCAP Core with which the 
             RPD is associated from the RPD's point of view."
    ::= { docsRphyRpdDevMibObjects 9 }

docsRphyRpdDevL2tpSessionStatsEntry OBJECT-TYPE
    SYNTAX      DocsRphyRpdDevL2tpSessionStatsEntry
    MAX-ACCESS  not-accessible
    STATUS      current
    DESCRIPTION
            "The conceptual row of docsRphyRpdDevL2tpSessionStatsTable.
             This table is an augmentation of 
             docsRphyL2tpSessionInfoTable."
    AUGMENTS { docsRphyRpdDevL2tpSessionInfoEntry }
    ::= { docsRphyRpdDevL2tpSessionStatsTable 1 }

DocsRphyRpdDevL2tpSessionStatsEntry ::= SEQUENCE
    {
    docsRphyRpdDevL2tpSessionStatsOutOfSeqPkts   Counter32,
    docsRphyRpdDevL2tpSessionStatsInPkts	 Counter64,
    docsRphyRpdDevL2tpSessionStatsInDiscards	 Counter64,
    docsRphyRpdDevL2tpSessionStatsOutPkts	 Counter64,
    docsRphyRpdDevL2tpSessionStatsOutErrors	 Counter64
    }
    
docsRphyRpdDevL2tpSessionStatsOutOfSeqPkts OBJECT-TYPE
    SYNTAX      Counter32
    MAX-ACCESS  read-only
    STATUS      current
    DESCRIPTION 
            "This attribute indicates the count of session packets that
             were received out of sequence from the point of view of the
             reporting entity. It is vendor dependent the re-sequence of 
             packets. Implementations that do not re-sequence packets 
             also increase the value of ifInDiscards for the respective 
             entry."
    ::= { docsRphyRpdDevL2tpSessionStatsEntry 1 }
    
 docsRphyRpdDevL2tpSessionStatsInPkts OBJECT-TYPE
    SYNTAX      Counter64
    MAX-ACCESS  read-only
    STATUS      current
    DESCRIPTION 
            "This attribute counts the number of received packets accepted 
            for processing above the L2TPv3 protocol layer. The InPackets 
            attribute count excludes packets dropped by the L2TPv3 protocol 
            layer itself (e.g. OutOfSequencePackets and InDiscards)."
    ::= { docsRphyRpdDevL2tpSessionStatsEntry 2 } 
    
 docsRphyRpdDevL2tpSessionStatsInDiscards OBJECT-TYPE
    SYNTAX      Counter64
    MAX-ACCESS  read-only
    STATUS      current
    DESCRIPTION 
            "This attribute counts the number of received packets discarded 
            by the L2TPv3 protocol layer itself, including those discarded 
            because they were out of sequence. The InDiscards attribute 
            count includes packets unable to be forwarded to a higher layer 
            for processing (e.g. unknown L2tpv3 session Id). Interpretation 
            of what discards are counted in this attribute is 
            vendor-specific."
    ::= { docsRphyRpdDevL2tpSessionStatsEntry 3 } 
    
 docsRphyRpdDevL2tpSessionStatsOutPkts OBJECT-TYPE
    SYNTAX      Counter64
    MAX-ACCESS  read-only
    STATUS      current
    DESCRIPTION 
            "This attribute counts the number of packets conceptually 
            attempted to be transmitted from above the L2TPv3 protocol layer. 
            The OutPackets attribute counts packets discarded by the L2TPv3 
            protocol layer itself (i.e. as counted by OutErrors)."
    ::= { docsRphyRpdDevL2tpSessionStatsEntry 4 }    
    
 docsRphyRpdDevL2tpSessionStatsOutErrors OBJECT-TYPE
    SYNTAX      Counter64
    MAX-ACCESS  read-only
    STATUS      current
    DESCRIPTION 
            "This attribute counts the number of packets attempted to be 
            transmitted from above the L2TPv3 protocol layer that could not 
            be transmitted below the L2TPv3 protocol layer itself. 
            Interpretation of what errors are counted in this attribute is 
            vendor specific."
    ::= { docsRphyRpdDevL2tpSessionStatsEntry 5 }     
  
-- ---------------------------------------------------------------------
-- RPD Diagnostic Status Table
-- ---------------------------------------------------------------------

docsRphyRpdDevDiagStatusTable OBJECT-TYPE
        SYNTAX      SEQUENCE OF DocsRphyRpdDevDiagStatusEntry
        MAX-ACCESS  not-accessible
        STATUS      current
        DESCRIPTION
            "This table reports information about an RPD's diagnostic
             self test results."
        ::= { docsRphyRpdDevMibObjects 10 }


docsRphyRpdDevDiagStatusEntry OBJECT-TYPE
        SYNTAX     DocsRphyRpdDevDiagStatusEntry
        MAX-ACCESS not-accessible
        STATUS     current
        DESCRIPTION
            "The conceptual row of docsRphyRpdDevDiagStatusTable.
             This table returns at least one row indicating pass or
             failure for the diagnostic self test."
        INDEX { docsRphyRpdDevInfoUniqueId }
        ::= { docsRphyRpdDevDiagStatusTable 1 }


DocsRphyRpdDevDiagStatusEntry ::= SEQUENCE
       {
       docsRphyRpdDevDiagStatusProbableCause         SnmpAdminString,
       docsRphyRpdDevDiagStatusAdditionalText        SnmpAdminString,
       docsRphyRpdDevDiagStatusSeverityLevel         RphyEventSeverityType
       }

docsRphyRpdDevDiagStatusProbableCause OBJECT-TYPE
        SYNTAX      SnmpAdminString
        MAX-ACCESS  read-only
        STATUS      current
        DESCRIPTION 
            "This attribute reports the probable cause of the 
             diagnostic test error condition.  Probable causes 
             may be related to:
             - Communications error
             - Quality of Service error
             - Processing error
             - Equipment error
             - Environmental error
             The format for values returned are vendor-specific.
             When the self test result is a pass, this attribute 
             returns 'Self Test Passed'."
        ::= { docsRphyRpdDevDiagStatusEntry 1 }
        
docsRphyRpdDevDiagStatusAdditionalText OBJECT-TYPE
        SYNTAX      SnmpAdminString
        MAX-ACCESS  read-only
        STATUS      current
        DESCRIPTION 
            "This attribute reports a free form text description of the 
             diagnostic test error condition.  This provides 
             supplemental information for the ProbableCause.
             When the self test result is a pass, this attribute returns 
             'No errors found'."
        ::= { docsRphyRpdDevDiagStatusEntry 2 }
        
docsRphyRpdDevDiagStatusSeverityLevel OBJECT-TYPE
        SYNTAX      RphyEventSeverityType
        MAX-ACCESS  read-only
        STATUS      current
        DESCRIPTION 
            "This attribute reports the severity level for the 
             diagnostic test error condition. Severity levels are based 
             on the DOCSIS event priority levels.
             When the self test result is a pass, this attribute returns 
             'information'."
        ::= { docsRphyRpdDevDiagStatusEntry 3 }
        
-- ---------------------------------------------------------------------
-- RPD DEPI Multicast Session Table
-- ---------------------------------------------------------------------

docsRphyRpdDevDepiMcastSessionTable OBJECT-TYPE
        SYNTAX      SEQUENCE OF DocsRphyRpdDevDepiMcastSessionEntry
        MAX-ACCESS  not-accessible
        STATUS      current
        DESCRIPTION
            "This table reports the DEPI IP multicast sessions 
             currently joined by an RPD."
        ::= { docsRphyRpdDevMibObjects 11 }


docsRphyRpdDevDepiMcastSessionEntry OBJECT-TYPE
        SYNTAX     DocsRphyRpdDevDepiMcastSessionEntry
        MAX-ACCESS not-accessible
        STATUS     current
        DESCRIPTION
            "The conceptual row of docsRphyRpdDevDepiMcastSessionTable.
             A row entry of this table represents one DEPI IP Multicast 
             session replicated to one RPD. The indexing provides the 
             RPD unique identifier and the (S,G) IP address pair that 
             uniquely identifies an IP multicast session. The CCAP Core 
             creates a row entry when it confirms an RPD has joined a 
             DEPI IP multicast session. The CCAP Core deletes the row
             entry when it confirms an RPD has left the DEPI IP 
             multicast session or disconnects its GCP session with 
             the CCAP Core."
        INDEX { docsRphyRpdDevInfoUniqueId,
                docsRphyRpdDevDepiMcastSessionIpAddrType,
                docsRphyRpdDevDepiMcastSessionGrpIpAddr,
                docsRphyRpdDevDepiMcastSessionSrcIpAddr }
        ::= { docsRphyRpdDevDepiMcastSessionTable 1 }


DocsRphyRpdDevDepiMcastSessionEntry ::= SEQUENCE
       {
       docsRphyRpdDevDepiMcastSessionIpAddrType            InetAddressType,
       docsRphyRpdDevDepiMcastSessionGrpIpAddr             InetAddress,
       docsRphyRpdDevDepiMcastSessionSrcIpAddr             InetAddress,
       docsRphyRpdDevDepiMcastSessionLocalLcceIpAddr       InetAddress,
       docsRphyRpdDevDepiMcastSessionRemoteLcceIpAddr      InetAddress,
       docsRphyRpdDevDepiMcastSessionId                    Unsigned32,
       docsRphyRpdDevDepiMcastSessionJoinTime              DateAndTime
       }

docsRphyRpdDevDepiMcastSessionIpAddrType OBJECT-TYPE
        SYNTAX      InetAddressType
        MAX-ACCESS  not-accessible
        STATUS      current
        DESCRIPTION 
            "This key attribute reports whether the IP addresses 
             provided in GroupIpAddr, SourceIpAddr, LocalLcceIpAddr 
             and RemoteLcceIpAddr are IPv4 or IPv6."
        ::= { docsRphyRpdDevDepiMcastSessionEntry 1 }
        
docsRphyRpdDevDepiMcastSessionGrpIpAddr OBJECT-TYPE
        SYNTAX      InetAddress
        MAX-ACCESS  not-accessible
        STATUS      current
        DESCRIPTION 
            "This key attribute reports the group (destination) address 
             of an IP multicast session transmitted via DEPI 
             multicast."
        ::= { docsRphyRpdDevDepiMcastSessionEntry 2 }
        
docsRphyRpdDevDepiMcastSessionSrcIpAddr OBJECT-TYPE
        SYNTAX      InetAddress
        MAX-ACCESS  not-accessible
        STATUS      current
        DESCRIPTION 
            "For Source Specific Multicast (SSM), this key attribute 
             reports the source IP address of an IP multicast session 
             transmitted via DEPI multicast. For Any-Source Multicast 
             (ASM) sessions, this attribute reports the all-0s IP 
             address."
        ::= { docsRphyRpdDevDepiMcastSessionEntry 3 }
        
docsRphyRpdDevDepiMcastSessionLocalLcceIpAddr OBJECT-TYPE
        SYNTAX      InetAddress
        MAX-ACCESS  read-only
        STATUS      current
        DESCRIPTION 
            "This attribute reports the RPD local LCCE IP address of 
             the L2TPv3 DEPI control session that instructed the RPD 
             to join the IP multicast session."
        ::= { docsRphyRpdDevDepiMcastSessionEntry 4 }
        
docsRphyRpdDevDepiMcastSessionRemoteLcceIpAddr OBJECT-TYPE
        SYNTAX      InetAddress
        MAX-ACCESS  read-only
        STATUS      current
        DESCRIPTION 
            "This attribute reports the RPD remote LCCE IP address 
             (i.e. on the CCAP Core) of the L2TPv3 control session 
             that instructed the RPD to join the IP multicast session."
        ::= { docsRphyRpdDevDepiMcastSessionEntry 5 }
        
docsRphyRpdDevDepiMcastSessionId OBJECT-TYPE
        SYNTAX      Unsigned32 (2147483649..2147549183)
        MAX-ACCESS  read-only
        STATUS      current
        DESCRIPTION 
            "This attribute reports the L2TPv3 Session ID assigned by 
             the CCAP Core to the DEPI IP multicast session. The value 
             is assigned according to the referenced specification in 
             the range 0x80000001 through 0x8000FFFF."
        ::= { docsRphyRpdDevDepiMcastSessionEntry 6 }
  
docsRphyRpdDevDepiMcastSessionJoinTime OBJECT-TYPE
        SYNTAX      DateAndTime
        MAX-ACCESS  read-only
        STATUS      current
        DESCRIPTION 
            "This attribute reports the last time the RPD has joined this session."
        ::= { docsRphyRpdDevDepiMcastSessionEntry 7 }  
        
-- ---------------------------------------------------------------------
-- RPD Event Log Table
-- ---------------------------------------------------------------------

docsRphyRpdDevEventLogTable OBJECT-TYPE
        SYNTAX      SEQUENCE OF DocsRphyRpdDevEventLogEntry
        MAX-ACCESS  not-accessible
        STATUS      current
        DESCRIPTION
            "This table reports event log information for an RPD."
        ::= { docsRphyRpdDevMibObjects 12 }


docsRphyRpdDevEventLogEntry OBJECT-TYPE
        SYNTAX     DocsRphyRpdDevEventLogEntry
        MAX-ACCESS not-accessible
        STATUS     current
        DESCRIPTION
            "The conceptual row of docsRphyRpdDevEventLogTable."
        INDEX { docsRphyRpdDevInfoUniqueId,
                docsRphyRpdDevEventLogIndex }
        ::= { docsRphyRpdDevEventLogTable 1 }


DocsRphyRpdDevEventLogEntry ::= SEQUENCE
       {
       docsRphyRpdDevEventLogIndex                 Unsigned32,
       docsRphyRpdDevEventLogFirstTime             DateAndTime,
       docsRphyRpdDevEventLogLastTime              DateAndTime,
       docsRphyRpdDevEventLogCounts                Counter32,
       docsRphyRpdDevEventLogLevel                 RphyEventSeverityType,
       docsRphyRpdDevEventLogId                    Unsigned32,
       docsRphyRpdDevEventLogText                  SnmpAdminString
       }

docsRphyRpdDevEventLogIndex OBJECT-TYPE
        SYNTAX      Unsigned32
        MAX-ACCESS  not-accessible
        STATUS      current
        DESCRIPTION 
            "This key attribute provides relative ordering of the events 
             in the event log. This attribute will always increase 
             except when
             (a) the log is reset 
             (b) the device reboots and does not implement non-volatile 
             storage for this log, or 
             (c) it reaches the value 2^31. The next entry for all the 
             above cases is 1."
        ::= { docsRphyRpdDevEventLogEntry 1 }
        
docsRphyRpdDevEventLogFirstTime OBJECT-TYPE
        SYNTAX      DateAndTime
        MAX-ACCESS  read-only
        STATUS      current
        DESCRIPTION 
            "This attribute provides the local RPD time 
             when this event was created."
        ::= { docsRphyRpdDevEventLogEntry 2 }
        
docsRphyRpdDevEventLogLastTime OBJECT-TYPE
        SYNTAX      DateAndTime
        MAX-ACCESS  read-only
        STATUS      current
        DESCRIPTION 
            "When an event reports only one event occurrence, this 
             attribute will have the same value as the corresponding 
             instance of FirstTime. When an event reports multiple 
             event occurrences, this attribute will record the local 
             RPD time when the most recent occurrence for this event 
             occurred."
        ::= { docsRphyRpdDevEventLogEntry 3 }
        
docsRphyRpdDevEventLogCounts OBJECT-TYPE
        SYNTAX      Counter32
        MAX-ACCESS  read-only
        STATUS      current
        DESCRIPTION 
            "This attribute provides the number of consecutive event 
             occurrences reported by this event. This starts at 1 with 
             the creation of this event occurrence and increments by 1 
             for each subsequent duplicate event occurrence."
        ::= { docsRphyRpdDevEventLogEntry 4 }
        
docsRphyRpdDevEventLogLevel OBJECT-TYPE
        SYNTAX      RphyEventSeverityType
        MAX-ACCESS  read-only
        STATUS      current
        DESCRIPTION 
            "This attribute provides the priority level of this event, 
             as defined by Annex B. These are ordered from most serious 
             (emergency) to least serious (debug)."
        REFERENCE 
            "DOCSIS DCA MHAv2 Remote PHY OSS Interface Specification
             CM-SP-R-OSSI-I04-160923, Annex B."
        ::= { docsRphyRpdDevEventLogEntry 5 }
        
docsRphyRpdDevEventLogId OBJECT-TYPE
        SYNTAX      Unsigned32
        MAX-ACCESS  read-only
        STATUS      current
        DESCRIPTION 
            "This attribute provides the identifier of this event, 
             as defined by Annex B."
        REFERENCE 
            "DOCSIS DCA MHAv2 Remote PHY OSS Interface Specification
             CM-SP-R-OSSI-I04-160923, Annex B."
        ::= { docsRphyRpdDevEventLogEntry 6 }
        
docsRphyRpdDevEventLogText OBJECT-TYPE
        SYNTAX      SnmpAdminString
        MAX-ACCESS  read-only
        STATUS      current
        DESCRIPTION 
            "This attribute provides the message text of this event, 
             as defined by Annex B."
        REFERENCE 
            "DOCSIS DCA MHAv2 Remote PHY OSS Interface Specification
             CM-SP-R-OSSI-I04-160923, Annex B."
        ::= { docsRphyRpdDevEventLogEntry 7 }
        
-- ---------------------------------------------------------------------
-- RPD Oob551UsChanStatus Table
-- ---------------------------------------------------------------------

docsRphyRpdDevOob551UsChanStatusTable OBJECT-TYPE
        SYNTAX      SEQUENCE OF DocsRphyRpdDevOob551UsChanStatusEntry
        MAX-ACCESS  not-accessible
        STATUS      current
        DESCRIPTION
            "This table provides per-RPD counts of upstream SCTE 55-1 cells sent 
             to a Network Controller."
        ::= { docsRphyRpdDevMibObjects 13 }


docsRphyRpdDevOob551UsChanStatusEntry OBJECT-TYPE
        SYNTAX     DocsRphyRpdDevOob551UsChanStatusEntry
        MAX-ACCESS not-accessible
        STATUS     current
        DESCRIPTION
            "The conceptual row of docsRphyRpdDevOob551UsChanStatusTable.
             A row entry of this table represents counts that are updated 
             by the CCAP Core, which parses each upstream SCTE 55-1 packet 
             and uses the power level and packet status 
             (which are really cell status) bits in those packets to determine
             how to update the counters."
        INDEX { docsRphyRpdDevInfoUniqueId,
                docsRphyRpdDevOob551UsChanStatusRfPort,
                docsRphyRpdDevOob551UsChanStatusChannelId }
        ::= { docsRphyRpdDevOob551UsChanStatusTable 1 }


DocsRphyRpdDevOob551UsChanStatusEntry ::= SEQUENCE
       {
       docsRphyRpdDevOob551UsChanStatusRfPort                      Unsigned32,
       docsRphyRpdDevOob551UsChanStatusChannelId                   Unsigned32,
       docsRphyRpdDevOob551UsChanStatusNcIpAddrType                InetAddressType,
       docsRphyRpdDevOob551UsChanStatusNcIpAddr                    InetAddress,
       docsRphyRpdDevOob551UsChanStatusArpdSrcIpAddrType           InetAddressType,
       docsRphyRpdDevOob551UsChanStatusArpdSrcIpAddr               InetAddress,
       docsRphyRpdDevOob551UsChanStatusPerfectCellsRcvd            Counter64,
       docsRphyRpdDevOob551UsChanStatusCorrectedCellsRcvd          Counter64,
       docsRphyRpdDevOob551UsChanStatusUncorrectableCellsRcvd      Counter64,
       docsRphyRpdDevOob551UsChanStatusTotalCellsRcvd              Counter64,
       docsRphyRpdDevOob551UsChanStatusPwrLevel                    Integer32,
       docsRphyRpdDevOob551UsChanStatusMaxPwrLevel                 Integer32,
       docsRphyRpdDevOob551UsChanStatusMinPwrLevel                 Integer32,
       docsRphyRpdDevOob551UsChanStatusCounterDiscontinuityTime    TimeStamp
       }

docsRphyRpdDevOob551UsChanStatusRfPort OBJECT-TYPE
        SYNTAX      Unsigned32
        MAX-ACCESS  not-accessible
        STATUS      current
        DESCRIPTION 
            "This key attribute reports the RPD RF port number carrying
             this SCTE 55-1 US channel."
        ::= { docsRphyRpdDevOob551UsChanStatusEntry 1 }
        
docsRphyRpdDevOob551UsChanStatusChannelId OBJECT-TYPE
        SYNTAX      Unsigned32
        MAX-ACCESS  not-accessible
        STATUS      current
        DESCRIPTION 
            "This key attribute reports the demodulator ID (channel number) 
            for this SCTE 55-1 US channel."
        ::= { docsRphyRpdDevOob551UsChanStatusEntry 2 }
        
docsRphyRpdDevOob551UsChanStatusNcIpAddrType OBJECT-TYPE
        SYNTAX      InetAddressType
        MAX-ACCESS  read-only
        STATUS      current
        DESCRIPTION 
            "This attribute indicates whether the IP address provide in 
             docsRphyRpdDevOob551UsChanStatusNcIpAddr is IPv4 or IPv6."
        ::= { docsRphyRpdDevOob551UsChanStatusEntry 3 }
    
docsRphyRpdDevOob551UsChanStatusNcIpAddr OBJECT-TYPE
        SYNTAX      InetAddress
        MAX-ACCESS  read-only
        STATUS      current
        DESCRIPTION 
            "This attribute reports the IP host address of the 
            Network Controller receiving the cells on this 
            SCTE 55-1 US channel."
        ::= { docsRphyRpdDevOob551UsChanStatusEntry 4 }
        
docsRphyRpdDevOob551UsChanStatusArpdSrcIpAddrType OBJECT-TYPE
        SYNTAX      InetAddressType
        MAX-ACCESS  read-only
        STATUS      current
        DESCRIPTION 
            "This attribute indicates whether the IP address provide in 
             docsRphyRpdDevOob551UsChanStatusArpdSrcIpAddr is IPv4 or IPv6."
        ::= { docsRphyRpdDevOob551UsChanStatusEntry 5 }
    
docsRphyRpdDevOob551UsChanStatusArpdSrcIpAddr OBJECT-TYPE
        SYNTAX      InetAddress
        MAX-ACCESS  read-only
        STATUS      current
        DESCRIPTION 
            "This attribute reports the virtual ARPD source 
            IP host address used when sending cells to the 
            Network Controller."
        ::= { docsRphyRpdDevOob551UsChanStatusEntry 6 }
        
docsRphyRpdDevOob551UsChanStatusPerfectCellsRcvd OBJECT-TYPE
        SYNTAX      Counter64
        MAX-ACCESS  read-only
        STATUS      current
        DESCRIPTION 
            "This attribute reports the number of perfect cells
             received by the demodulator for this SCTE 55-1 US channel. 
             Perfect cells have status 0 in the US SCTE 55-1 OOB packet."
        ::= { docsRphyRpdDevOob551UsChanStatusEntry 7 }
        
docsRphyRpdDevOob551UsChanStatusCorrectedCellsRcvd OBJECT-TYPE
        SYNTAX      Counter64
        MAX-ACCESS  read-only
        STATUS      current
        DESCRIPTION 
            "This attribute reports the number of errored cells 
            received by the demodulator for this SCTE 55-1 US channel 
            that were successfully corrected. Corrected cells have 
            status 1 in the US SCTE 55-1 OOB packet."
        ::= { docsRphyRpdDevOob551UsChanStatusEntry 8 }
  
docsRphyRpdDevOob551UsChanStatusUncorrectableCellsRcvd OBJECT-TYPE
        SYNTAX      Counter64
        MAX-ACCESS  read-only
        STATUS      current
        DESCRIPTION 
            "This attribute reports the number of errored cells received 
            by the demodulator for this SCTE 55-1 US channel that could 
            not be corrected. Uncorrectable cells have status 3 in the 
            US SCTE 55-1 OOB packet."
        ::= { docsRphyRpdDevOob551UsChanStatusEntry 9 }          

docsRphyRpdDevOob551UsChanStatusTotalCellsRcvd OBJECT-TYPE
        SYNTAX      Counter64
        MAX-ACCESS  read-only
        STATUS      current
        DESCRIPTION 
            "This attribute reports the total of all cells received for 
            this SCTE 55-1 US channel."
        ::= { docsRphyRpdDevOob551UsChanStatusEntry 10 }
        
docsRphyRpdDevOob551UsChanStatusPwrLevel OBJECT-TYPE
        SYNTAX      Integer32
        MAX-ACCESS  read-only
        STATUS      current
        DESCRIPTION 
            "This attribute reports the average power level from nominal 
            of all received MAC Cells by the demodulator for this upstream 
            SCTE 55-1 channel in tenths of a dB. The six power level bits 1 
            in the US SCTE 55-1 OOB packet report the nominal power per cell 
            in units of 0.5 dB."
        ::= { docsRphyRpdDevOob551UsChanStatusEntry 11 }
        
docsRphyRpdDevOob551UsChanStatusMaxPwrLevel OBJECT-TYPE
        SYNTAX      Integer32
        MAX-ACCESS  read-only
        STATUS      current
        DESCRIPTION 
            "This attribute reports the maximum power level from nominal 
            of all received MAC Cells by the demodulator for this upstream 
            SCTE 55-1 channel in tenths of a dB."
        ::= { docsRphyRpdDevOob551UsChanStatusEntry 12 }
        
docsRphyRpdDevOob551UsChanStatusMinPwrLevel OBJECT-TYPE
        SYNTAX      Integer32
        MAX-ACCESS  read-only
        STATUS      current
        DESCRIPTION 
            "This attribute reports the minimum power level from nominal of 
            all received MAC Cells by the demodulator for this upstream SCTE 55-1 
            channel in tenths of a dB."
        ::= { docsRphyRpdDevOob551UsChanStatusEntry 13 }
  
docsRphyRpdDevOob551UsChanStatusCounterDiscontinuityTime OBJECT-TYPE
        SYNTAX      TimeStamp
        MAX-ACCESS  read-only
        STATUS      current
        DESCRIPTION 
            "TThis attribute reports the value of sysUpTime on the most recent 
            occasion at which any one or more of this interface's counters suffered 
            a discontinuity. If no such discontinuities have occurred since the last 
            re-initialization of the local management subsystem, then this attribute 
            reports a zero value."
        ::= { docsRphyRpdDevOob551UsChanStatusEntry 14 }  

-- ---------------------------------------------------------------------
-- RPD CrashDataFileStatus Table
-- ---------------------------------------------------------------------

docsRphyRpdDevCrashDataFileStatusTable OBJECT-TYPE
        SYNTAX      SEQUENCE OF DocsRphyRpdDevCrashDataFileStatusEntry
        MAX-ACCESS  not-accessible
        STATUS      current
        DESCRIPTION
            "This table provides status information for the 
            crash analysis data files."
        ::= { docsRphyRpdDevMibObjects 14 }


docsRphyRpdDevCrashDataFileStatusEntry OBJECT-TYPE
        SYNTAX     DocsRphyRpdDevCrashDataFileStatusEntry
        MAX-ACCESS not-accessible
        STATUS     current
        DESCRIPTION
            "The conceptual row of docsRphyRpdDevCrashDataFileStatusTable.
             A row entry of this table represents a file 
             that is available in the device for upload or 
             for which an upload is in progress."
        INDEX { docsRphyRpdDevInfoUniqueId,
                docsRphyRpdDevCrashDataFileStatusIndex}
        ::= { docsRphyRpdDevCrashDataFileStatusTable 1 }


DocsRphyRpdDevCrashDataFileStatusEntry ::= SEQUENCE
       {
       docsRphyRpdDevCrashDataFileStatusIndex                      Unsigned32,
       docsRphyRpdDevCrashDataFileStatusFilename                   SnmpAdminString,
       docsRphyRpdDevCrashDataFileStatusFileStatus                 INTEGER
       }

docsRphyRpdDevCrashDataFileStatusIndex OBJECT-TYPE
        SYNTAX      Unsigned32
        MAX-ACCESS  not-accessible
        STATUS      current
        DESCRIPTION 
            "This key attribute uniquely identifies a crash analysis file."
        ::= { docsRphyRpdDevCrashDataFileStatusEntry 1 }
        
docsRphyRpdDevCrashDataFileStatusFilename OBJECT-TYPE
        SYNTAX      SnmpAdminString (SIZE (1..255))
        MAX-ACCESS  read-only
        STATUS      current
        DESCRIPTION 
            "This attribute contains the name of the crash analysis file,
             stored in the device that is available to be uploaded to the
             server.  Filenames are defined by the application that creates 
             them. The RPD SHOULD generate crash analysis files with names 
             which include RPD's unique id and a timestamp. The timestamp 
             indicates the time when the crash has occurred with granularity
             of one second. The RPD SHOULD format the timestamp in the form 
             'Unix time', which is defined as the number of seconds that have 
             elapsed since midnight Coordinated Universal Time (UTC), 
             Thursday, 1 January 1970. For example, a crash file name 
             'RPD_crash_dump_id_00000187ADF_time_1403405123' indicates that 
             the file was generated by RPD with Unique ID of 00.00.00.18.7A.DF 
             on Sunday 22nd June 2014 02:45:23 AM."
        ::= { docsRphyRpdDevCrashDataFileStatusEntry 2 }
        
docsRphyRpdDevCrashDataFileStatusFileStatus OBJECT-TYPE
        SYNTAX      INTEGER {
                             other(1),
                             availableForUpload(2),
                             uploadInProgress(3),
                             uploadCompleted(4),
                             uploadPending(5),
                             uploadCancelled(6),
                             error(7)                             
                             }
        MAX-ACCESS  read-only
        STATUS      current
        DESCRIPTION 
            "This attribute reflects the status of the crash data file. 
            The possible values are listed below.
			other(1) - Any condition not covered by the other defined values.
			availableForUpload(2) - The file is available to be uploaded.
			uploadInProgress(3) - The file is currently being uploaded. 
				The file is not available for another upload in this state.
			uploadCompleted(4) - The file was successfully uploaded. 
				The file is available for another upload.
			uploadPending(5) - The file has been selected for upload but a 
				condition does not allow the upload to take place. The upload 
				will start when the condition blocking uploads has been removed. 
				For example, another upload that is currently in progress could 
				cause this value to be returned. uploadPending status can also 
				indicate a situation where the RPD is waiting to retry the upload 
				after the initial attempt(s) has failed. The file is not available 
				for another upload in this state.
			uploadCancelled(6) - An upload was cancelled before it completed. 
				The file is available for another upload.
			error(7) - An error occurred and the file was not successfully uploaded. 
				The file is available for another upload."
        ::= { docsRphyRpdDevCrashDataFileStatusEntry 3 }

-- ---------------------------------------------------------------------
-- RPD US Signal Quality Table
-- ---------------------------------------------------------------------

docsRphyRpdDevUsSignalQualityTable OBJECT-TYPE
        SYNTAX      SEQUENCE OF DocsRphyRpdDevUsSignalQualityEntry
        MAX-ACCESS  not-accessible
        STATUS      current
        DESCRIPTION
            "This table provide individual upstream signal quality 
            values for RPDs."
        ::= { docsRphyRpdDevMibObjects 15 }


docsRphyRpdDevUsSignalQualityEntry OBJECT-TYPE
        SYNTAX     DocsRphyRpdDevUsSignalQualityEntry
        MAX-ACCESS not-accessible
        STATUS     current
        DESCRIPTION
            "The conceptual row of docsRphyRpdDevUsSignalQualityTable.
             A row entry of this table represents the upstream signal quality
             values of a single RPD"
        INDEX { docsRphyRpdDevInfoUniqueId,
                docsRphyRpdDevUsSignalQualityRfPort,
                docsRphyRpdDevUsSignalQualityChannelIfIndex }
        ::= { docsRphyRpdDevUsSignalQualityTable 1 }


DocsRphyRpdDevUsSignalQualityEntry ::= SEQUENCE
       {
       docsRphyRpdDevUsSignalQualityRfPort                     	Unsigned32,
       docsRphyRpdDevUsSignalQualityChannelIfIndex             	InterfaceIndex,
       docsRphyRpdDevUsSignalQualityRxMer                 	Integer32,
       docsRphyRpdDevUsSignalQualityRxMerSamples		Unsigned32,
       docsRphyRpdDevUsSignalQualityUnerroreds			Counter64,
       docsRphyRpdDevUsSignalQualityCorrecteds			Counter64,
       docsRphyRpdDevUsSignalQualityUncorrectables		Counter64
       }

docsRphyRpdDevUsSignalQualityRfPort OBJECT-TYPE
        SYNTAX      Unsigned32
        MAX-ACCESS  not-accessible
        STATUS      current
        DESCRIPTION 
            "This key attribute reports the RPD RF port number carrying 
            this US channel. This corresponds to the attribute RpdUsRfPortNum 
            of the RpdUsRfPortRef object in the configuration Information Model."
        ::= { docsRphyRpdDevUsSignalQualityEntry 1 }
        
docsRphyRpdDevUsSignalQualityChannelIfIndex OBJECT-TYPE
        SYNTAX      InterfaceIndex
        MAX-ACCESS  not-accessible
        STATUS      current
        DESCRIPTION 
            "This attribute corresponds to the ifIndex of the Upstream 
            Physical Channel of the CCAP Core for this US channel. Note 
            that with upstream virtual combining, this attribute corresponds 
            to the same CCAP Core ifIndex for different RPD unique Ids."
        ::= { docsRphyRpdDevUsSignalQualityEntry 2 }

docsRphyRpdDevUsSignalQualityRxMer OBJECT-TYPE
        SYNTAX      Integer32 (-2147483648..2147483647)
        UNITS       "TenthdB"
        MAX-ACCESS  read-only
        STATUS      current
        DESCRIPTION 
            "This attribute reports an in-channel received average 
            Modulation Error Ratio (MER). An RxMER sample is defined 
            as an estimate, provided by the demodulator, of the ratio: 
 			(average constellation energy with equally likely symbols) / 
 			(average squared magnitude of error vector)
			RxMER is measured just prior to FEC (trellis/Reed-Solomon) 
			decoding. RxMER includes the effects of the HFC channel as 
			well as implementation effects of the modulator and demodulator. 
			Error vector estimation may vary among demodulator implementations.  
			The CCAP Core RxMER is averaged over a given number of bursts at 
			the burst receiver, which may correspond to transmissions from 
			multiple users. In the case of S-CDMA mode, RxMER is measured on 
			the de-spread signal.			
			For OFDMA channels, this attribute always reports 0."
        ::= { docsRphyRpdDevUsSignalQualityEntry 3 }    
        
docsRphyRpdDevUsSignalQualityRxMerSamples OBJECT-TYPE
        SYNTAX      Unsigned32
        MAX-ACCESS  read-only
        STATUS      current
        DESCRIPTION 
            "This attribute reports RxMerSamples which is a statistically 
            significant number of bursts for the CCAP Core, processed to 
            arrive at the RxMER value. For the CCAP Core, the MER measurement 
            includes only valid bursts that are not in contention regions.
			For OFDMA channels, this attribute always reports 0."
        ::= { docsRphyRpdDevUsSignalQualityEntry 4 }  

docsRphyRpdDevUsSignalQualityUnerroreds OBJECT-TYPE
        SYNTAX      Counter64
        MAX-ACCESS  read-only
        STATUS      current
        DESCRIPTION 
            "This attribute reports the count of codewords received on 
            this channel without error. This includes all codewords, 
            whether or not they were part of frames destined for this device.
			Reference: OFDMA FEC Error Reporting section of this specification."
        ::= { docsRphyRpdDevUsSignalQualityEntry 5 }   
        
docsRphyRpdDevUsSignalQualityCorrecteds OBJECT-TYPE
        SYNTAX      Counter64
        MAX-ACCESS  read-only
        STATUS      current
        DESCRIPTION 
            "This attribute reports the count of codewords received on 
            this channel with correctable errors.  This includes all 
            codewords, whether or not they were part of frames destined 
            for this device.
			Reference: OFDMA FEC Error Reporting section of this specification."
        ::= { docsRphyRpdDevUsSignalQualityEntry 6 }    
        
docsRphyRpdDevUsSignalQualityUncorrectables OBJECT-TYPE
        SYNTAX      Counter64
        MAX-ACCESS  read-only
        STATUS      current
        DESCRIPTION 
            "This attribute reports the count of codewords received on 
            this channel with uncorrectable errors.  This includes all 
            codewords, whether or not they were part of frames destined 
            for this device.
			Reference: OFDMA FEC Error Reporting section of this specification."
        ::= { docsRphyRpdDevUsSignalQualityEntry 7 } 
                



-- ---------------------------------------------------------------------
-- RPD Host Resources System Table
-- Derived from RFC 2790    
-- ---------------------------------------------------------------------

docsRphyRpdDevHostResSysTable OBJECT-TYPE
        SYNTAX      SEQUENCE OF DocsRphyRpdDevHostResSysEntry
        MAX-ACCESS  not-accessible
        STATUS      current
        DESCRIPTION
            "This table identifies the RPD for which the details and statistics 
             are being provided."
        ::= { docsRphyRpdDevMibObjects 16 }


docsRphyRpdDevHostResSysEntry OBJECT-TYPE
        SYNTAX     DocsRphyRpdDevHostResSysEntry
        MAX-ACCESS not-accessible
        STATUS     current
        DESCRIPTION
            "The conceptual row of docsRphyRpdDevHostResSysTable.
             A row entry of this table represents the details and statistics 
	     of the RPD."
        INDEX { docsRphyRpdDevInfoUniqueId }
        ::= { docsRphyRpdDevHostResSysTable 1 }


DocsRphyRpdDevHostResSysEntry ::= SEQUENCE
       {
       docsRphyRpdDevHostResSysDate	DateAndTime
       }

docsRphyRpdDevHostResSysDate OBJECT-TYPE
    SYNTAX  DateAndTime
    MAX-ACCESS  read-only
    STATUS  current
    DESCRIPTION
	    "This attribute contains a date-time specification for the local
              time of day."
    ::= { docsRphyRpdDevHostResSysEntry 1 }


-- ---------------------------------------------------------------------
-- RPD Host Resources Storage Table
-- Derived from RFC 2790    
-- ---------------------------------------------------------------------

docsRphyRpdDevHostResStorTable OBJECT-TYPE
        SYNTAX      SEQUENCE OF DocsRphyRpdDevHostResStorEntry
        MAX-ACCESS  not-accessible
        STATUS      current
        DESCRIPTION
	    "The (conceptual) table of logical storage areas on
           the host.

           An entry shall be placed in the storage table for each
           logical area of storage that is allocated and has
           fixed resource limits.  The amount of storage
           represented in an entity is the amount actually usable
           by the requesting entity, and excludes loss due to
           formatting or file system reference information.

           These entries are associated with logical storage
           areas, as might be seen by an application, rather than
           physical storage entities which are typically seen by
           an operating system.  Storage such as tapes and
           floppies without file systems on them are typically
           not allocated in chunks by the operating system to
           requesting applications, and therefore shouldn't
           appear in this table.  Examples of valid storage for
           this table include disk partitions, file systems, ram
           (for some architectures this is further segmented into
           regular memory, extended memory, and so on), backing
           store for virtual memory (swap space).

           This table is intended to be a useful diagnostic for
           `out of memory' and `out of buffers' types of
           failures.  In addition, it can be a useful performance
           monitoring tool for tracking memory, disk, or buffer
           usage."
        ::= { docsRphyRpdDevMibObjects 17 }

docsRphyRpdDevHostResStorEntry OBJECT-TYPE
        SYNTAX     DocsRphyRpdDevHostResStorEntry
        MAX-ACCESS not-accessible
        STATUS     current
        DESCRIPTION
            "The conceptual row of docsRphyRpdDevHostResStorTable.
             A row entry of this table represents a logical storage area on
	     the host."
	 INDEX { docsRphyRpdDevInfoUniqueId,
	         docsRphyRpdDevHostResStorIndex}
        ::= { docsRphyRpdDevHostResStorTable 1 }


DocsRphyRpdDevHostResStorEntry ::= SEQUENCE
       {
       docsRphyRpdDevHostResStorIndex			Unsigned32,
       docsRphyRpdDevHostResStorType			AutonomousType,
       docsRphyRpdDevHostResStorAllocationUnits	        Unsigned32,
       docsRphyRpdDevHostResStorAllocationFailures	Counter64,
       docsRphyRpdDevHostResStorSize			Unsigned32,
       docsRphyRpdDevHostResStorUsed			Unsigned32,
       docsRphyRpdDevHostResStorDescr			SnmpAdminString
       }

docsRphyRpdDevHostResStorIndex OBJECT-TYPE
       SYNTAX  Unsigned32  (0..4294967295)
       MAX-ACCESS  not-accessible
       STATUS  current
       DESCRIPTION
	    "A unique value for each logical storage area
             contained by the host."
       ::= {  docsRphyRpdDevHostResStorEntry 1 }

docsRphyRpdDevHostResStorType OBJECT-TYPE
       SYNTAX  AutonomousType
       MAX-ACCESS  read-only
       STATUS  current
       DESCRIPTION
	    "The type of storage represented by this entry."
       ::= { docsRphyRpdDevHostResStorEntry 2 }
	

docsRphyRpdDevHostResStorAllocationUnits OBJECT-TYPE
    SYNTAX  Unsigned32
    UNITS   "Bytes"
    MAX-ACCESS  read-only
    STATUS  current
    DESCRIPTION
	"The size, in bytes, of the data objects allocated
           from this pool.  If this entry is monitoring sectors,
           blocks, buffers, or packets, for example, this number
           will commonly be greater than one.  Otherwise this
           number will typically be one."
    ::= {  docsRphyRpdDevHostResStorEntry 3 }


docsRphyRpdDevHostResStorAllocationFailures OBJECT-TYPE
    SYNTAX  Counter64
    MAX-ACCESS  read-only
    STATUS  current
    DESCRIPTION
	"The number of requests for storage represented by
           this entry that could not be honored due to not enough
           storage.  It should be noted that as this object has a
           SYNTAX of Counter64, that it does not have a defined
           initial value.  However, it is recommended that this
           object be initialized to zero, even though management
           stations must not depend on such an initialization."
    ::= { docsRphyRpdDevHostResStorEntry 4 }


docsRphyRpdDevHostResStorSize OBJECT-TYPE
    SYNTAX  Unsigned32
    MAX-ACCESS  read-write
    STATUS  current
    DESCRIPTION
	"The size of the storage represented by this entry, in
           units of Storage Allocation Units. This object is
           writable to allow remote configuration of the size of
           the storage area in those cases where such an
           operation makes sense and is possible on the
           underlying system. For example, the amount of main
           memory allocated to a buffer pool might be modified or
           the amount of disk space allocated to virtual memory
           might be modified."
    ::= {  docsRphyRpdDevHostResStorEntry 5 }

docsRphyRpdDevHostResStorUsed OBJECT-TYPE
    SYNTAX  Unsigned32
    MAX-ACCESS  read-only
    STATUS  current
    DESCRIPTION
	"The amount of the storage represented by this entry
           that is allocated, in units of
           Storage Allocation Units"
    ::= { docsRphyRpdDevHostResStorEntry 6 }

docsRphyRpdDevHostResStorDescr OBJECT-TYPE
    SYNTAX  SnmpAdminString
    MAX-ACCESS  read-only
    STATUS  current
    DESCRIPTION
	"A description of the type and instance of the storage
           described by this entry."
    ::= { docsRphyRpdDevHostResStorEntry 7 }

-- ---------------------------------------------------------------------
-- RPD Host Resources Sw Run Table
-- Derived from RFC 2790    
-- ---------------------------------------------------------------------

docsRphyRpdDevHostResSwRunTable OBJECT-TYPE
        SYNTAX      SEQUENCE OF DocsRphyRpdDevHostResSwRunEntry
        MAX-ACCESS  not-accessible
        STATUS      current
        DESCRIPTION
	    "The (conceptual) table of software running on the
	    host."
	  ::= { docsRphyRpdDevMibObjects 18 }


docsRphyRpdDevHostResSwRunEntry OBJECT-TYPE
        SYNTAX     DocsRphyRpdDevHostResSwRunEntry
        MAX-ACCESS not-accessible
        STATUS     current
        DESCRIPTION
            "The (conceptual) entry for one piece of software
           running on the host. Note that because the installed
           software table only contains information for software
           stored locally on this host, not every piece of
           running software will be found in the installed
           software table.  This is true of software that was
           loaded and run from a non-local source, such as a
           network-mounted file systemA row entry of this table 
           represents a logical storage area on the host."
	INDEX { docsRphyRpdDevInfoUniqueId,
	         docsRphyRpdDevHostResSwRunIndex}
        ::= { docsRphyRpdDevHostResSwRunTable 1 }


DocsRphyRpdDevHostResSwRunEntry ::= SEQUENCE
       {
       docsRphyRpdDevHostResSwRunIndex			Unsigned32,
       docsRphyRpdDevHostResSwRunType			INTEGER,
       docsRphyRpdDevHostResSwRunStatus	                INTEGER,
       docsRphyRpdDevHostResSwRunPerfCpu	        Unsigned32,
       docsRphyRpdDevHostResSwRunPerfMem		Unsigned32,
       docsRphyRpdDevHostResSwRunName			SnmpAdminString
       }
    
docsRphyRpdDevHostResSwRunIndex OBJECT-TYPE
       SYNTAX  Unsigned32
       MAX-ACCESS  not-accessible
       STATUS  current
       DESCRIPTION
	    "A unique value for each piece of software running on
             the host.  Wherever possible, this should be the
             system's native, unique identification number."
       ::= { docsRphyRpdDevHostResSwRunEntry 1 }

docsRphyRpdDevHostResSwRunType OBJECT-TYPE
       SYNTAX  INTEGER {
                      unknown(1),
                      operatingSystem(2),
                      deviceDriver(3),
                      application(4)
		      }
       MAX-ACCESS  read-only
       STATUS  current
       DESCRIPTION
	    "The type of this software."
       ::= { docsRphyRpdDevHostResSwRunEntry 2 }


docsRphyRpdDevHostResSwRunStatus OBJECT-TYPE
       SYNTAX  INTEGER {
                      running(1),
                      runnable(2),    -- waiting for resource
                                      -- (i.e., CPU, memory, IO)
                      notRunnable(3), -- loaded but waiting for event
                      invalid(4)      -- not loaded
                  }
	MAX-ACCESS  read-only
	STATUS  current
	DESCRIPTION
	     "The status of this running piece of software.
              Setting this value to invalid(4) shall cause this
              software to stop running and to be unloaded. Sets to
              other values are not valid."
	::= { docsRphyRpdDevHostResSwRunEntry 3 }

docsRphyRpdDevHostResSwRunPerfCpu OBJECT-TYPE
        SYNTAX  Unsigned32
        MAX-ACCESS  read-only
        STATUS  current
        DESCRIPTION
	     "The number of centi-seconds of the total system's CPU
              resources consumed by this process.  Note that on a
              multi-processor system, this value may increment by
              more than one centi-second in one centi-second of real
              (wall clock) time."
       ::= {  docsRphyRpdDevHostResSwRunEntry 4 }

docsRphyRpdDevHostResSwRunPerfMem OBJECT-TYPE
       SYNTAX  Unsigned32
       MAX-ACCESS  read-only
       STATUS  current
       DESCRIPTION
	   "The total amount of real system memory allocated to
            this process."
       ::= {  docsRphyRpdDevHostResSwRunEntry 5 }

docsRphyRpdDevHostResSwRunName OBJECT-TYPE
       SYNTAX  SnmpAdminString
       MAX-ACCESS  read-only
       STATUS  current
       DESCRIPTION
	    "A textual description of this running piece of
             software, including the manufacturer, revision,  and
             the name by which it is commonly known."
       ::= { docsRphyRpdDevHostResSwRunEntry 6 }


-- ---------------------------------------------------------------------
-- RPD Static Pw Capabilities Table
-- ---------------------------------------------------------------------

docsRphyRpdDevStaticPwCapTable OBJECT-TYPE
        SYNTAX      SEQUENCE OF DocsRphyRpdDevStaticPwCapEntry
        MAX-ACCESS  not-accessible
        STATUS      current
        DESCRIPTION
            "This table provides information about the static pseudo-wire
             capabilities of the RPD."
        ::= { docsRphyRpdDevMibObjects 19 }


docsRphyRpdDevStaticPwCapEntry OBJECT-TYPE
        SYNTAX     DocsRphyRpdDevStaticPwCapEntry
        MAX-ACCESS not-accessible
        STATUS     current
        DESCRIPTION
            "The conceptual row of docsRphyRpdDevStaticPwCapTable."
        INDEX { docsRphyRpdDevInfoUniqueId }
        ::= { docsRphyRpdDevStaticPwCapTable 1 }


DocsRphyRpdDevStaticPwCapEntry ::= SEQUENCE
       {
       docsRphyRpdDevStaticPwCapMaxFwdStaticPws                 Unsigned32,
       docsRphyRpdDevStaticPwCapMaxRetStaticPws                 Unsigned32,
       docsRphyRpdDevStaticPwCapSupportsStaticMptDepiPw         TruthValue,
       docsRphyRpdDevStaticPwCapSupportsStaticMpt55d1RetPw      TruthValue,
       docsRphyRpdDevStaticPwCapSupportsStaticPspNdfPw          TruthValue,
       docsRphyRpdDevStaticPwCapSupportsStaticPspNdrPw          TruthValue
       }

docsRphyRpdDevStaticPwCapMaxFwdStaticPws OBJECT-TYPE
        SYNTAX      Unsigned32 (0..65535)
        MAX-ACCESS  read-only
        STATUS      current
        DESCRIPTION 
            "This attribute reports the maximum number of 
             static forward pseudowires supported by the RPD."
        ::= { docsRphyRpdDevStaticPwCapEntry 1 }

docsRphyRpdDevStaticPwCapMaxRetStaticPws OBJECT-TYPE
        SYNTAX      Unsigned32 (0..65535)
        MAX-ACCESS  read-only
        STATUS      current
        DESCRIPTION 
            "This attribute reports the maximum number of
             static return pseudowires supported by the RPD."
        ::= { docsRphyRpdDevStaticPwCapEntry 2 }
        
docsRphyRpdDevStaticPwCapSupportsStaticMptDepiPw OBJECT-TYPE
        SYNTAX      TruthValue
        MAX-ACCESS  read-only
        STATUS      current
        DESCRIPTION 
            "This attribute reports whether the RPD supports 
             configuration of static pseudowires of DEPI MPT 
             (MPT-DEPI-PW) subtype."
        ::= { docsRphyRpdDevStaticPwCapEntry 3 }

docsRphyRpdDevStaticPwCapSupportsStaticMpt55d1RetPw OBJECT-TYPE
        SYNTAX      TruthValue
        MAX-ACCESS  read-only
        STATUS      current
        DESCRIPTION 
            "This attribute reports whether the RPD supports 
             configuration of static pseudowires of SCTE 55-1 
             return (MPT-55-1-RET) subtype."
        ::= { docsRphyRpdDevStaticPwCapEntry 4 }

docsRphyRpdDevStaticPwCapSupportsStaticPspNdfPw OBJECT-TYPE
        SYNTAX      TruthValue
        MAX-ACCESS  read-only
        STATUS      current
        DESCRIPTION 
            "This attribute reports whether the RPD supports 
             configuration of static pseudowires of PSP NDF
             (PSP-NDF) subtype."
        ::= { docsRphyRpdDevStaticPwCapEntry 5 }

docsRphyRpdDevStaticPwCapSupportsStaticPspNdrPw OBJECT-TYPE
        SYNTAX      TruthValue
        MAX-ACCESS  read-only
        STATUS      current
        DESCRIPTION 
            "This attribute reports whether the RPD supports 
             configuration of static pseudowires of PSP NDR 
             (PSP-NDF) subtype."
        ::= { docsRphyRpdDevStaticPwCapEntry 6 }


-- ---------------------------------------------------------------------
-- RPD Physical Group Objects Derived from RFC 6933 ENTITY-MIB
-- RPD Interface Group Objects Derived from IF-MIB RFC 2863
-- ---------------------------------------------------------------------  

-- ---------------------------------------------------------------------
-- RPD Physical Entity Table extracted from RFC 6933 ENTITY-MIB
-- ---------------------------------------------------------------------

docsRphyRpdIfPhysEntityTable OBJECT-TYPE
    SYNTAX      SEQUENCE OF DocsRphyRpdIfPhysEntityEntry
    MAX-ACCESS  not-accessible
    STATUS      current
    DESCRIPTION
            "This table reports entities that exist within each Remote
             PHY Node that is communicating with the CCAP Core. Because
             the entities exist within the Remote PHY Nodes and not the
             CCAP Core, the RPDs communicate this information to the
             CCAP core via GCP.  This object is based on the
             entPhysicalTable object specified in the ENTITY-MIB from
             RFC 4133.
             See the reference for additional requirements."
    REFERENCE
        "DOCSIS DCA MHAv2 Remote PHY OSS Interface Specification
         CM-SP-R-OSSI-I04-160923, Entity section."
    ::= { docsRphyRpdIfMibObjects 1 }

docsRphyRpdIfPhysEntityEntry       OBJECT-TYPE
    SYNTAX      DocsRphyRpdIfPhysEntityEntry
    MAX-ACCESS  not-accessible
    STATUS      current
    DESCRIPTION
            "Information about a particular physical entity.

            Each entry provides objects (docsRphyRpdIfPhysEntityDescr,
            docsRphyRpdIfPhysEntityVendorType, and docsRphyRpdIfPhysEntityClass) to help an NMS
            identify and characterize the entry and objects
            (docsRphyRpdIfPhysEntityContainedIn and docsRphyRpdIfPhysEntityParentRelPos) to help
            an NMS relate the particular entry to other entries in this
            table."
    INDEX   { docsRphyRpdDevInfoUniqueId,
              docsRphyRpdIfPhysEntityIndex }
    ::= { docsRphyRpdIfPhysEntityTable 1 }

DocsRphyRpdIfPhysEntityEntry ::= SEQUENCE {
      docsRphyRpdIfPhysEntityIndex          PhysicalIndex,
      docsRphyRpdIfPhysEntityDescr          SnmpAdminString,
      docsRphyRpdIfPhysEntityVendorType     AutonomousType,
      docsRphyRpdIfPhysEntityContainedIn    PhysicalIndexOrZero,
      docsRphyRpdIfPhysEntityClass          IANAPhysicalClass,
      docsRphyRpdIfPhysEntityParentRelPos   Integer32,
      docsRphyRpdIfPhysEntityName           SnmpAdminString,
      docsRphyRpdIfPhysEntityHardwareRev    SnmpAdminString,
      docsRphyRpdIfPhysEntityFirmwareRev    SnmpAdminString,
      docsRphyRpdIfPhysEntitySoftwareRev    SnmpAdminString,
      docsRphyRpdIfPhysEntitySerialNum      SnmpAdminString,
      docsRphyRpdIfPhysEntityMfgName        SnmpAdminString,
      docsRphyRpdIfPhysEntityModelName      SnmpAdminString,
      docsRphyRpdIfPhysEntityAlias          SnmpAdminString,
      docsRphyRpdIfPhysEntityAssetID        SnmpAdminString,
      docsRphyRpdIfPhysEntityIsFRU          TruthValue,
      docsRphyRpdIfPhysEntityMfgDate        DateAndTime,
      docsRphyRpdIfPhysEntityUris           OCTET STRING,
      docsRphyRpdIfPhysEntityUUID           UUIDorZero,
      docsRphyRpdIfPhysEntityCoreIfIndex    InterfaceIndexOrZero
}

docsRphyRpdIfPhysEntityIndex    OBJECT-TYPE
    SYNTAX      PhysicalIndex
    MAX-ACCESS  not-accessible
    STATUS      current
    DESCRIPTION
            "This key attribute reports an arbitrary value that uniquely 
             identifies the physical entity.  Index values for different 
             physical entities are not necessarily contiguous."
    ::= { docsRphyRpdIfPhysEntityEntry 1 }

docsRphyRpdIfPhysEntityDescr OBJECT-TYPE
    SYNTAX      SnmpAdminString
    MAX-ACCESS  read-only
    STATUS      current
    DESCRIPTION
            "A textual description of physical entity.  This object
            should contain a string that identifies the manufacturer's
            name for the physical entity and should be set to a
            distinct value for each version or model of the physical
            entity."
    ::= { docsRphyRpdIfPhysEntityEntry 2 }

docsRphyRpdIfPhysEntityVendorType OBJECT-TYPE
    SYNTAX      AutonomousType
    MAX-ACCESS  read-only
    STATUS      current
    DESCRIPTION
            "An indication of the vendor-specific hardware type of the
            physical entity.  Note that this is different from the
            definition of MIB-II's sysObjectID.

            An agent should set this object to an enterprise-specific
            registration identifier value indicating the specific
            equipment type in detail.  The associated instance of
            docsRphyRpdIfPhysEntityClass is used to indicate the general type of
            hardware device.

            If no vendor-specific registration identifier exists for
            this physical entity, or the value is unknown by this agent,
            then the value { 0 0 } is returned."
    ::= { docsRphyRpdIfPhysEntityEntry 3 }

docsRphyRpdIfPhysEntityContainedIn OBJECT-TYPE
    SYNTAX      PhysicalIndexOrZero
    MAX-ACCESS  read-only
    STATUS      current
    DESCRIPTION
            "The value of docsRphyRpdIfPhysEntityIndex for the physical entity that
            'contains' this physical entity.  A value of zero indicates
            this physical entity is not contained in any other physical
            entity.  Note that the set of 'containment' relationships
            define a strict hierarchy; that is, recursion is not
            allowed.

            In the event that a physical entity is contained by more
            than one physical entity (e.g., double-wide modules), this
            object should identify the containing entity with the lowest
            value of docsRphyRpdIfPhysEntityIndex."
    ::= { docsRphyRpdIfPhysEntityEntry 4 }

docsRphyRpdIfPhysEntityClass OBJECT-TYPE
    SYNTAX      IANAPhysicalClass
    MAX-ACCESS  read-only
    STATUS      current
    DESCRIPTION
            "An indication of the general hardware type of the physical
            entity.

            An agent should set this object to the standard enumeration
            value that most accurately indicates the general class of
            the physical entity, or the primary class if there is more
            than one entity.

            If no appropriate standard registration identifier exists
            for this physical entity, then the value 'other(1)' is
            returned.  If the value is unknown by this agent, then the
            value 'unknown(2)' is returned."
    ::= { docsRphyRpdIfPhysEntityEntry 5 }

docsRphyRpdIfPhysEntityParentRelPos OBJECT-TYPE
    SYNTAX      Integer32 (-1..2147483647)
    MAX-ACCESS  read-only
    STATUS      current
    DESCRIPTION
            "An indication of the relative position of this 'child'
            component among all its 'sibling' components.  Sibling
            components are defined as docsRphyRpdIfPhysEntityEntries that share the
            same instance values of each of the docsRphyRpdIfPhysEntityContainedIn
            and docsRphyRpdIfPhysEntityClass objects.

            An NMS can use this object to identify the relative ordering
            for all sibling components of a particular parent
            (identified by the docsRphyRpdIfPhysEntityContainedIn instance in each
            sibling entry).

            If possible, this value should match any external labeling
            of the physical component.  For example, for a container
            (e.g., card slot) labeled as 'slot #3',
            docsRphyRpdIfPhysEntityParentRelPos should have the value '3'.  Note
            that the docsRphyRpdIfPhysEntityEntry for the module plugged in slot 3
            should have an docsRphyRpdIfPhysEntityParentRelPos value of '1'.

            If the physical position of this component does not match
            any external numbering or clearly visible ordering, then
            user documentation or other external reference material
            should be used to determine the parent-relative position.
            If this is not possible, then the agent should assign a
            consistent (but possibly arbitrary) ordering to a given set
            of 'sibling' components, perhaps based on internal
            representation of the components.

            If the agent cannot determine the parent-relative position
            for some reason, or if the associated value of
            docsRphyRpdIfPhysEntityContainedIn is '0', then the value '-1' is
            returned.  Otherwise, a non-negative integer is returned,
            indicating the parent-relative position of this physical
            entity.

            Parent-relative ordering normally starts from '1' and
            continues to 'N', where 'N' represents the highest
            positioned child entity.  However, if the physical entities
            (e.g., slots) are labeled from a starting position of zero,
            then the first sibling should be associated with an
            docsRphyRpdIfPhysEntityParentRelPos value of '0'.  Note that this
            ordering may be sparse or dense, depending on agent
            implementation.

            The actual values returned are not globally meaningful, as
            each 'parent' component may use different numbering
            algorithms.  The ordering is only meaningful among siblings
            of the same parent component.

            The agent should retain parent-relative position values
            across reboots, either through algorithmic assignment or use
            of non-volatile storage."
    ::= { docsRphyRpdIfPhysEntityEntry 6 }

docsRphyRpdIfPhysEntityName OBJECT-TYPE
    SYNTAX      SnmpAdminString
    MAX-ACCESS  read-only
    STATUS      current
    DESCRIPTION
            "The textual name of the physical entity.  The value of this
            object should be the name of the component as assigned by
            the local device and should be suitable for use in commands
            entered at the device's 'console'.  This might be a text
            name (e.g., 'console') or a simple component number (e.g.,
            port or module number, such as '1'), depending on the
            physical component naming syntax of the device.

            If there is no local name, or if this object is otherwise
            not applicable, then this object contains a zero-length
            string.

            Note that the value of docsRphyRpdIfPhysEntityName for two physical
            entities will be the same in the event that the console
            interface does not distinguish between them, e.g., slot-1
            and the card in slot-1."
    ::= { docsRphyRpdIfPhysEntityEntry 7 }

docsRphyRpdIfPhysEntityHardwareRev    OBJECT-TYPE
    SYNTAX      SnmpAdminString
    MAX-ACCESS  read-only
    STATUS      current
    DESCRIPTION
            "The vendor-specific hardware revision string for the
            physical entity.  The preferred value is the hardware
            revision identifier actually printed on the component itself
            (if present).

            Note that if revision information is stored internally in a
            non-printable (e.g., binary) format, then the agent must
            convert such information to a printable format in an
            implementation-specific manner.

            If no specific hardware revision string is associated with
            the physical component, or if this information is unknown to
            the agent, then this object will contain a zero-length
            string."
    ::= { docsRphyRpdIfPhysEntityEntry 8 }

docsRphyRpdIfPhysEntityFirmwareRev    OBJECT-TYPE
    SYNTAX      SnmpAdminString
    MAX-ACCESS  read-only
    STATUS      current
    DESCRIPTION
            "The vendor-specific firmware revision string for the
            physical entity.

            Note that if revision information is stored internally in a
            non-printable (e.g., binary) format, then the agent must
            convert such information to a printable format in an
            implementation-specific manner.

            If no specific firmware programs are associated with the
            physical component, or if this information is unknown to the
            agent, then this object will contain a zero-length string."
    ::= { docsRphyRpdIfPhysEntityEntry 9 }

docsRphyRpdIfPhysEntitySoftwareRev    OBJECT-TYPE
    SYNTAX      SnmpAdminString
    MAX-ACCESS  read-only
    STATUS      current
    DESCRIPTION
            "The vendor-specific software revision string for the
            physical entity.

            Note that if revision information is stored internally in a
            non-printable (e.g., binary) format, then the agent must
            convert such information to a printable format in an
            implementation-specific manner.

            If no specific software programs are associated with the
            physical component, or if this information is unknown to the
            agent, then this object will contain a zero-length string."
    ::= { docsRphyRpdIfPhysEntityEntry 10 }

docsRphyRpdIfPhysEntitySerialNum   OBJECT-TYPE
    SYNTAX      SnmpAdminString (SIZE (0..32))
    MAX-ACCESS  read-only
    STATUS      current
    DESCRIPTION
            "The vendor-specific serial number string for the physical
            entity.  The preferred value is the serial number string
            actually printed on the component itself (if present).

            On the first instantiation of a physical entity, the value
            of docsRphyRpdIfPhysEntitySerialNum associated with that entity is set
            to the correct vendor-assigned serial number, if this
            information is available to the agent.  If a serial number
            is unknown or non-existent, the docsRphyRpdIfPhysEntitySerialNum will be
            set to a zero-length string instead.

            Note that implementations that can correctly identify the
            serial numbers of all installed physical entities do not
            need to provide write access to the docsRphyRpdIfPhysEntitySerialNum
            object.  Agents that cannot provide non-volatile storage
            for the docsRphyRpdIfPhysEntitySerialNum strings are not required to
            implement write access for this object.

            Not every physical component will have a serial number, or
            even need one.  Physical entities for which the associated
            value of the docsRphyRpdIfPhysEntityIsFRU object is equal to 'false(2)'
            (e.g., the repeater ports within a repeater module) do not
            need their own unique serial numbers.  An agent does not
            have to provide write access for such entities and may
            return a zero-length string."
    ::= { docsRphyRpdIfPhysEntityEntry 11 }

docsRphyRpdIfPhysEntityMfgName   OBJECT-TYPE
    SYNTAX      SnmpAdminString
    MAX-ACCESS  read-only
    STATUS      current
    DESCRIPTION
            "The name of the manufacturer of this physical component.
            The preferred value is the manufacturer name string actually
            printed on the component itself (if present).

            Note that comparisons between instances of the
            docsRphyRpdIfPhysEntityModelName, docsRphyRpdIfPhysEntityFirmwareRev,
            docsRphyRpdIfPhysEntitySoftwareRev, and the docsRphyRpdIfPhysEntitySerialNum
            objects are only meaningful amongst docsRphyRpdIfPhysEntityEntries with
            the same value of docsRphyRpdIfPhysEntityMfgName.

            If the manufacturer name string associated with the physical
            component is unknown to the agent, then this object will
            contain a zero-length string."
    ::= { docsRphyRpdIfPhysEntityEntry 12 }

docsRphyRpdIfPhysEntityModelName   OBJECT-TYPE
    SYNTAX      SnmpAdminString
    MAX-ACCESS  read-only
    STATUS      current
    DESCRIPTION
            "The vendor-specific model name identifier string associated
            with this physical component.  The preferred value is the
            customer-visible part number, which may be printed on the
            component itself.

            If the model name string associated with the physical
            component is unknown to the agent, then this object will
            contain a zero-length string."
    ::= { docsRphyRpdIfPhysEntityEntry 13 }

docsRphyRpdIfPhysEntityAlias    OBJECT-TYPE
    SYNTAX      SnmpAdminString (SIZE (0..32))
    MAX-ACCESS  read-only
    STATUS      current
    DESCRIPTION
            "This object is an 'alias' name for the physical entity, as
            specified by a network manager, and provides a non-volatile
            'handle' for the physical entity.

            On the first instantiation of a physical entity, the value
            of docsRphyRpdIfPhysEntityAlias associated with that entity is set to
            the zero-length string.  However, the agent may set the
            value to a locally unique default value, instead of a
            zero-length string."
    ::= { docsRphyRpdIfPhysEntityEntry 14 }

docsRphyRpdIfPhysEntityAssetID OBJECT-TYPE
    SYNTAX      SnmpAdminString (SIZE (0..32))
    MAX-ACCESS  read-only
    STATUS      current
    DESCRIPTION
            "This object is a user-assigned asset tracking identifier
            (as specified by a network manager) for the physical entity
            and provides non-volatile storage of this information.

            On the first instantiation of a physical entity, the value
            of docsRphyRpdIfPhysEntityAssetID associated with that entity is set to
            the zero-length string.

            Not every physical component will have an asset tracking
            identifier or even need one.  Physical entities for which
            the associated value of the docsRphyRpdIfPhysEntityIsFRU object is equal
            to 'false(2)' (e.g., the repeater ports within a repeater
            module) do not need their own unique asset tracking
            identifier.  An agent does not have to provide write access
            for such entities and may instead return a zero-length
            string.

            If no asset tracking information is associated with the
            physical component, then this object will contain a
            zero-length string."
    ::= { docsRphyRpdIfPhysEntityEntry 15 }

docsRphyRpdIfPhysEntityIsFRU OBJECT-TYPE
    SYNTAX      TruthValue
    MAX-ACCESS  read-only
    STATUS      current
    DESCRIPTION
            "This object indicates whether or not this physical entity
            is considered a 'field replaceable unit' by the vendor.
            If this object contains the value 'true(1)', then this
            docsRphyRpdIfPhysEntityEntry identifies a field replaceable unit.  For
            all docsRphyRpdIfPhysEntityEntries that represent components
            permanently contained within a field replaceable unit, the
            value 'false(2)' should be returned for this object."
    ::= { docsRphyRpdIfPhysEntityEntry 16 }

docsRphyRpdIfPhysEntityMfgDate  OBJECT-TYPE
    SYNTAX      DateAndTime
    MAX-ACCESS  read-only
    STATUS      current
    DESCRIPTION
            "This object contains the date of manufacturing of the
            managed entity.  If the manufacturing date is unknown or
            not supported, the object is not instantiated.  The special
            value '0000000000000000'H may also be returned in this
            case."
    ::= { docsRphyRpdIfPhysEntityEntry 17 }

docsRphyRpdIfPhysEntityUris OBJECT-TYPE
    SYNTAX      OCTET STRING
    MAX-ACCESS  read-only
    STATUS      current
    DESCRIPTION
            "This object contains identification
            information about the physical entity.  The object
            contains URIs; therefore, the syntax of this object
            must conform to RFC 3986, Section 3.

            Multiple URIs may be present and are separated by white
            space characters.  Leading and trailing white space
            characters are ignored.

            If no URI identification information is known
            about the physical entity, the object is not
            instantiated.  A zero-length octet string may also be
            returned in this case."
    REFERENCE
            "RFC 3986, Uniform Resource Identifiers (URI): Generic
            Syntax, Section 2, August 1998."
    ::= { docsRphyRpdIfPhysEntityEntry 18 }

docsRphyRpdIfPhysEntityUUID OBJECT-TYPE
    SYNTAX      UUIDorZero
    MAX-ACCESS  read-only
    STATUS      current
    DESCRIPTION
            "This object contains identification information
            about the physical entity.  The object contains a
            Universally Unique Identifier, the syntax of this object
            must conform to RFC 4122, Section 4.1.

            A zero-length octet string is returned if no UUID
            information is known."
    REFERENCE
            "RFC 4122, A Universally Unique IDentifier (UUID) URN
            Namespace, Section 4.1, July 2005."
    ::= { docsRphyRpdIfPhysEntityEntry 19 }
    
docsRphyRpdIfPhysEntityCoreIfIndex OBJECT-TYPE
    SYNTAX     InterfaceIndexOrZero
    MAX-ACCESS read-only
    STATUS     current
    DESCRIPTION
           "If the entity represents an ifTable interface on the CCAP 
            Core, this attribute provides the ifIndex assigned by the 
            CCAP Core to that entity. Otherwise, this attribute returns 
            a value of zero."
    ::= { docsRphyRpdIfPhysEntityEntry 20 }
    
-- ---------------------------------------------------------------------
-- RPD Entity Sensor Table extracted from RFC 3433 ENTITY-SENSOR-MIB
-- ---------------------------------------------------------------------

docsRphyRpdIfPhysEntSensorTable OBJECT-TYPE
    SYNTAX        SEQUENCE OF DocsRphyRpdIfPhysEntSensorEntry
    MAX-ACCESS    not-accessible
    STATUS        current
    DESCRIPTION
            "This table contains one row per physical sensor represented
            by an associated row in the docsRphyRpdIfPhysEntityTable.
            See the reference for additional requirements."
    REFERENCE
        "DOCSIS DCA MHAv2 Remote PHY OSS Interface Specification
         CM-SP-R-OSSI-I04-160923, Sensor section."
    ::= { docsRphyRpdIfMibObjects 2 }

docsRphyRpdIfPhysEntSensorEntry OBJECT-TYPE
    SYNTAX        DocsRphyRpdIfPhysEntSensorEntry
    MAX-ACCESS    not-accessible
    STATUS        current
    DESCRIPTION
            "Information about a particular physical sensor.

            An entry in this table describes the present reading of a
            sensor, the measurement units and scale, and sensor
            operational status.

            Entries are created in this table by the agent.  The CCAP 
            Core SHOULD create an entry for each physical sensor at 
            the same time as the associated Entity table instance. 
            The CCAP Core SHOULD delete an entry if the associated 
            Entity table entry is deleted."
    INDEX  { docsRphyRpdDevInfoUniqueId,
             docsRphyRpdIfPhysEntityIndex }    
    ::= { docsRphyRpdIfPhysEntSensorTable 1 }

DocsRphyRpdIfPhysEntSensorEntry ::= SEQUENCE {
        docsRphyRpdIfPhysEntSensorType            EntitySensorDataType,
        docsRphyRpdIfPhysEntSensorScale           EntitySensorDataScale,
        docsRphyRpdIfPhysEntSensorPrecision       EntitySensorPrecision,
        docsRphyRpdIfPhysEntSensorValue           EntitySensorValue,
        docsRphyRpdIfPhysEntSensorOperStatus      EntitySensorStatus,
        docsRphyRpdIfPhysEntSensorUnitsDisplay    SnmpAdminString,
        docsRphyRpdIfPhysEntSensorValueTimeStamp  TimeStamp,
        docsRphyRpdIfPhysEntSensorValueUpdateRate Unsigned32
}

docsRphyRpdIfPhysEntSensorType OBJECT-TYPE
    SYNTAX        EntitySensorDataType
    MAX-ACCESS    read-only
    STATUS        current
    DESCRIPTION
            "This attribute reports the type of data returned by the 
             associated Value attribute.

             The CCAP Core SHOULD set the value during instance creation. 
             The CCAP Core SHOULD NOT change the value during operation."
    ::= { docsRphyRpdIfPhysEntSensorEntry 1 }

docsRphyRpdIfPhysEntSensorScale OBJECT-TYPE
    SYNTAX        EntitySensorDataScale
    MAX-ACCESS    read-only
    STATUS        current
    DESCRIPTION
            "This attribute reports a data scaling factor, represented 
             with an International System of Units (SI) prefix.  The 
             actual data units are determined by examining this attribute 
             together with the associated SensorType attribute.
             This attribute is defined together with SensorType and 
             Precision.  
             Together, these three attributes are used to identify the 
             semantics of the Value attribute."
    ::= { docsRphyRpdIfPhysEntSensorEntry 2 }

docsRphyRpdIfPhysEntSensorPrecision OBJECT-TYPE
    SYNTAX        EntitySensorPrecision
    MAX-ACCESS    read-only
    STATUS        current
    DESCRIPTION
            "This attribute reports the number of decimal places of 
             precision in fixed-point sensor values returned by the 
             associated Value attribute.
             This attribute should be set to '0' when the associated 
             SensorType value is not a fixed-point type: e.g., 
             'percentRH(9)', 'rpm(10)', 'cmm(11)', or 'truthvalue(12)'."
    ::= { docsRphyRpdIfPhysEntSensorEntry 3 }

docsRphyRpdIfPhysEntSensorValue OBJECT-TYPE
    SYNTAX        EntitySensorValue
    MAX-ACCESS    read-only
    STATUS        current
    DESCRIPTION
            "This attribute reports the most recent measurement obtained 
             by the RPD for this sensor.

             To correctly interpret the value of this object, the
             associated SensorType, SensorScale, and
             SensorPrecision attributes must also be examined."
    ::= { docsRphyRpdIfPhysEntSensorEntry 4 }

docsRphyRpdIfPhysEntSensorOperStatus OBJECT-TYPE
    SYNTAX        EntitySensorStatus
    MAX-ACCESS    read-only
    STATUS        current
    DESCRIPTION
            "The operational status of the sensor."
    ::= { docsRphyRpdIfPhysEntSensorEntry 5 }

docsRphyRpdIfPhysEntSensorUnitsDisplay OBJECT-TYPE
    SYNTAX      SnmpAdminString
    MAX-ACCESS  read-only
    STATUS      current
    DESCRIPTION
            "A textual description of the data units that should be used
            in the display of SensorValue."
    ::= { docsRphyRpdIfPhysEntSensorEntry 6 }

docsRphyRpdIfPhysEntSensorValueTimeStamp OBJECT-TYPE
    SYNTAX        TimeStamp
    MAX-ACCESS    read-only
    STATUS        current
    DESCRIPTION
            "This attribute reports the value of RpdSysUpTime at the 
             time the status and/or value of this sensor was last 
             obtained by the RPD."
    ::= { docsRphyRpdIfPhysEntSensorEntry 7 }

docsRphyRpdIfPhysEntSensorValueUpdateRate  OBJECT-TYPE
    SYNTAX        Unsigned32
    UNITS         "milliseconds"
    MAX-ACCESS    read-only
    STATUS        current
    DESCRIPTION
            "This attribute reports an indication of the frequency that 
             the CCAP Core updates the associated Value object, 
             represented in milliseconds.

            The value zero indicates:

                - the sensor value is updated on demand 
                - the sensor value is updated when the sensor
                  value changes (event-driven)
                - the RPD does not know the update rate."
    ::= { docsRphyRpdIfPhysEntSensorEntry 8 }
  
-- ---------------------------------------------------------------------
-- RPD Ethernet Interface Table Objects
-- ---------------------------------------------------------------------
docsRphyRpdIfEnetTable OBJECT-TYPE
    SYNTAX      SEQUENCE OF DocsRphyRpdIfEnetEntry
    MAX-ACCESS  not-accessible
    STATUS      current
    DESCRIPTION
            "This table provides details about the Ethernet interfaces 
             on the RPD. The attributes of this object are based on the 
             ifTable/ifXTable specified in RFC 2863.
             The CCAP Core MUST create an instance of this object for 
             every Ethernet interface on the RPD.
             See the reference for additional requirements."
    REFERENCE
        "DOCSIS DCA MHAv2 Remote PHY OSS Interface Specification
         CM-SP-R-OSSI-I04-160923, EnetIf section."
    ::= { docsRphyRpdIfMibObjects 3 }

docsRphyRpdIfEnetEntry OBJECT-TYPE
    SYNTAX      DocsRphyRpdIfEnetEntry
    MAX-ACCESS  not-accessible
    STATUS      current
    DESCRIPTION
            "An entry containing management information applicable to a
            particular interface.
            The Ethernet IfIndex is chosen by the RPD."
    INDEX   { docsRphyRpdDevInfoUniqueId,
              docsRphyRpdIfEnetPortIndex }
    ::= { docsRphyRpdIfEnetTable 1 }

DocsRphyRpdIfEnetEntry ::=
    SEQUENCE {
        docsRphyRpdIfEnetPortIndex             Unsigned32,
        docsRphyRpdIfEnetDescr                 SnmpAdminString,
        docsRphyRpdIfEnetName                  SnmpAdminString,
        docsRphyRpdIfEnetAlias                 SnmpAdminString,
        docsRphyRpdIfEnetType                  IANAifType,
        docsRphyRpdIfEnetMtu                   Integer32,
        docsRphyRpdIfEnetPhysAddress           PhysAddress,
        docsRphyRpdIfEnetAdminStatus           INTEGER,
        docsRphyRpdIfEnetOperStatus            INTEGER,
        docsRphyRpdIfEnetLastChange            TimeStamp,
        docsRphyRpdIfEnetLinkUpDownTrapEnable  TruthValue,
        docsRphyRpdIfEnetHighSpeed             Gauge32,
        docsRphyRpdIfEnetPromiscuousMode       TruthValue,
        docsRphyRpdIfEnetConnectorPresent      TruthValue       
    }

docsRphyRpdIfEnetPortIndex OBJECT-TYPE
    SYNTAX      Unsigned32 (0..255)
    MAX-ACCESS  not-accessible
    STATUS      current
    DESCRIPTION
            "This key attribute reports a unique index for this 
             Ethernet port interface."
    ::= { docsRphyRpdIfEnetEntry 1 }

docsRphyRpdIfEnetDescr OBJECT-TYPE
    SYNTAX      SnmpAdminString (SIZE (0..255))
    MAX-ACCESS  read-only
    STATUS      current
    DESCRIPTION
            "A textual string containing information about the
            interface.  This string should include the name of the
            manufacturer, the product name and the version of the
            interface hardware/software."
    ::= { docsRphyRpdIfEnetEntry 2 }
    
docsRphyRpdIfEnetName OBJECT-TYPE
    SYNTAX      SnmpAdminString
    MAX-ACCESS  read-only
    STATUS      current
    DESCRIPTION
            "This attribute reports a textual string representing a 
             name that describes the interface. The CCAP Core MUST 
             populate this object with the ID that is used in GCP for 
             this port."
    ::= { docsRphyRpdIfEnetEntry 3 }

docsRphyRpdIfEnetAlias   OBJECT-TYPE
    SYNTAX      SnmpAdminString (SIZE(0..64))
    MAX-ACCESS  read-only
    STATUS      current
    DESCRIPTION
            "This attribute reports an Alias for the interface. On the 
             first instantiation of an interface, the value of Alias 
             associated with that interface is the zero-length string. 
             As and when a value is written into an instance of Alias 
             through a network management operation, then the RPD 
             retains the supplied value in the Alias instance 
             associated with the same interface for as long as that 
             interface remains instantiated, including across all 
             re-initializations/reboots of the network management 
             system, including those which result in a change of the 
             interface's EnetPortIndex value."
    ::= { docsRphyRpdIfEnetEntry 4 }

docsRphyRpdIfEnetType OBJECT-TYPE
    SYNTAX      IANAifType
    MAX-ACCESS  read-only
    STATUS      current
    DESCRIPTION
            "This attribute reports the type of interface. Additional 
             values for Type are assigned by the Internet Assigned 
             Numbers Authority (IANA), through updating the syntax of 
             the IANAifType textual convention. The types are defined 
             in the IANAifType-MIB. The value reported by this 
             attribute is ethernetCsmacd."
    ::= { docsRphyRpdIfEnetEntry 5 }

docsRphyRpdIfEnetMtu OBJECT-TYPE
    SYNTAX      Integer32
    MAX-ACCESS  read-only
    STATUS      current
    DESCRIPTION
            "This attribute reports the size of the largest packet which 
             can be sent/received on the interface, specified in octets. 
             For interfaces that are used for transmitting network 
             datagrams, this is the size of the largest network datagram 
             that can be sent on the interface."
    ::= { docsRphyRpdIfEnetEntry 6 }

docsRphyRpdIfEnetPhysAddress OBJECT-TYPE
    SYNTAX      PhysAddress
    MAX-ACCESS  read-only
    STATUS      current
    DESCRIPTION
            "This attribute reports the interface's address at its 
             protocol sub-layer. For example, for an 802.x interface, 
             this attribute normally contains a MAC address. The 
             interface's media-specific MIB defines the bit and byte 
             ordering and the format of the value of this attribute. 
             For interfaces which do not have such an address (e.g., a 
             serial line), this attribute reports an octet string of 
             zero length."
    ::= { docsRphyRpdIfEnetEntry 7 }

docsRphyRpdIfEnetAdminStatus OBJECT-TYPE
    SYNTAX  INTEGER {
                up(1),       
                down(2),
                testing(3)   
            }
    MAX-ACCESS  read-only
    STATUS      current
    DESCRIPTION
            "This attribute reports the state of the interface. The 
             testing(3) state indicates that no operational packets can
             be passed. When a managed system initializes, all 
             interfaces start with AdminStatus in the down(2) state. 
             As a result of either explicit management action or per 
             configuration information retained by the managed system, 
             AdminStatus is then changed to either the up(1) or 
             testing(3) states (or remains in the down(2) state)."
    ::= { docsRphyRpdIfEnetEntry 8 }

docsRphyRpdIfEnetOperStatus OBJECT-TYPE
    SYNTAX  INTEGER {
                up(1),        
                down(2),
                testing(3),  
                unknown(4),   
                dormant(5),
                notPresent(6),    
                lowerLayerDown(7) 
            }
    MAX-ACCESS  read-only
    STATUS      current
    DESCRIPTION
            "This attribute reports the current operational state of 
             the interface. The testing(3) state indicates that no 
             operational packets can be passed.  If AdminStatus is 
             down(2) then ifOperStatus should be down(2).  If 
             AdminStatus is changed to up(1), then OperStatus should 
             change to up(1) if the interface is ready to transmit and 
             receive network traffic; it should change to dormant(5) if 
             the interface is waiting for external actions (such as a 
             serial line waiting for an incoming connection); it should 
             remain in the down(2) state if and only if there is a fault 
             that prevents it from going to the up(1) state; it should 
             remain in the notPresent(6) state if the interface has 
             missing (typically, hardware) components."
    ::= { docsRphyRpdIfEnetEntry 9 }

docsRphyRpdIfEnetLastChange OBJECT-TYPE
    SYNTAX      TimeStamp
    MAX-ACCESS  read-only
    STATUS      current
    DESCRIPTION
            "This attribute reports the value of RpdSysUpTime at the 
             time the interface entered its current operational state.  
             If the current state was entered prior to the last 
             re-initialization of the local network management 
             subsystem, then this attribute reports a zero value."
    ::= { docsRphyRpdIfEnetEntry 10 }

docsRphyRpdIfEnetLinkUpDownTrapEnable  OBJECT-TYPE
    SYNTAX      TruthValue
    MAX-ACCESS  read-only
    STATUS      current
    DESCRIPTION
            "This attribute reports whether linkup/linkdown traps are 
             generated for this interface.
             A value of true indicates that traps are enabled.
             A value of false indicates that traps are disabled."
    ::= { docsRphyRpdIfEnetEntry 11 }

docsRphyRpdIfEnetHighSpeed OBJECT-TYPE
    SYNTAX      Gauge32
    MAX-ACCESS  read-only
    STATUS      current
    DESCRIPTION
            "This attribute reports an estimate of the interface's 
            current bandwidth in units of 1,000,000 bits per second.  
            If this attribute reports a value of 'n' then the speed of 
            the interface is somewhere in the range of 'n-500,000' to 
            'n+499,999'.  For interfaces which do not vary in bandwidth 
            or for those where no accurate estimation can be made, this 
            attribute reports the nominal bandwidth."
    ::= { docsRphyRpdIfEnetEntry 12 }

docsRphyRpdIfEnetPromiscuousMode  OBJECT-TYPE
    SYNTAX      TruthValue
    MAX-ACCESS  read-only
    STATUS      current
    DESCRIPTION
            "This attribute reports a value of '2' (false) if this 
             interface only accepts packets/frames that are addressed 
             to this interface.
             This attribute reports a value of '1' (true) when the 
             station accepts all packets/frames transmitted on the media.  
             The value of PromiscuousMode does not affect the reception 
             of broadcast and multicast packets/frames by the interface."
    ::= { docsRphyRpdIfEnetEntry 13 }

docsRphyRpdIfEnetConnectorPresent   OBJECT-TYPE
    SYNTAX      TruthValue
    MAX-ACCESS  read-only
    STATUS      current
    DESCRIPTION
            "This attribute reports the value 'true' if the interface 
             sublayer has a physical connector and the value 'false' 
             otherwise."
    ::= { docsRphyRpdIfEnetEntry 14 }

    
-- ---------------------------------------------------------------------
-- RPD Ethernet Interface Stats Table Objects 
-- ---------------------------------------------------------------------
docsRphyRpdIfEnetStatsTable        OBJECT-TYPE
    SYNTAX      SEQUENCE OF DocsRphyRpdIfEnetStatsEntry
    MAX-ACCESS  not-accessible
    STATUS      current
    DESCRIPTION
            "This table reports statistics for the Ethernet interfaces 
             on the RPD. The attributes of this object are based on the 
             ifTable/ifXTable specified in RFC 2863. The CCAP Core MUST 
             create an instance of this object for every EnetIf object 
             instance.

             Discontinuities in the value of these counters can occur at 
             reinitialization of the managed system, and at other times as 
             indicated by the value of CounterDiscontinuityTime.
             See the reference for additional requirements."
    REFERENCE
        "DOCSIS DCA MHAv2 Remote PHY OSS Interface Specification
         CM-SP-R-OSSI-I04-160923, EnetIfStats section."
    ::= { docsRphyRpdIfMibObjects 4 }

docsRphyRpdIfEnetStatsEntry        OBJECT-TYPE
    SYNTAX      DocsRphyRpdIfEnetStatsEntry
    MAX-ACCESS  not-accessible
    STATUS      current
    DESCRIPTION
            "An entry containing statistical information
            applicable to a particular RPD ethernet interface."
    AUGMENTS    { docsRphyRpdIfEnetEntry }
    ::= { docsRphyRpdIfEnetStatsTable 1 }

DocsRphyRpdIfEnetStatsEntry ::=
    SEQUENCE {
        docsRphyRpdIfEnetStatsInOctets            Counter64,
        docsRphyRpdIfEnetStatsOutOctets           Counter64,
        docsRphyRpdIfEnetStatsInFrames            Counter64,
        docsRphyRpdIfEnetStatsOutFrames           Counter64,
        docsRphyRpdIfEnetStatsInUnicastOctets     Counter64,
        docsRphyRpdIfEnetStatsOutUnicastOctets    Counter64,
        docsRphyRpdIfEnetStatsInUnicastFrames     Counter64,
        docsRphyRpdIfEnetStatsOutUnicastFrames    Counter64,
        docsRphyRpdIfEnetStatsInMulticastOctets   Counter64,
        docsRphyRpdIfEnetStatsOutMulticastOctets  Counter64,
        docsRphyRpdIfEnetStatsInMulticastFrames   Counter64,
        docsRphyRpdIfEnetStatsOutMulticastFrames  Counter64,
        docsRphyRpdIfEnetStatsInBroadcastOctets   Counter64,
        docsRphyRpdIfEnetStatsOutBroadcastOctets  Counter64,
        docsRphyRpdIfEnetStatsInBroadcastFrames   Counter64,
        docsRphyRpdIfEnetStatsOutBroadcastFrames  Counter64,
        docsRphyRpdIfEnetStatsInDiscards          Counter64,
        docsRphyRpdIfEnetStatsOutDiscards         Counter64,
        docsRphyRpdIfEnetStatsInErrors            Counter64,
        docsRphyRpdIfEnetStatsOutErrors           Counter64,
        docsRphyRpdIfEnetStatsInUnknownProtos     Counter64,
        docsRphyRpdIfEnetStatsCounterDiscontinuityTime TimeStamp
    }

docsRphyRpdIfEnetStatsInOctets OBJECT-TYPE
    SYNTAX      Counter64
    MAX-ACCESS  read-only
    STATUS      current
    DESCRIPTION
            "The total number of octets received on the interface,
            including framing characters."
    ::= { docsRphyRpdIfEnetStatsEntry 1 }
    
docsRphyRpdIfEnetStatsOutOctets OBJECT-TYPE
    SYNTAX      Counter64
    MAX-ACCESS  read-only
    STATUS      current
    DESCRIPTION
            "The total number of octets transmitted out of the
            interface, including framing characters."
    ::= { docsRphyRpdIfEnetStatsEntry 2 }
    
docsRphyRpdIfEnetStatsInFrames OBJECT-TYPE
    SYNTAX      Counter64
    MAX-ACCESS  read-only
    STATUS      current
    DESCRIPTION
            "The total number of frames received on the interface,
            including framing characters."
    ::= { docsRphyRpdIfEnetStatsEntry 3 }
    
docsRphyRpdIfEnetStatsOutFrames OBJECT-TYPE
    SYNTAX      Counter64
    MAX-ACCESS  read-only
    STATUS      current
    DESCRIPTION
            "The total number of frames transmitted out of the
            interface, including framing characters."
    ::= { docsRphyRpdIfEnetStatsEntry 4 }
    
docsRphyRpdIfEnetStatsInUnicastOctets OBJECT-TYPE
    SYNTAX      Counter64
    MAX-ACCESS  read-only
    STATUS      current
    DESCRIPTION
            "The number of octets, delivered by this sub-layer to a
            higher (sub-)layer, which were not addressed to a multicast
            or broadcast address at this sub-layer."
    ::= { docsRphyRpdIfEnetStatsEntry 5 }
   
docsRphyRpdIfEnetStatsOutUnicastOctets OBJECT-TYPE
    SYNTAX      Counter64
    MAX-ACCESS  read-only
    STATUS      current
    DESCRIPTION
            "The total number of octets that higher-level protocols
            requested be transmitted, and which were not addressed to a
            multicast or broadcast address at this sub-layer, including
            those that were discarded or not sent."
    ::= { docsRphyRpdIfEnetStatsEntry 6 }
     
docsRphyRpdIfEnetStatsInUnicastFrames OBJECT-TYPE
    SYNTAX      Counter64
    MAX-ACCESS  read-only
    STATUS      current
    DESCRIPTION
            "The number of frames, delivered by this sub-layer to a
            higher (sub-)layer, which were not addressed to a multicast
            or broadcast address at this sub-layer."
    ::= { docsRphyRpdIfEnetStatsEntry 7 }
    
docsRphyRpdIfEnetStatsOutUnicastFrames OBJECT-TYPE
    SYNTAX      Counter64
    MAX-ACCESS  read-only
    STATUS      current
    DESCRIPTION
            "The total number of frames that higher-level protocols
            requested be transmitted, and which were not addressed to a
            multicast or broadcast address at this sub-layer, including
            those that were discarded or not sent."
    ::= { docsRphyRpdIfEnetStatsEntry 8 }
    
docsRphyRpdIfEnetStatsInMulticastOctets OBJECT-TYPE
    SYNTAX      Counter64
    MAX-ACCESS  read-only
    STATUS      current
    DESCRIPTION
            "The number of octets, delivered by this sub-layer to a
            higher (sub-)layer, which were addressed to a multicast
            address at this sub-layer.  For a MAC layer protocol, this
            includes both Group and Functional addresses."
    ::= { docsRphyRpdIfEnetStatsEntry 9 }
    
docsRphyRpdIfEnetStatsOutMulticastOctets OBJECT-TYPE
    SYNTAX      Counter64
    MAX-ACCESS  read-only
    STATUS      current
    DESCRIPTION
            "The total number of octets that higher-level protocols
            requested be transmitted, and which were addressed to a
            multicast address at this sub-layer, including those that
            were discarded or not sent.  For a MAC layer protocol, this
            includes both Group and Functional addresses."
    ::= { docsRphyRpdIfEnetStatsEntry 10 }
    
docsRphyRpdIfEnetStatsInMulticastFrames OBJECT-TYPE
    SYNTAX      Counter64
    MAX-ACCESS  read-only
    STATUS      current
    DESCRIPTION
            "The number of frames, delivered by this sub-layer to a
            higher (sub-)layer, which were addressed to a multicast
            address at this sub-layer.  For a MAC layer protocol, this
            includes both Group and Functional addresses."
    ::= { docsRphyRpdIfEnetStatsEntry 11 }

docsRphyRpdIfEnetStatsOutMulticastFrames OBJECT-TYPE
    SYNTAX      Counter64
    MAX-ACCESS  read-only
    STATUS      current
    DESCRIPTION
            "The total number of frames that higher-level protocols
            requested be transmitted, and which were addressed to a
            multicast address at this sub-layer, including those that
            were discarded or not sent.  For a MAC layer protocol, this
            includes both Group and Functional addresses."
    ::= { docsRphyRpdIfEnetStatsEntry 12 }
    
docsRphyRpdIfEnetStatsInBroadcastOctets OBJECT-TYPE
    SYNTAX      Counter64
    MAX-ACCESS  read-only
    STATUS      current
    DESCRIPTION
            "The number of octets, delivered by this sub-layer to a
            higher (sub-)layer, which were addressed to a broadcast
            address at this sub-layer."
    ::= { docsRphyRpdIfEnetStatsEntry 13 }

docsRphyRpdIfEnetStatsOutBroadcastOctets OBJECT-TYPE
    SYNTAX      Counter64
    MAX-ACCESS  read-only
    STATUS      current
    DESCRIPTION
            "The total number of octets that higher-level protocols
            requested be transmitted, and which were addressed to a
            broadcast address at this sub-layer, including those that
            were discarded or not sent."
    ::= { docsRphyRpdIfEnetStatsEntry 14 }

docsRphyRpdIfEnetStatsInBroadcastFrames OBJECT-TYPE
    SYNTAX      Counter64
    MAX-ACCESS  read-only
    STATUS      current
    DESCRIPTION
            "The number of frames, delivered by this sub-layer to a
            higher (sub-)layer, which were addressed to a broadcast
            address at this sub-layer."
    ::= { docsRphyRpdIfEnetStatsEntry 15 }

docsRphyRpdIfEnetStatsOutBroadcastFrames OBJECT-TYPE
    SYNTAX      Counter64
    MAX-ACCESS  read-only
    STATUS      current
    DESCRIPTION
            "The total number of frames that higher-level protocols
            requested be transmitted, and which were addressed to a
            broadcast address at this sub-layer, including those that
            were discarded or not sent."
    ::= { docsRphyRpdIfEnetStatsEntry 16 }

docsRphyRpdIfEnetStatsInDiscards OBJECT-TYPE
    SYNTAX      Counter64
    MAX-ACCESS  read-only
    STATUS      current
    DESCRIPTION
            "The number of inbound packets which were chosen to be
            discarded even though no errors had been detected to prevent
            their being deliverable to a higher-layer protocol.  One
            possible reason for discarding such a packet could be to
            free up buffer space."
    ::= { docsRphyRpdIfEnetStatsEntry 17 }

docsRphyRpdIfEnetStatsOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space."
    ::= { docsRphyRpdIfEnetStatsEntry 18 }
    
docsRphyRpdIfEnetStatsInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol."
    ::= { docsRphyRpdIfEnetStatsEntry 19 }

docsRphyRpdIfEnetStatsOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors."
    ::= { docsRphyRpdIfEnetStatsEntry 20 }
    
docsRphyRpdIfEnetStatsInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0."
    ::= { docsRphyRpdIfEnetStatsEntry 21 }

docsRphyRpdIfEnetStatsCounterDiscontinuityTime OBJECT-TYPE
    SYNTAX      TimeStamp
    MAX-ACCESS  read-only
    STATUS      current
    DESCRIPTION
            "The value of sysUpTime on the most recent occasion at which
            any one or more of this interface's counters suffered a
            discontinuity.  The relevant counters are the specific
            instances associated with this interface of any Counter32 or
            Counter64 object contained in the docsRphyRpdIfEnetStatsTable.  If
            no such discontinuities have occurred since the last re-
            initialization of the local management subsystem, then this
            object contains a zero value."
    ::= { docsRphyRpdIfEnetStatsEntry 22 }
    
-- ---------------------------------------------------------------------
-- RPD Ethernet Interface to CCAP Core Entity Map Table Objects 
-- ---------------------------------------------------------------------
docsRphyRpdIfRpdEnetToCoreEntityMapTable        OBJECT-TYPE
    SYNTAX      SEQUENCE OF DocsRphyRpdIfRpdEnetToCoreEntityMapEntry
    MAX-ACCESS  not-accessible
    STATUS      current
    DESCRIPTION
            "If the RPD implements an Entity for an Ethernet port 
             (which is optional), this table provides the mapping 
             between the RPD's EnetPortIndex as signaled in GCP and 
             the corresponding docsRphyRpdIfPhysEntityIndex assigned
             by the CCAP Core to report that entity.
             See the reference for additional requirements."
    REFERENCE
        "DOCSIS DCA MHAv2 Remote PHY OSS Interface Specification
         CM-SP-R-OSSI-I04-160923, EnetGcpToEntityMap section."
    ::= { docsRphyRpdIfMibObjects 5 }

docsRphyRpdIfRpdEnetToCoreEntityMapEntry        OBJECT-TYPE
    SYNTAX      DocsRphyRpdIfRpdEnetToCoreEntityMapEntry
    MAX-ACCESS  not-accessible
    STATUS      current
    DESCRIPTION
            "An entry in docsRphyRpdIfRpdEnetToCoreEntityMapTable."
    INDEX    { docsRphyRpdDevInfoUniqueId,
               docsRphyRpdIfEnetPortIndex }
    ::= { docsRphyRpdIfRpdEnetToCoreEntityMapTable 1 }

DocsRphyRpdIfRpdEnetToCoreEntityMapEntry ::=
    SEQUENCE {
        docsRphyRpdIfRpdEnetToCoreEntityMapEntityIndex           Unsigned32
    }

docsRphyRpdIfRpdEnetToCoreEntityMapEntityIndex OBJECT-TYPE
    SYNTAX      Unsigned32
    MAX-ACCESS  read-only
    STATUS      current
    DESCRIPTION
            "The value of this attribute must match the value of 
             docsRphyRpdIfPhysEntityIndex for the row in
             docsRphyRpdIfPhysEntityTable that reports the RPD Ethernet 
             port signaled in GCP with EnetPortIndex."
    ::= { docsRphyRpdIfRpdEnetToCoreEntityMapEntry 1 }
    
-- ---------------------------------------------------------------------
-- CCAP Core ifTable Interface to RPD Interface Map Table Objects 
-- ---------------------------------------------------------------------
docsRphyRpdIfCoreToRpdMapTable        OBJECT-TYPE
    SYNTAX      SEQUENCE OF DocsRphyRpdIfCoreToRpdMapEntry
    MAX-ACCESS  not-accessible
    STATUS      current
    DESCRIPTION
            "This table maps certain CCAP Core ifTable interfaces 
             identified with an ifIndex to an RPD interface identified 
             in GCP.
             See the reference for additional requirements."
    REFERENCE
        "DOCSIS DCA MHAv2 Remote PHY OSS Interface Specification
         CM-SP-R-OSSI-I04-160923, IfToGcpMap section."
    ::= { docsRphyRpdIfMibObjects 6 }

docsRphyRpdIfCoreToRpdMapEntry        OBJECT-TYPE
    SYNTAX      DocsRphyRpdIfCoreToRpdMapEntry
    MAX-ACCESS  not-accessible
    STATUS      current
    DESCRIPTION
            "An entry in docsRphyRpdIfCoreToRpdMapTable.
             An entry exists for each RPD interface directly represented 
             in the CCAP ifTable. The IfIndex corresponds to 
             a CCAP Core ifIndex for one of the following interface 
             types implemented on an RPD:

             - docsCableDownstream(128)
             - docsCableUpstreamChannel(205)
             - docsCableUpstreamRfPort(256)
             - cableDownstreamRfPort(257)
             - docsCableDownstreamOfdm(277)
             - docsCableUpstreamOfdma(278)
             - mpegTransport(214)
             - docsCableScte55d1FwdOob (283) 
             - docsCableScte55d1RetOob (284) 
             - docsCableScte55d2DsOob (285) 
             - docsCableScte55d2UsOob (286) 
             - docsCableNdf (287) 
             - docsCableNdr (288) 

             Note that this table does not contain an instance for 
             ifType ethernetCsmacd(6) because the Ethernet ports of 
             the RPD are considered internal to a logical CCAP and 
             are not reported in the CCAP ifTable."
    INDEX    { ifIndex }
    ::= { docsRphyRpdIfCoreToRpdMapTable 1 }

DocsRphyRpdIfCoreToRpdMapEntry ::=
    SEQUENCE {
        docsRphyRpdIfCoreToRpdMapRpdUniqueId           MacAddress,
        docsRphyRpdIfCoreToRpdMapRpdRfPortDirection    IfDirection,
        docsRphyRpdIfCoreToRpdMapRpdRfPortIndex        Unsigned32,
        docsRphyRpdIfCoreToRpdMapRpdRfChanType         RphyChannelType,
        docsRphyRpdIfCoreToRpdMapRpdRfChanIndex        Unsigned32
    }
    
docsRphyRpdIfCoreToRpdMapRpdUniqueId OBJECT-TYPE
    SYNTAX      MacAddress
    MAX-ACCESS  read-only
    STATUS      current
    DESCRIPTION
            "This attribute specifies the MAC address associated with
             the lowest numbered CIN facing Ethernet port. The value of 
             this attribute matches the value of the 
             docsRphyRpdDevInfoUniqueId attribute from the 
             docsRphyRpdDevInfoTable."
    ::= { docsRphyRpdIfCoreToRpdMapEntry 1 }
    
docsRphyRpdIfCoreToRpdMapRpdRfPortDirection OBJECT-TYPE
    SYNTAX      IfDirection
    MAX-ACCESS  read-only
    STATUS      current
    DESCRIPTION
            "This attribute reports the direction of an RF port, which 
             together with RpdRfPortIndex uniquely identifies an RF 
             port on the RPD. The RF port direction is signalled in the 
             GCP 'RfPortType' TLV 13.2 for an RF port interface or 
             implied by the value of the GCP 'RfChannelType' TLV 12.2 
             for an RF channel interface."
    ::= { docsRphyRpdIfCoreToRpdMapEntry 2 }
    
docsRphyRpdIfCoreToRpdMapRpdRfPortIndex OBJECT-TYPE
    SYNTAX      Unsigned32 (0..255)
    MAX-ACCESS  read-only
    STATUS      current
    DESCRIPTION
            "This attribute reports the Index of an RF port on an RPD, 
             which together with RpdRfPortDirection uniquely 
             identifies an RF port on the RPD. The value matches the 
             value signaled in GCP 'RfPortIndex' TLV 12.1 or the GCP 
             'RfPortIndex1' TLV 13.1."
    ::= { docsRphyRpdIfCoreToRpdMapEntry 3 }
    
docsRphyRpdIfCoreToRpdMapRpdRfChanType OBJECT-TYPE
    SYNTAX      RphyChannelType
    MAX-ACCESS  read-only
    STATUS      current
    DESCRIPTION
            "For RF channel interfaces, This attribute reports the type 
             of the channel as signaled in the GCP 'RfChannelType' 
             TLV 12.2. For RF port interfaces, this attribute must be 
             set to other(0). Each value of this attribute corresponds 
             to a separate sequence of channel indices."
    ::= { docsRphyRpdIfCoreToRpdMapEntry 4 }
    
docsRphyRpdIfCoreToRpdMapRpdRfChanIndex OBJECT-TYPE
    SYNTAX      Unsigned32 (0..255)
    MAX-ACCESS  read-only
    STATUS      current
    DESCRIPTION
            "For interfaces corresponding to RF channels, this attribute 
             reports the channel of the type specified in 
             RpdRfChannelType, and matches the value signaled in the GCP 
             'RfChannelIndex' TLV 12.3. For RF port interfaces, this 
             attribute reports 0."
    ::= { docsRphyRpdIfCoreToRpdMapEntry 5 }
    
-- ---------------------------------------------------------------------
-- RPD Interface to CCAP Core ifTable Interface Map Table Objects 
-- ---------------------------------------------------------------------
docsRphyRpdIfRpdToCoreMapTable        OBJECT-TYPE
    SYNTAX      SEQUENCE OF DocsRphyRpdIfRpdToCoreMapEntry
    MAX-ACCESS  not-accessible
    STATUS      current
    DESCRIPTION
            "This table maps certain RPD interface identified via GCP 
             integers to an ifIndex reported by the CCAP Core. This 
             table instruments the same information as the 
             docsRphyRpdIfCoreToRpdMapTable, but with different indexing 
             than that table.
             See the reference for additional requirements."
    REFERENCE
        "DOCSIS DCA MHAv2 Remote PHY OSS Interface Specification
         CM-SP-R-OSSI-I04-160923, GcpToIfMap section."
    ::= { docsRphyRpdIfMibObjects 7 }

docsRphyRpdIfRpdToCoreMapEntry        OBJECT-TYPE
    SYNTAX      DocsRphyRpdIfRpdToCoreMapEntry
    MAX-ACCESS  not-accessible
    STATUS      current
    DESCRIPTION
            "An entry in docsRphyRpdIfRpdToCoreMapTable.
             An entry exists for each RPD interface directly represented 
             in the CCAP ifTable. The index 'CoreIfIndex' corresponds to 
             a CCAP core ifIndex for one of the following interface 
             types implemented on an RPD:

	     - docsCableDownstream(128)
             - docsCableUpstreamChannel(205)
             - docsCableUpstreamRfPort(256)
             - cableDownstreamRfPort(257)
             - docsCableDownstreamOfdm(277)
             - docsCableUpstreamOfdma(278)
             - mpegTransport(214)
             - docsCableScte55d1FwdOob (283) 
             - docsCableScte55d1RetOob (284) 
             - docsCableScte55d2DsOob (285) 
             - docsCableScte55d2UsOob (286) 
             - docsCableNdf (287) 
             - docsCableNdr (288) 

             Note that this table does not contain an instance for 
             ifType ethernetCsmacd(6) because the Ethernet ports of 
             the RPD are considered internal to a logical CCAP and 
             are not reported in the CCAP ifTable."
    INDEX    { docsRphyRpdDevInfoUniqueId,
               docsRphyRpdIfRpdToCoreMapRpdRfPortDirection,
               docsRphyRpdIfRpdToCoreMapRpdRfPortIndex,
               docsRphyRpdIfRpdToCoreMapRpdRfChanType,
               docsRphyRpdIfRpdToCoreMapRpdRfChanIndex }
    ::= { docsRphyRpdIfRpdToCoreMapTable 1 }

DocsRphyRpdIfRpdToCoreMapEntry ::=
    SEQUENCE {
        docsRphyRpdIfRpdToCoreMapRpdRfPortDirection    IfDirection,
        docsRphyRpdIfRpdToCoreMapRpdRfPortIndex        Unsigned32,
        docsRphyRpdIfRpdToCoreMapRpdRfChanType         RphyChannelType,
        docsRphyRpdIfRpdToCoreMapRpdRfChanIndex        Unsigned32,
        docsRphyRpdIfRpdToCoreMapCoreIfIndex           InterfaceIndex
    }
    
docsRphyRpdIfRpdToCoreMapRpdRfPortDirection OBJECT-TYPE
    SYNTAX      IfDirection
    MAX-ACCESS  not-accessible
    STATUS      current
    DESCRIPTION
            "This attribute reports the direction of an RF port, which 
             together with RpdRfPortIndex uniquely identifies an RF 
             port on the RPD. The RF port direction is signalled in the 
             GCP 'RfPortType' TLV 13.2 for an RF port interface or 
             implied by the value of the GCP 'RfChannelType' TLV 12.2 
             for an RF channel interface."
    ::= { docsRphyRpdIfRpdToCoreMapEntry 1 }
    
docsRphyRpdIfRpdToCoreMapRpdRfPortIndex OBJECT-TYPE
    SYNTAX      Unsigned32 (0..255)
    MAX-ACCESS  not-accessible
    STATUS      current
    DESCRIPTION
            "This attribute reports the Index of an RF port on an RPD, 
             which together with RpdRfPortDirection uniquely 
             identifies an RF port on the RPD. The value matches the 
             value signaled in GCP 'RfPortIndex' TLV 12.1 or the GCP 
             'RfPortIndex1' TLV 13.1."
    ::= { docsRphyRpdIfRpdToCoreMapEntry 2 }
    
docsRphyRpdIfRpdToCoreMapRpdRfChanType OBJECT-TYPE
    SYNTAX      RphyChannelType
    MAX-ACCESS  not-accessible
    STATUS      current
    DESCRIPTION
            "For RF channel interfaces, This attribute reports the type 
             of the channel as signaled in the GCP 'RfChannelType' 
             TLV 12.2. For RF port interfaces, this attribute must be 
             set to other(0). Each value of this attribute corresponds 
             to a separate sequence of channel indices."
    ::= { docsRphyRpdIfRpdToCoreMapEntry 3 }
    
docsRphyRpdIfRpdToCoreMapRpdRfChanIndex OBJECT-TYPE
    SYNTAX      Unsigned32 (0..255)
    MAX-ACCESS  not-accessible
    STATUS      current
    DESCRIPTION
            "For interfaces corresponding to RF channels, this attribute 
             reports the channel of the type specified in 
             RpdRfChannelType, and matches the value signaled in the GCP 
             'RfChannelIndex' TLV 12.3. For RF port interfaces, this 
             attribute reports 0."
    ::= { docsRphyRpdIfRpdToCoreMapEntry 4 }
    
docsRphyRpdIfRpdToCoreMapCoreIfIndex OBJECT-TYPE
    SYNTAX      InterfaceIndex
    MAX-ACCESS  read-only
    STATUS      current
    DESCRIPTION
            "This key attribute reports the CCAP Core IfIndex for the 
             RPD Interface identified in GCP."
    ::= { docsRphyRpdIfRpdToCoreMapEntry 5 }
    
-- ---------------------------------------------------------------------
-- RPD IP Group Objects Derived from IP-MIB RFC 4293
-- ---------------------------------------------------------------------

-- ---------------------------------------------------------------------
-- IPv4 Scalar Group Objects
-- ---------------------------------------------------------------------
docsRphyRpdIpv4GrpTable OBJECT-TYPE
    SYNTAX     SEQUENCE OF DocsRphyRpdIpv4GrpEntry
    MAX-ACCESS not-accessible
    STATUS     current
    DESCRIPTION
           "The table containing per-RPD IPv4-specific
            information."
    ::= { docsRphyRpdIpMibObjects 1 }

docsRphyRpdIpv4GrpEntry OBJECT-TYPE
    SYNTAX     DocsRphyRpdIpv4GrpEntry
    MAX-ACCESS not-accessible
    STATUS     current
    DESCRIPTION
           "An entry containing IPv4-specific information for a specific
            RPD."
    INDEX { docsRphyRpdDevInfoUniqueId }
    ::= { docsRphyRpdIpv4GrpTable 1 }

DocsRphyRpdIpv4GrpEntry ::= SEQUENCE {
        docsRphyRpdIpv4GrpDefaultTTL                 Integer32,
        docsRphyRpdIpv4GrpInterfaceTableLastChange   TimeStamp
    }

docsRphyRpdIpv4GrpDefaultTTL OBJECT-TYPE
    SYNTAX     Integer32 (1..255)
    MAX-ACCESS read-only
    STATUS     current
    DESCRIPTION
           "The default value inserted into the Time-To-Live field of
            the IPv4 header of datagrams originated at this entity,
            whenever a TTL value is not supplied by the transport layer
            protocol."
    ::= { docsRphyRpdIpv4GrpEntry 1 }
    
docsRphyRpdIpv4GrpInterfaceTableLastChange OBJECT-TYPE
    SYNTAX     TimeStamp
    MAX-ACCESS read-only
    STATUS     current
    DESCRIPTION
           "This attribute reports the value of RpdSysUpTime on the 
            most recent occasion at which an instance of the 
            Ipv4Interface object was added or deleted, or when a 
            ReasmMaxSize or an EnableStatus attribute of the 
            Ipv4Interface object was modified."
    ::= { docsRphyRpdIpv4GrpEntry 2 }

-- ---------------------------------------------------------------------
-- IPv6 Scalar Group Objects
-- ---------------------------------------------------------------------
docsRphyRpdIpv6GrpTable OBJECT-TYPE
    SYNTAX     SEQUENCE OF DocsRphyRpdIpv6GrpEntry
    MAX-ACCESS not-accessible
    STATUS     current
    DESCRIPTION
           "The table containing per-RPD IPv6-specific
            information."
    ::= { docsRphyRpdIpMibObjects 2 }

docsRphyRpdIpv6GrpEntry OBJECT-TYPE
    SYNTAX     DocsRphyRpdIpv6GrpEntry
    MAX-ACCESS not-accessible
    STATUS     current
    DESCRIPTION
           "An entry containing IPv6-specific information for a specific
            RPD."
    INDEX { docsRphyRpdDevInfoUniqueId }
    ::= { docsRphyRpdIpv6GrpTable 1 }

DocsRphyRpdIpv6GrpEntry ::= SEQUENCE {
        docsRphyRpdIpv6GrpIpDefaultHopLimit        Integer32, 
        docsRphyRpdIpv6GrpInterfaceTableLastChange TimeStamp,
        docsRphyRpdIpv6GrpIfStatsTableLastChange   TimeStamp
    }

docsRphyRpdIpv6GrpIpDefaultHopLimit OBJECT-TYPE
    SYNTAX     Integer32 (0..255)
    MAX-ACCESS read-only
    STATUS     current
    DESCRIPTION
           "The default value inserted into the Hop Limit field of the
            IPv6 header of datagrams originated at this entity whenever
            a Hop Limit value is not supplied by the transport layer
            protocol."
    REFERENCE "RFC 2461 Section 6.3.2"
    ::= { docsRphyRpdIpv6GrpEntry 1 }
    
docsRphyRpdIpv6GrpInterfaceTableLastChange OBJECT-TYPE
    SYNTAX     TimeStamp
    MAX-ACCESS read-only
    STATUS     current
    DESCRIPTION
           "This attribute reports the value of RpdSysUpTime on the 
            most recent occasion at which an instance of the 
            Ipv6Interface object was added or deleted or when a 
            ReasmMaxSize, InterfaceIdentifier, EnableStatus, 
            ReachableTime, RetransmitTime, or Forwarding attribute 
            of the Ipv6Interface object was modified."
    ::= { docsRphyRpdIpv6GrpEntry 2 }
    
docsRphyRpdIpv6GrpIfStatsTableLastChange OBJECT-TYPE
    SYNTAX     TimeStamp
    MAX-ACCESS read-only
    STATUS     current
    DESCRIPTION
           "This attribute reports the value of RpdSysUpTime on the most 
            recent occasion at which an instance of the ipIfStats object 
            was added or deleted."
    ::= { docsRphyRpdIpv6GrpEntry 3 }
    
-- ---------------------------------------------------------------------
-- IPv4 Interface Table
-- ---------------------------------------------------------------------

docsRphyRpdIpv4InterfaceTable OBJECT-TYPE
    SYNTAX     SEQUENCE OF DocsRphyRpdIpv4InterfaceEntry
    MAX-ACCESS not-accessible
    STATUS     current
    DESCRIPTION
           "The table containing per-interface IPv4-specific
            information."
    ::= { docsRphyRpdIpMibObjects 3 }

docsRphyRpdIpv4InterfaceEntry OBJECT-TYPE
    SYNTAX     DocsRphyRpdIpv4InterfaceEntry
    MAX-ACCESS not-accessible
    STATUS     current
    DESCRIPTION
           "An entry containing IPv4-specific information for an RPD's
            ethernet port."
    INDEX { docsRphyRpdDevInfoUniqueId,
            docsRphyRpdIfEnetPortIndex }
    ::= { docsRphyRpdIpv4InterfaceTable 1 }

DocsRphyRpdIpv4InterfaceEntry ::= SEQUENCE {
        docsRphyRpdIpv4InterfaceEnableStatus    INTEGER,
        docsRphyRpdIpv4InterfaceRetransmitTime  Unsigned32
    }

docsRphyRpdIpv4InterfaceEnableStatus OBJECT-TYPE
    SYNTAX     INTEGER {
                 up(1),
                 down(2)
    }
    MAX-ACCESS read-only
    STATUS     current
    DESCRIPTION
           "The indication of whether IPv4 is enabled (up) or disabled
            (down) on this interface.  This object does not affect the
            state of the interface itself, only its connection to an
            IPv4 stack.  The IF-MIB should be used to control the state
            of the interface."
    ::= { docsRphyRpdIpv4InterfaceEntry 1 }

docsRphyRpdIpv4InterfaceRetransmitTime OBJECT-TYPE
    SYNTAX     Unsigned32
    UNITS      "milliseconds"
    MAX-ACCESS read-only
    STATUS     current
    DESCRIPTION
           "The time between retransmissions of ARP requests to a
            neighbor when resolving the address or when probing the
            reachability of a neighbor."
    ::= { docsRphyRpdIpv4InterfaceEntry 2 }

-- ---------------------------------------------------------------------
-- IPv6 Interface Table
-- ---------------------------------------------------------------------

docsRphyRpdIpv6InterfaceTable OBJECT-TYPE
    SYNTAX     SEQUENCE OF DocsRphyRpdIpv6InterfaceEntry
    MAX-ACCESS not-accessible
    STATUS     current
    DESCRIPTION
           "The table containing per-interface IPv6-specific
            information."
    ::= { docsRphyRpdIpMibObjects 4 }

docsRphyRpdIpv6InterfaceEntry OBJECT-TYPE
    SYNTAX     DocsRphyRpdIpv6InterfaceEntry
    MAX-ACCESS not-accessible
    STATUS     current
    DESCRIPTION
           "An entry containing IPv6-specific information for an RPD's
            ethernet port."
    INDEX { docsRphyRpdDevInfoUniqueId,
            docsRphyRpdIfEnetPortIndex }
    ::= { docsRphyRpdIpv6InterfaceTable 1 }

DocsRphyRpdIpv6InterfaceEntry ::= SEQUENCE {
        docsRphyRpdIpv6InterfaceIdentifier      Ipv6AddressIfIdentifierTC,
        docsRphyRpdIpv6InterfaceEnableStatus    INTEGER,
        docsRphyRpdIpv6InterfaceReachableTime   Unsigned32,
        docsRphyRpdIpv6InterfaceRetransmitTime  Unsigned32
    }

docsRphyRpdIpv6InterfaceIdentifier OBJECT-TYPE
    SYNTAX     Ipv6AddressIfIdentifierTC
    MAX-ACCESS read-only
    STATUS     current
    DESCRIPTION
           "The Interface Identifier for this interface.  The Interface
            Identifier is combined with an address prefix to form an
            interface address.

            By default, the Interface Identifier is auto-configured
            according to the rules of the link type to which this
            interface is attached.

            A zero length identifier may be used where appropriate."
    ::= { docsRphyRpdIpv6InterfaceEntry 1 }

docsRphyRpdIpv6InterfaceEnableStatus OBJECT-TYPE
    SYNTAX     INTEGER {
                 up(1),
                 down(2)
    }
    MAX-ACCESS read-only
    STATUS     current
    DESCRIPTION
           "The indication of whether IPv6 is enabled (up) or disabled
            (down) on this interface.  This object does not affect the
            state of the interface itself, only its connection to an
            IPv6 stack.  The IF-MIB should be used to control the state
            of the interface."
    ::= { docsRphyRpdIpv6InterfaceEntry 2 }

docsRphyRpdIpv6InterfaceReachableTime OBJECT-TYPE
    SYNTAX     Unsigned32
    UNITS      "milliseconds"
    MAX-ACCESS read-only
    STATUS     current
    DESCRIPTION
           "The time a neighbor is considered reachable after receiving
            a reachability confirmation."
    REFERENCE "RFC 2461, Section 6.3.2"
    ::= { docsRphyRpdIpv6InterfaceEntry 3 }

docsRphyRpdIpv6InterfaceRetransmitTime OBJECT-TYPE
    SYNTAX     Unsigned32
    UNITS      "milliseconds"
    MAX-ACCESS read-only
    STATUS     current
    DESCRIPTION
           "The time between retransmissions of Neighbor Solicitation
            messages to a neighbor when resolving the address or when
            probing the reachability of a neighbor."
    REFERENCE "RFC 2461, Section 6.3.2"
    ::= { docsRphyRpdIpv6InterfaceEntry 4 }

-- ---------------------------------------------------------------------
-- Per-Interface IP Statistics Table
-- ---------------------------------------------------------------------

docsRphyRpdIpIfStatsTable OBJECT-TYPE
    SYNTAX     SEQUENCE OF DocsRphyRpdIpIfStatsEntry
    MAX-ACCESS not-accessible
    STATUS     current
    DESCRIPTION
           "This table provides statistics for IP Packets sent or 
            received by an RPD's own IP Address.
            It is modeled after the IP-MIB IpIfStatsTable described in 
            RFC 4293; however, all counters are 64 bit.
            Discontinuities in the value of these counters can occur at 
            re-initialization of the management system, and at other 
            times as indicated by the value of the DiscontinuityTime 
            attribute in this table."
    ::= { docsRphyRpdIpMibObjects 5 }

docsRphyRpdIpIfStatsEntry OBJECT-TYPE
    SYNTAX     DocsRphyRpdIpIfStatsEntry
    MAX-ACCESS not-accessible
    STATUS     current
    DESCRIPTION
           "An interface statistics entry containing objects for a
            particular interface and version of IP."
    INDEX { docsRphyRpdDevInfoUniqueId,
            docsRphyRpdIpIfStatsIPVersion, 
            docsRphyRpdIfEnetPortIndex }
    ::= { docsRphyRpdIpIfStatsTable 1 }

DocsRphyRpdIpIfStatsEntry ::= SEQUENCE {
        docsRphyRpdIpIfStatsIPVersion           InetVersion,
        docsRphyRpdIpIfStatsInReceives          Counter64,
        docsRphyRpdIpIfStatsInOctets            Counter64,
        docsRphyRpdIpIfStatsInHdrErrors         Counter64,
        docsRphyRpdIpIfStatsInNoRoutes          Counter64,
        docsRphyRpdIpIfStatsInAddrErrors        Counter64,
        docsRphyRpdIpIfStatsInUnknownProtos     Counter64,
        docsRphyRpdIpIfStatsInTruncatedPkts     Counter64,
        docsRphyRpdIpIfStatsInDiscards          Counter64,      
        docsRphyRpdIpIfStatsInDelivers          Counter64,        
        docsRphyRpdIpIfStatsOutRequests         Counter64,      
        docsRphyRpdIpIfStatsOutDiscards         Counter64,
        docsRphyRpdIpIfStatsOutTransmits        Counter64,  
        docsRphyRpdIpIfStatsOutOctets           Counter64,    
        docsRphyRpdIpIfStatsInMcastPkts         Counter64,   
        docsRphyRpdIpIfStatsInMcastOctets       Counter64,  
        docsRphyRpdIpIfStatsOutMcastPkts        Counter64,
        docsRphyRpdIpIfStatsOutMcastOctets      Counter64,
        docsRphyRpdIpIfStatsDiscontinuityTime   TimeStamp,
        docsRphyRpdIpIfStatsRefreshRate         Unsigned32
    }

docsRphyRpdIpIfStatsIPVersion OBJECT-TYPE
    SYNTAX     InetVersion
    MAX-ACCESS not-accessible
    STATUS     current
    DESCRIPTION
           "This key attribute reports the IP version of this entry."
    ::= { docsRphyRpdIpIfStatsEntry 1 }

docsRphyRpdIpIfStatsInReceives OBJECT-TYPE
    SYNTAX     Counter64
    MAX-ACCESS read-only
    STATUS     current
    DESCRIPTION
           "The total number of input IP datagrams received, including
            those received in error."
    ::= { docsRphyRpdIpIfStatsEntry 2 }

docsRphyRpdIpIfStatsInOctets OBJECT-TYPE
    SYNTAX     Counter64
    MAX-ACCESS read-only
    STATUS     current
    DESCRIPTION
           "The total number of octets received in input IP datagrams,
            including those received in error."
    ::= { docsRphyRpdIpIfStatsEntry 3 }

docsRphyRpdIpIfStatsInHdrErrors OBJECT-TYPE
    SYNTAX     Counter64
    MAX-ACCESS read-only
    STATUS     current
    DESCRIPTION
           "The number of input IP datagrams discarded due to errors in
            their IP headers, including version number mismatch, other
            format errors, hop count exceeded, errors discovered in
            processing their IP options, etc."
    ::= { docsRphyRpdIpIfStatsEntry 4 }

docsRphyRpdIpIfStatsInNoRoutes OBJECT-TYPE
    SYNTAX     Counter64
    MAX-ACCESS read-only
    STATUS     current
    DESCRIPTION
           "The number of input IP datagrams discarded because no route
            could be found to transmit them to their destination."
    ::= { docsRphyRpdIpIfStatsEntry 5 }

docsRphyRpdIpIfStatsInAddrErrors OBJECT-TYPE
    SYNTAX     Counter64
    MAX-ACCESS read-only
    STATUS     current
    DESCRIPTION
           "The number of input IP datagrams discarded because the IP
            address in their IP header's destination field was not a
            valid address to be received at this entity.  This count
            includes invalid addresses (e.g., ::0).  For entities that
            are not IP routers and therefore do not forward datagrams,
            this counter includes datagrams discarded because the
            destination address was not a local address."
    ::= { docsRphyRpdIpIfStatsEntry 6 }

docsRphyRpdIpIfStatsInUnknownProtos OBJECT-TYPE
    SYNTAX     Counter64
    MAX-ACCESS read-only
    STATUS     current
    DESCRIPTION
           "The number of locally-addressed IP datagrams received
            successfully but discarded because of an unknown or
            unsupported protocol.

            When tracking interface statistics, the counter of the
            interface to which these datagrams were addressed is
            incremented.  This interface might not be the same as the
            input interface for some of the datagrams."
    ::= { docsRphyRpdIpIfStatsEntry 7 }

docsRphyRpdIpIfStatsInTruncatedPkts OBJECT-TYPE
    SYNTAX     Counter64
    MAX-ACCESS read-only
    STATUS     current
    DESCRIPTION
           "The number of input IP datagrams discarded because the
            datagram frame didn't carry enough data."
    ::= { docsRphyRpdIpIfStatsEntry 8 }

docsRphyRpdIpIfStatsInDiscards OBJECT-TYPE
    SYNTAX     Counter64
    MAX-ACCESS read-only
    STATUS     current
    DESCRIPTION
           "The number of input IP datagrams for which no problems were
            encountered to prevent their continued processing, but
            were discarded (e.g., for lack of buffer space).  Note that
            this counter does not include any datagrams discarded while
            awaiting re-assembly."
    ::= { docsRphyRpdIpIfStatsEntry 9 }

docsRphyRpdIpIfStatsInDelivers OBJECT-TYPE
    SYNTAX     Counter64
    MAX-ACCESS read-only
    STATUS     current
    DESCRIPTION
           "The total number of datagrams successfully delivered to IP
            user-protocols (including ICMP)."
    ::= { docsRphyRpdIpIfStatsEntry 10 }

docsRphyRpdIpIfStatsOutRequests OBJECT-TYPE
    SYNTAX     Counter64
    MAX-ACCESS read-only
    STATUS     current
    DESCRIPTION
           "The total number of IP datagrams that local IP user-
            protocols (including ICMP) supplied to IP in requests for
            transmission."
    ::= { docsRphyRpdIpIfStatsEntry 11 }

docsRphyRpdIpIfStatsOutDiscards OBJECT-TYPE
    SYNTAX     Counter64
    MAX-ACCESS read-only
    STATUS     current
    DESCRIPTION
           "The number of output IP datagrams for which no problem was
            encountered to prevent their transmission to their
            destination, but were discarded (e.g., for lack of
            buffer space).  Note that this counter would include
            datagrams counted in docsRphyRpdIpIfStatsOutForwDatagrams if any such
            datagrams met this (discretionary) discard criterion."
    ::= { docsRphyRpdIpIfStatsEntry 12 }

docsRphyRpdIpIfStatsOutTransmits OBJECT-TYPE
    SYNTAX     Counter64
    MAX-ACCESS read-only
    STATUS     current
    DESCRIPTION
           "The total number of IP datagrams that this entity supplied
            to the lower layers for transmission."
    ::= { docsRphyRpdIpIfStatsEntry 13 }

docsRphyRpdIpIfStatsOutOctets OBJECT-TYPE
    SYNTAX     Counter64
    MAX-ACCESS read-only
    STATUS     current
    DESCRIPTION
           "The total number of octets in IP datagrams delivered to the
            lower layers for transmission."
    ::= { docsRphyRpdIpIfStatsEntry 14 }

docsRphyRpdIpIfStatsInMcastPkts OBJECT-TYPE
    SYNTAX     Counter64
    MAX-ACCESS read-only
    STATUS     current
    DESCRIPTION
           "The number of IP multicast datagrams received."
    ::= { docsRphyRpdIpIfStatsEntry 15 }

docsRphyRpdIpIfStatsInMcastOctets OBJECT-TYPE
    SYNTAX     Counter64
    MAX-ACCESS read-only
    STATUS     current
    DESCRIPTION
           "The total number of octets received in IP multicast
            datagrams."
    ::= { docsRphyRpdIpIfStatsEntry 16 }

docsRphyRpdIpIfStatsOutMcastPkts OBJECT-TYPE
    SYNTAX     Counter64
    MAX-ACCESS read-only
    STATUS     current
    DESCRIPTION
           "The number of IP multicast datagrams transmitted."
    ::= { docsRphyRpdIpIfStatsEntry 17 }

docsRphyRpdIpIfStatsOutMcastOctets OBJECT-TYPE
    SYNTAX     Counter64
    MAX-ACCESS read-only
    STATUS     current
    DESCRIPTION
           "The total number of octets transmitted in IP multicast
            datagrams."
    ::= { docsRphyRpdIpIfStatsEntry 18 }

docsRphyRpdIpIfStatsDiscontinuityTime OBJECT-TYPE
    SYNTAX     TimeStamp
    MAX-ACCESS read-only
    STATUS     current
    DESCRIPTION
           "The value of sysUpTime on the most recent occasion at which
            any one or more of this entry's counters suffered a
            discontinuity."
    ::= { docsRphyRpdIpIfStatsEntry 19 }

docsRphyRpdIpIfStatsRefreshRate OBJECT-TYPE
    SYNTAX     Unsigned32
    UNITS "milli-seconds"
    MAX-ACCESS read-only
    STATUS     current
    DESCRIPTION
           "The minimum reasonable polling interval for this entry.
            This object provides an indication of the minimum amount of
            time required to update the counters in this entry."
    ::= { docsRphyRpdIpIfStatsEntry 20 }


-- ---------------------------------------------------------------------
-- Internet Address Table
-- ---------------------------------------------------------------------

docsRphyRpdIpAddressTable OBJECT-TYPE
    SYNTAX     SEQUENCE OF DocsRphyRpdIpAddressEntry
    MAX-ACCESS not-accessible
    STATUS     current
    DESCRIPTION
           "This table contains addressing information relevant to the
            entity's interfaces.

            This table does not contain multicast address information.

            Note well: When including IPv6 link-local addresses in this
            table, the entry must use an InetAddressType of 'docsRphyRpdIpv6z' in
            order to differentiate between the possible interfaces."
    REFERENCE "RFC 4293 ipAddressTable"
    ::= { docsRphyRpdIpMibObjects 6 }

docsRphyRpdIpAddressEntry OBJECT-TYPE
    SYNTAX     DocsRphyRpdIpAddressEntry
    MAX-ACCESS not-accessible
    STATUS     current
    DESCRIPTION
           "An address mapping for a particular interface."
    INDEX { docsRphyRpdDevInfoUniqueId,
            docsRphyRpdIpAddressAddrType, 
            docsRphyRpdIpAddressAddr }
    ::= { docsRphyRpdIpAddressTable 1 }

DocsRphyRpdIpAddressEntry ::= SEQUENCE {
        docsRphyRpdIpAddressAddrType       InetAddressType,
        docsRphyRpdIpAddressAddr           InetAddress,
        docsRphyRpdIpAddressEnetPortIndex  Unsigned32,
        docsRphyRpdIpAddressType           INTEGER,
        docsRphyRpdIpAddressPrefixLen      InetAddressPrefixLength,
        docsRphyRpdIpAddressOrigin         IpAddressOriginTC,
        docsRphyRpdIpAddressStatus         IpAddressStatusTC,
        docsRphyRpdIpAddressCreated        TimeStamp,
        docsRphyRpdIpAddressLastChanged    TimeStamp
    }

docsRphyRpdIpAddressAddrType OBJECT-TYPE
    SYNTAX     InetAddressType
    MAX-ACCESS not-accessible
    STATUS     current
    DESCRIPTION
           "The address type of docsRphyRpdIpAddressAddr."
    ::= { docsRphyRpdIpAddressEntry 1 }

docsRphyRpdIpAddressAddr OBJECT-TYPE
    SYNTAX     InetAddress
    MAX-ACCESS not-accessible
    STATUS     current
    DESCRIPTION
           "The IP address to which this entry's addressing information
            pertains.  The address type of this object is specified in
            AddrType.

            Implementors need to be aware that if the size of
            Addr exceeds 116 octets, then OIDS of instances of
            columns in this row will have more than 128 sub-identifiers
            and cannot be accessed using SNMPv1, SNMPv2c, or SNMPv3."
    ::= { docsRphyRpdIpAddressEntry 2 }

docsRphyRpdIpAddressEnetPortIndex OBJECT-TYPE
    SYNTAX     Unsigned32 (0..255)
    MAX-ACCESS read-only
    STATUS     current
    DESCRIPTION
           "This attribute reports a unique index for this 
            Ethernet port interface."
    ::= { docsRphyRpdIpAddressEntry 3 }

docsRphyRpdIpAddressType OBJECT-TYPE
    SYNTAX     INTEGER {
                 unicast(1),
                 anycast(2),
                 broadcast(3)
    }
    MAX-ACCESS read-only
    STATUS     current
    DESCRIPTION
           "The type of address.  broadcast(3) is not a valid value for
            IPv6 addresses (RFC 3513)."
    ::= { docsRphyRpdIpAddressEntry 4 }

docsRphyRpdIpAddressPrefixLen OBJECT-TYPE
    SYNTAX     InetAddressPrefixLength
    MAX-ACCESS read-only
    STATUS     current
    DESCRIPTION
           "This attribute reports the prefix length associated 
            with this address."
    ::= { docsRphyRpdIpAddressEntry 5 }

docsRphyRpdIpAddressOrigin OBJECT-TYPE
    SYNTAX     IpAddressOriginTC
    MAX-ACCESS read-only
    STATUS     current
    DESCRIPTION
           "The origin of the address."
    ::= { docsRphyRpdIpAddressEntry 6 }

docsRphyRpdIpAddressStatus OBJECT-TYPE
    SYNTAX     IpAddressStatusTC
    MAX-ACCESS read-only
    STATUS     current
    DESCRIPTION
           "The status of the address, describing if the address can be
            used for communication.

            In the absence of other information, an IPv4 address is
            always preferred(1)."
    ::= { docsRphyRpdIpAddressEntry 7 }

docsRphyRpdIpAddressCreated OBJECT-TYPE
    SYNTAX     TimeStamp
    MAX-ACCESS read-only
    STATUS     current
    DESCRIPTION
           "The value of sysUpTime at the time this entry was created.
            If this entry was created prior to the last re-
            initialization of the local network management subsystem,
            then this object contains a zero value."
    ::= { docsRphyRpdIpAddressEntry 8 }

docsRphyRpdIpAddressLastChanged OBJECT-TYPE
    SYNTAX     TimeStamp
    MAX-ACCESS read-only
    STATUS     current
    DESCRIPTION
           "The value of sysUpTime at the time this entry was last
            updated.  If this entry was updated prior to the last re-
            initialization of the local network management subsystem,
            then this object contains a zero value."
    ::= { docsRphyRpdIpAddressEntry 9 }
    

-- ---------------------------------------------------------------------
-- Internet Address Translation Table
-- ---------------------------------------------------------------------

docsRphyRpdIpNetToPhysicalTable OBJECT-TYPE
    SYNTAX     SEQUENCE OF DocsRphyRpdIpNetToPhysicalEntry
    MAX-ACCESS not-accessible
    STATUS     current
    DESCRIPTION
           "The IP Address Translation table used for mapping from IP
            addresses to physical addresses.

            The Address Translation tables contain the IP address to
            'physical' address equivalences.  Some interfaces do not use
            translation tables for determining address equivalences
            (e.g., DDN-X.25 has an algorithmic method); if all
            interfaces are of this type, then the Address Translation
            table is empty, i.e., has zero entries.

            While many protocols may be used to populate this table, ARP
            and Neighbor Discovery are the most likely
            options."
    REFERENCE "RFC 4293 ipNetToPhysicalTable"
    ::= { docsRphyRpdIpMibObjects 7 }

docsRphyRpdIpNetToPhysicalEntry OBJECT-TYPE
    SYNTAX     DocsRphyRpdIpNetToPhysicalEntry
    MAX-ACCESS not-accessible
    STATUS     current
    DESCRIPTION
           "Each entry contains one IP address to `physical' address
            equivalence."
    INDEX       { docsRphyRpdDevInfoUniqueId,
                  docsRphyRpdIfEnetPortIndex,
                  docsRphyRpdIpNetToPhysicalNetAddressType,
                  docsRphyRpdIpNetToPhysicalNetAddress }
    ::= { docsRphyRpdIpNetToPhysicalTable 1 }

DocsRphyRpdIpNetToPhysicalEntry ::= SEQUENCE {
        docsRphyRpdIpNetToPhysicalNetAddressType  InetAddressType,
        docsRphyRpdIpNetToPhysicalNetAddress      InetAddress,
        docsRphyRpdIpNetToPhysicalPhysAddress     PhysAddress,
        docsRphyRpdIpNetToPhysicalLastUpdated     TimeStamp,
        docsRphyRpdIpNetToPhysicalType            INTEGER,
        docsRphyRpdIpNetToPhysicalState           INTEGER
    }

docsRphyRpdIpNetToPhysicalNetAddressType OBJECT-TYPE
    SYNTAX     InetAddressType
    MAX-ACCESS not-accessible
    STATUS     current
    DESCRIPTION
           "The type of NetAddress."
    ::= { docsRphyRpdIpNetToPhysicalEntry 1 }

docsRphyRpdIpNetToPhysicalNetAddress OBJECT-TYPE
    SYNTAX     InetAddress
    MAX-ACCESS not-accessible
    STATUS     current
    DESCRIPTION
           "The IP Address corresponding to the media-dependent
            'physical' address.  The address type of this object is
            specified in AddressType.

            Implementors need to be aware that if the size of
            NetAddress exceeds 115 octets, then OIDS of
            instances of columns in this row will have more than 128
            sub-identifiers and cannot be accessed using SNMPv1,
            SNMPv2c, or SNMPv3."
    ::= { docsRphyRpdIpNetToPhysicalEntry 2 }

docsRphyRpdIpNetToPhysicalPhysAddress OBJECT-TYPE
    SYNTAX     PhysAddress (SIZE(0..65535))
    MAX-ACCESS read-only
    STATUS     current
    DESCRIPTION
           "The media-dependent 'physical' address."
    ::= { docsRphyRpdIpNetToPhysicalEntry 3 }

docsRphyRpdIpNetToPhysicalLastUpdated OBJECT-TYPE
    SYNTAX     TimeStamp
    MAX-ACCESS read-only
    STATUS     current
    DESCRIPTION
           "This attribute reports the value of RpdSysUpTime at the time
            this entry was last updated.  If this entry was updated 
            prior to the last re-initialization of the local network 
            management subsystem, then this attribute contains a 
            zero value."
    ::= { docsRphyRpdIpNetToPhysicalEntry 4 }

docsRphyRpdIpNetToPhysicalType OBJECT-TYPE
    SYNTAX     INTEGER {
                other(1),        -- none of the following
                invalid(2),      -- an invalidated mapping
                dynamic(3),
                static(4),
                local(5)         -- local interface
            }
    MAX-ACCESS read-only
    STATUS     current
    DESCRIPTION
           "The type of mapping. It is an
            implementation-specific matter as to whether the agent
            removes an invalidated entry from the table.  Accordingly,
            management stations must be prepared to receive tabular
            information from agents that corresponds to entries not
            currently in use.  Proper interpretation of such entries
            requires examination of the relevant Type
            attribute.

            The 'dynamic(3)' type indicates that the IP address to
            physical addresses mapping has been dynamically resolved
            using e.g., IPv4 ARP or the IPv6 Neighbor Discovery
            protocol.

            The 'static(4)' type indicates that the mapping has been
            statically configured.  Both of these refer to entries that
            provide mappings for other entities addresses.

            The 'local(5)' type indicates that the mapping is provided
            for an entity's own interface address."
    ::= { docsRphyRpdIpNetToPhysicalEntry 5 }

docsRphyRpdIpNetToPhysicalState OBJECT-TYPE
    SYNTAX     INTEGER {
                     reachable(1), -- confirmed reachability

                     stale(2),     -- unconfirmed reachability

                     delay(3),     -- waiting for reachability
                                   -- confirmation before entering
                                   -- the probe state

                     probe(4),     -- actively probing

                     invalid(5),   -- an invalidated mapping

                     unknown(6),   -- state can not be determined
                                   -- for some reason.

                     incomplete(7) -- address resolution is being
                                   -- performed.
                    }
    MAX-ACCESS read-only
    STATUS     current
    DESCRIPTION
           "The Neighbor Unreachability Detection state for the
            interface when the address mapping in this entry is used.
            If Neighbor Unreachability Detection is not in use (e.g. for
            IPv4), this object is always unknown(6)."
    ::= { docsRphyRpdIpNetToPhysicalEntry 6 }

-- ---------------------------------------------------------------------
-- Default Router Table
-- ---------------------------------------------------------------------

docsRphyRpdIpDefaultRouterTable OBJECT-TYPE
    SYNTAX     SEQUENCE OF DocsRphyRpdIpDefaultRouterEntry
    MAX-ACCESS not-accessible
    STATUS     current
    DESCRIPTION
           "The table used to describe the default routers known to the
            RPD."
    REFERENCE "RFC 4293 ipDefaultRouterTable"
    ::= { docsRphyRpdIpMibObjects 8 }

docsRphyRpdIpDefaultRouterEntry OBJECT-TYPE
    SYNTAX     DocsRphyRpdIpDefaultRouterEntry
    MAX-ACCESS not-accessible
    STATUS     current
    DESCRIPTION
           "Each entry contains information about a default router known
            to the RPD."
    INDEX { docsRphyRpdDevInfoUniqueId,
            docsRphyRpdIpDefaultRouterAddressType, 
            docsRphyRpdIpDefaultRouterAddress,
            docsRphyRpdIfEnetPortIndex }
    ::= { docsRphyRpdIpDefaultRouterTable 1 }

DocsRphyRpdIpDefaultRouterEntry ::= SEQUENCE {
        docsRphyRpdIpDefaultRouterAddressType  InetAddressType,
        docsRphyRpdIpDefaultRouterAddress      InetAddress,
        docsRphyRpdIpDefaultRouterLifetime     Unsigned32,
        docsRphyRpdIpDefaultRouterPreference   INTEGER
    }

docsRphyRpdIpDefaultRouterAddressType OBJECT-TYPE
    SYNTAX     InetAddressType
    MAX-ACCESS not-accessible
    STATUS     current
    DESCRIPTION
           "This key attribute reports the type of IP address in the 
            Address attribute."
    ::= { docsRphyRpdIpDefaultRouterEntry 1 }

docsRphyRpdIpDefaultRouterAddress OBJECT-TYPE
    SYNTAX     InetAddress
    MAX-ACCESS not-accessible
    STATUS     current
    DESCRIPTION
           "The IP address of the default router represented by this
            row.  The address type of this object is specified in
            AddressType.

            Implementers need to be aware that if the size of
            Address exceeds 115 octets, then OIDS of
            instances of columns in this row will have more than 128
            sub-identifiers and cannot be accessed using SNMPv1,
            SNMPv2c, or SNMPv3."
    ::= { docsRphyRpdIpDefaultRouterEntry 2 }

docsRphyRpdIpDefaultRouterLifetime OBJECT-TYPE
    SYNTAX     Unsigned32 (0..65535)
    UNITS      "seconds"
    MAX-ACCESS read-only
    STATUS     current
    DESCRIPTION
           "The remaining length of time, in seconds, that this router
            will continue to be useful as a default router.  A value of
            zero indicates that it is no longer useful as a default
            router.  It is left to the implementer of the MIB as to
            whether a router with a lifetime of zero is removed from the
            list.

            For IPv6, this value should be extracted from the router
            advertisement messages."
    ::= { docsRphyRpdIpDefaultRouterEntry 3 }

docsRphyRpdIpDefaultRouterPreference OBJECT-TYPE
    SYNTAX     INTEGER {
                     reserved(-2),
                     low(-1),
                     medium(0),
                     high(1)
                    }
    MAX-ACCESS read-only
    STATUS     current
    DESCRIPTION
           "An indication of preference given to this router as a
            default router as described in the Default Router
            Preferences document.  Treating the value as a
            2 bit signed integer allows for simple arithmetic
            comparisons.

            For IPv4 routers or IPv6 routers that are not using the
            updated router advertisement format, this object is set to
            medium (0)."
    ::= { docsRphyRpdIpDefaultRouterEntry 4 }


-- ---------------------------------------------------------------------
-- ICMP per-version, per-message type ICMP counters Table
-- ---------------------------------------------------------------------

docsRphyRpdIpIcmpMsgStatsTable OBJECT-TYPE
    SYNTAX     SEQUENCE OF DocsRphyRpdIpIcmpMsgStatsEntry
    MAX-ACCESS not-accessible
    STATUS     current
    DESCRIPTION
           "The table of system-wide per-version, per-message type ICMP
            counters."
    REFERENCE "RFC 4293 icmpMsgStatsTable"
    ::= { docsRphyRpdIpIcmpMibObjects 1 }

docsRphyRpdIpIcmpMsgStatsEntry OBJECT-TYPE
    SYNTAX     DocsRphyRpdIpIcmpMsgStatsEntry
    MAX-ACCESS not-accessible
    STATUS     current
    DESCRIPTION
           "A conceptual row in the docsRphyRpdIpIcmpMsgStatsTable.

            The system should track each ICMP type value, even if that
            ICMP type is not supported by the system.  However, a
            given row need not be instantiated unless a message of that
            type has been processed, i.e., the row for
            Type=X MAY be instantiated before but is required to be
            instantiated after the first message with Type=X is
            received or transmitted.  After receiving or transmitting
            any succeeding messages with Type=X, the relevant counter
            must be incremented."
    INDEX { docsRphyRpdDevInfoUniqueId,
            docsRphyRpdIpIcmpMsgStatsIPVersion, 
            docsRphyRpdIpIcmpMsgStatsType }
    ::= { docsRphyRpdIpIcmpMsgStatsTable 1 }

DocsRphyRpdIpIcmpMsgStatsEntry ::= SEQUENCE {
        docsRphyRpdIpIcmpMsgStatsIPVersion  InetVersion,
        docsRphyRpdIpIcmpMsgStatsType       Integer32,
        docsRphyRpdIpIcmpMsgStatsInPkts     Counter64,
        docsRphyRpdIpIcmpMsgStatsOutPkts    Counter64
    }

docsRphyRpdIpIcmpMsgStatsIPVersion OBJECT-TYPE
    SYNTAX     InetVersion
    MAX-ACCESS not-accessible
    STATUS     current
    DESCRIPTION
           "The IP version of the statistics. Statistics are provided for 
            each IP version supported."
    ::= { docsRphyRpdIpIcmpMsgStatsEntry 1 }

docsRphyRpdIpIcmpMsgStatsType OBJECT-TYPE
    SYNTAX     Integer32 (0..255)
    MAX-ACCESS not-accessible
    STATUS     current
    DESCRIPTION
           "The ICMP type field of the message type being counted by
            this row.

            Note that ICMP message types are scoped by the address type
            in use."
    ::= { docsRphyRpdIpIcmpMsgStatsEntry 2 }

docsRphyRpdIpIcmpMsgStatsInPkts OBJECT-TYPE
    SYNTAX     Counter64
    MAX-ACCESS read-only
    STATUS     current
    DESCRIPTION
           "The number of input packets for this AF and type."
    ::= { docsRphyRpdIpIcmpMsgStatsEntry 3 }

docsRphyRpdIpIcmpMsgStatsOutPkts OBJECT-TYPE
    SYNTAX     Counter64
    MAX-ACCESS read-only
    STATUS     current
    DESCRIPTION
           "The number of output packets for this AF and type."
    ::= { docsRphyRpdIpIcmpMsgStatsEntry 4 }

-- ---------------------------------------------------------------------
-- CCAP Core Group Objects
-- ---------------------------------------------------------------------
                 
-- ---------------------------------------------------------
-- Core L2TP Session Info Table 
-- ---------------------------------------------------------
                 
docsRphyCcapL2tpSessionInfoTable OBJECT-TYPE
    SYNTAX      SEQUENCE OF DocsRphyCcapL2tpSessionInfoEntry
    MAX-ACCESS  not-accessible
    STATUS      current
    DESCRIPTION
            "This table provides details for every session that 
             terminates at the CCAP Core from the CCAP Core's point 
             of view. There will be multiple sessions for each RPD 
             with which the CCAP Core is associated."
    ::= { docsRphyCcapMibObjects 1 }

docsRphyCcapL2tpSessionInfoEntry OBJECT-TYPE
    SYNTAX      DocsRphyCcapL2tpSessionInfoEntry
    MAX-ACCESS  not-accessible
    STATUS      current
    DESCRIPTION
            "The conceptual row of docsRphyCcapL2tpSessionInfoTable.
        
             A row entry is created for every session the CCAP-Core 
             terminates."
    INDEX { docsRphyCcapL2tpSessionInfoSessionIpAddrType,
            docsRphyCcapL2tpSessionInfoCcapLcceIpAddr,
            docsRphyCcapL2tpSessionInfoRpdLcceIpAddr,
            docsRphyCcapL2tpSessionInfoDirection,
            docsRphyCcapL2tpSessionInfoL2tpSessionId }
    ::= { docsRphyCcapL2tpSessionInfoTable 1 }

DocsRphyCcapL2tpSessionInfoEntry ::= SEQUENCE
    {
    docsRphyCcapL2tpSessionInfoSessionIpAddrType     InetAddressType,
    docsRphyCcapL2tpSessionInfoCcapLcceIpAddr        InetAddress,
    docsRphyCcapL2tpSessionInfoRpdLcceIpAddr         InetAddress,
    docsRphyCcapL2tpSessionInfoDirection             INTEGER,
    docsRphyCcapL2tpSessionInfoL2tpSessionId         Unsigned32,
    docsRphyCcapL2tpSessionInfoCoreId                MacAddress,
    docsRphyCcapL2tpSessionInfoConnCtrlID            Unsigned32,
    docsRphyCcapL2tpSessionInfoUdpPort               InetPortNumber,
    docsRphyCcapL2tpSessionInfoDescr                 SnmpAdminString,
    docsRphyCcapL2tpSessionInfoSessionType           INTEGER,
    docsRphyCcapL2tpSessionInfoSessionSubType        INTEGER,
    docsRphyCcapL2tpSessionInfoMaxPayload            Unsigned32,
    docsRphyCcapL2tpSessionInfoPathPayload           Unsigned32,
    docsRphyCcapL2tpSessionInfoRpdIfMtu              Unsigned32,
    docsRphyCcapL2tpSessionInfoCoreIfMtu             Unsigned32,
    docsRphyCcapL2tpSessionInfoIncludeDOCSISMsgs     TruthValue,
    docsRphyCcapL2tpSessionInfoErrorCode             INTEGER,
    docsRphyCcapL2tpSessionInfoCreationTime          TimeStamp,
    docsRphyCcapL2tpSessionInfoOperStatus            OperStatusType,
    docsRphyCcapL2tpSessionInfoLocalStatus           BITS,
    docsRphyCcapL2tpSessionInfoLastChange            TimeStamp
    }

docsRphyCcapL2tpSessionInfoSessionIpAddrType OBJECT-TYPE
    SYNTAX      InetAddressType
    MAX-ACCESS  not-accessible
    STATUS      current
    DESCRIPTION 
            "This key attribute indicates whether the IP address
             provided in the CcapLcceIpAddress and RpdLcceIpAddr 
             attributes are IPv4 or IPv6."
    ::= { docsRphyCcapL2tpSessionInfoEntry 1 }

docsRphyCcapL2tpSessionInfoCcapLcceIpAddr OBJECT-TYPE
    SYNTAX      InetAddress
    MAX-ACCESS  not-accessible
    STATUS      current
    DESCRIPTION 
            "This key attribute provides the LCCE IP address on the
             CCAP Core of the session detailed in the instance. As
             reported by the RPD for a static multicast session, 
             this attribute is zero for an any source multicast and 
             the source IP for Source Specific Multicast (SSM)."
    ::= { docsRphyCcapL2tpSessionInfoEntry 2 }

docsRphyCcapL2tpSessionInfoRpdLcceIpAddr OBJECT-TYPE
    SYNTAX      InetAddress
    MAX-ACCESS  not-accessible
    STATUS      current
    DESCRIPTION 
            "This key attribute reports the remote-side
             RPD LCCE IP address of the session detailed
             in the instance."
    ::= { docsRphyCcapL2tpSessionInfoEntry 3 }
    
docsRphyCcapL2tpSessionInfoDirection OBJECT-TYPE
    SYNTAX      INTEGER {
                           forward(0),
                           return(1)
                        }
    MAX-ACCESS  not-accessible
    STATUS      current
    DESCRIPTION 
            "This key attribute reports the direction of the session detailed in the instance.  
             Valid values include:
             'forward' - Forward (downstream) direction toward the RPD.
             'return' -  Return (upstream) direction toward the CCAP Core."
    ::= { docsRphyCcapL2tpSessionInfoEntry 4 }

docsRphyCcapL2tpSessionInfoL2tpSessionId OBJECT-TYPE
    SYNTAX      Unsigned32
    MAX-ACCESS  not-accessible
    STATUS      current
    DESCRIPTION 
            "This key attribute reports the value of the 
            L2TPv3 session ID transmitted or received on 
            the session. "
    ::= { docsRphyCcapL2tpSessionInfoEntry 5 }

    
docsRphyCcapL2tpSessionInfoCoreId OBJECT-TYPE
    SYNTAX      MacAddress
    MAX-ACCESS  read-only
    STATUS      current
    DESCRIPTION 
            "This attribute provides the MAC address of the CCAP Core 
             with which this session terminates. The CCAP Core sends its
             MAC address to the RPD periodically via the DOCSIS SYNC MAC
             Message in the Source Address field."
    ::= { docsRphyCcapL2tpSessionInfoEntry 6 }
    
docsRphyCcapL2tpSessionInfoConnCtrlID OBJECT-TYPE
    SYNTAX      Unsigned32
    MAX-ACCESS  read-only
    STATUS      current
    DESCRIPTION 
            "This attribute indicates the control connection
             identifier (CCID) for this session."
    ::= { docsRphyCcapL2tpSessionInfoEntry 7 }
    
docsRphyCcapL2tpSessionInfoUdpPort OBJECT-TYPE
    SYNTAX      InetPortNumber
    MAX-ACCESS  read-only
    STATUS      current
    DESCRIPTION 
            "This attribute provides the UDP Port reported by the 
             CCAP Core when the DEPI session uses L2TPv3 Header Over
             UDP. This attribute reports a value of 0 when the session 
             is running with the L2TPv3 Session IP Header. 
             This port number is negotiated between the CCAP Core and 
             the RPD according to the L2TPv3 RFC."
    ::= { docsRphyCcapL2tpSessionInfoEntry 8 }
    
docsRphyCcapL2tpSessionInfoDescr OBJECT-TYPE
    SYNTAX      SnmpAdminString
    MAX-ACCESS  read-only
    STATUS      current
    DESCRIPTION 
            "This attribute provides an ASCII string constructed with
             the form:
             
             RemoteEndId=(pp:mmm:ccc), ... 
                  { repeated for multiple endpoints } 

             where
             pp is the 0-based port num signaled in the RemoteEndId AVP
             mmm is the channel-type enum value from the RemoteEndId AVP 
             ccc is the channel number from the RemoteEndId AVP."
    ::= { docsRphyCcapL2tpSessionInfoEntry 9 }
    
docsRphyCcapL2tpSessionInfoSessionType OBJECT-TYPE
    SYNTAX      INTEGER {
                           psp(1),
                           mpt(2)
                        }
    MAX-ACCESS  read-only
    STATUS      current
    DESCRIPTION 
            "This attribute specifies whether the session is an MPT 
             session or PSP session."
    ::= { docsRphyCcapL2tpSessionInfoEntry 10 }
    
docsRphyCcapL2tpSessionInfoSessionSubType OBJECT-TYPE
    SYNTAX      INTEGER {
                           mptLegacy(1),
                           pspLegacy(2),
                           mcm(3),
                           pspDepiMultichannel(4),
                           pspUepiScQam(5),
                           pspUepiOfdma(6),
                           pspBwReqScQam(7),
                           pspBwReqOfdma(8),
                           pspProbe(9),
                           pspRngReqScQam(10),
                           pspRngReqOfdma(11),
                           pspMapScQam(12),
                           pspMapOfdma(13),
                           pspSpecman(14),
                           pspPnm(15),
                           psp551Fwd(16),
                           psp551Ret(17),
                           psp552Fwd(18),
                           psp552Ret(19),
                           pspNdf(20),
                           pspNdr(21)
                        }
    MAX-ACCESS  read-only
    STATUS      current
    DESCRIPTION 
            "This attribute specifies the type of DEPI MPT or DEPI 
             PSP session."
    ::= { docsRphyCcapL2tpSessionInfoEntry 11 }

docsRphyCcapL2tpSessionInfoMaxPayload OBJECT-TYPE
    SYNTAX      Unsigned32
    MAX-ACCESS  read-only
    STATUS      current
    DESCRIPTION 
            "This attribute indicates the maximum MTU negotiated between
             the CCAP Core and the RPD during the session establishment 
             process. The MTU is the layer 3 payload of a layer 2 
             frame."
    REFERENCE
            "DEPI specification, Signaling
             DEPI specification Annex A."
    ::= { docsRphyCcapL2tpSessionInfoEntry 12 }

docsRphyCcapL2tpSessionInfoPathPayload OBJECT-TYPE
    SYNTAX      Unsigned32
    MAX-ACCESS  read-only
    STATUS      current
    DESCRIPTION 
            "This attribute indicates the maximum MTU traversing the CIN
             from CCAP Core to the RPD. This is calculated by the CCAP 
             Core by procedures such as MTU discovery as described in 
             the DEPI specification."
    REFERENCE
            "DEPI specification, Network MTU"
    ::= { docsRphyCcapL2tpSessionInfoEntry 13 }
    
docsRphyCcapL2tpSessionInfoRpdIfMtu OBJECT-TYPE
    SYNTAX      Unsigned32
    MAX-ACCESS  read-only
    STATUS      current
    DESCRIPTION 
            "This attribute provides the RPD's CIN interface MTU and is
             read as the value of the following L2TPV3 AVP transmitted 
             by the RPD during session setup:
             
             DEPI Downstream PW          UEPI Upstream PW
             DEPI Remote MTU AVP (ICRP)  UEPI Remote MTU AVP (ICRP)."
    ::= { docsRphyCcapL2tpSessionInfoEntry 14 }
    
docsRphyCcapL2tpSessionInfoCoreIfMtu OBJECT-TYPE
    SYNTAX      Unsigned32
    MAX-ACCESS  read-only
    STATUS      current
    DESCRIPTION 
            "This attribute provides the CCAP Core's CIN interface MTU
             and is read as the value of the following L2TPv3 AVP as 
             received by the device during session setup:
             
             DEPI Downstream PW          UEPI Upstream PW
             DEPI Local MTU AVP (ICRQ)   UEPI Local MTU AVP (ICRQ)."
    ::= { docsRphyCcapL2tpSessionInfoEntry 15 }

docsRphyCcapL2tpSessionInfoIncludeDOCSISMsgs OBJECT-TYPE
    SYNTAX      TruthValue
    MAX-ACCESS  read-only
    STATUS      current
    DESCRIPTION 
            "This attribute returns true if the CCAP Core includes 
             DOCSIS MAP messages and other MAC Management messages 
             in the interface entry associated with this control 
             entry. The CCAP Core determines whether the interface 
             includes DOCSIS messages as part of the payload."
    ::= { docsRphyCcapL2tpSessionInfoEntry 16 }

docsRphyCcapL2tpSessionInfoErrorCode OBJECT-TYPE
    SYNTAX      INTEGER {
        none(1),
        invalidMACInterfaceValue(2),
        invalidInterfaceValue(3),
        noResourcesForInterfaceIndex(4),
        l2tpv3Error(5),
        ifAdminStatusSetToDown(6)
        }
    MAX-ACCESS  read-only
    STATUS      current
    DESCRIPTION 
            "The error code raised when the session is in an error
            state. 
            'invalidMACInterfaceValue'  
               Indicates wrong assignment of the CCAP Core MAC interface
               ifIndex.
            'invalidInterfaceValue'  
               Indicates wrong assignment of the CCAP Core Downstream 
               interface ifIndex
            'noResourcesForInterfaceIfIndex' 
               Indicates the CCAP Core has no more resources to
               assign a session to this entry.
            'l2tpv3Error'
               An L2TPv3 StopCCN or CDN message was issued 
            'ifAdminStatusSetToDown'
               Indicates the ifAdminStatus was set to down and the
               session was torn down."
    ::= { docsRphyCcapL2tpSessionInfoEntry 17 }

docsRphyCcapL2tpSessionInfoCreationTime OBJECT-TYPE
    SYNTAX      TimeStamp
    MAX-ACCESS  read-only
    STATUS      current
    DESCRIPTION 
            "The attribute contains the sysUptime when the entry was 
             turned active."
    ::= { docsRphyCcapL2tpSessionInfoEntry 18 }
    
docsRphyCcapL2tpSessionInfoOperStatus OBJECT-TYPE
    SYNTAX      OperStatusType
    MAX-ACCESS  read-only
    STATUS      current
    DESCRIPTION 
            "This attribute provides the current status of the 
             pseudowire from the point of view of the specific 
             reporting entity (CCAP-Core). For static psuedowires, 
             the only values that the RPD can report are 'up' and 
             'down'. 
             These values are conveyed to the Core via the 
             RpdCircuitStatus TLV (TLV 59.1.3)." 
    ::= { docsRphyCcapL2tpSessionInfoEntry 19 }

docsRphyCcapL2tpSessionInfoLocalStatus OBJECT-TYPE
    SYNTAX      BITS {
                      other(0),
                      pwNotForwarding(1), 
                      servicePwRxFault(2), 
                      servicePwTxFault(3), 
                      psnPwRxFault(4), 
                      psnPwTxFault(5)
    }
    MAX-ACCESS  read-only
    STATUS      current
    DESCRIPTION 
            "The attribute provides the status of the pseudowire 
             in the local node. If the 'other' bit is set, it indicates
             that an additional vendor-specific status is reported. 
             If none of the bits are set, it indicates no faults are 
             reported."
    ::= { docsRphyCcapL2tpSessionInfoEntry 20 }
    
docsRphyCcapL2tpSessionInfoLastChange OBJECT-TYPE
    SYNTAX      TimeStamp
    MAX-ACCESS  read-only
    STATUS      current
    DESCRIPTION 
            "The attribute provides the value of sysUpTime 
             when the session entered its current OperStatus 
             state from the point of view of the specific 
             reporting entity (CCAP-Core)."
    ::= { docsRphyCcapL2tpSessionInfoEntry 21 }
    
-- ---------------------------------------------------------
-- CCAP Core L2TP Session Flow Table 
-- ---------------------------------------------------------
                 
docsRphyCcapL2tpSessionFlowTable OBJECT-TYPE
    SYNTAX      SEQUENCE OF DocsRphyCcapL2tpSessionFlowEntry
    MAX-ACCESS  not-accessible
    STATUS      current
    DESCRIPTION
            "This table represents a PSP Flow of L2TP session or for 
             those sessions, which do not have PSP Flows, represents 
             entire session. In the latter case the PSP Flow Id by 
             convention is zero."
    ::= { docsRphyCcapMibObjects 2 }

docsRphyCcapL2tpSessionFlowEntry OBJECT-TYPE
    SYNTAX      DocsRphyCcapL2tpSessionFlowEntry
    MAX-ACCESS  not-accessible
    STATUS      current
    DESCRIPTION
            "The conceptual row of docsRphyCcapL2tpSessionFlowTable.
             This is an extension to 
             docsRphyCcapL2tpSessionInfoTable for the CCAP Core."
    INDEX { docsRphyCcapL2tpSessionInfoSessionIpAddrType,
            docsRphyCcapL2tpSessionInfoCcapLcceIpAddr,
            docsRphyCcapL2tpSessionInfoRpdLcceIpAddr,
            docsRphyCcapL2tpSessionInfoDirection,
            docsRphyCcapL2tpSessionInfoL2tpSessionId,
            docsRphyCcapL2tpSessionFlowPspFlowId }
    ::= { docsRphyCcapL2tpSessionFlowTable 1 }

DocsRphyCcapL2tpSessionFlowEntry ::= SEQUENCE
    {
    docsRphyCcapL2tpSessionFlowPspFlowId   Unsigned32,
    docsRphyCcapL2tpSessionFlowPhbId       Unsigned32
    }
    
docsRphyCcapL2tpSessionFlowPspFlowId OBJECT-TYPE
    SYNTAX      Unsigned32 (0..255)
    MAX-ACCESS  not-accessible
    STATUS      current
    DESCRIPTION 
            "This attribute identifies a PSP Flow within the session. 
             For sessions which do not have PSP Flows, this attribute 
             is zero."
	 ::= { docsRphyCcapL2tpSessionFlowEntry 1 }

docsRphyCcapL2tpSessionFlowPhbId OBJECT-TYPE
     SYNTAX  Unsigned32 (0..255)
     MAX-ACCESS  read-only
     STATUS  current
     DESCRIPTION
	     "This attribute reports the Per Hop Behavior Identifier 
	      that equals the 6-bit DSCP with which the CCAP Core 
              transmits downstream L2TPv3 data packets for the flow 
              or which is signaled to the RPD for insertion in upstream
              L2TPv3 data packets transmitted by the RPD."
	 ::= { docsRphyCcapL2tpSessionFlowEntry 2 }
    
-- ---------------------------------------------------------
-- CCAP Core L2TP Session Statistics Table 
-- ---------------------------------------------------------
                 
docsRphyCcapL2tpSessionStatsTable OBJECT-TYPE
    SYNTAX      SEQUENCE OF DocsRphyCcapL2tpSessionStatsEntry
    MAX-ACCESS  not-accessible
    STATUS      current
    DESCRIPTION
            "This table provides statistics for every session that 
             terminates at the CCAP-Core from the CCAP Core's point of 
             view. It also provides statistics about each tunnel 
             session between the RPD and each CCAP Core with which the 
             RPD is associated from the RPD's point of view."
    ::= { docsRphyCcapMibObjects 3 }

docsRphyCcapL2tpSessionStatsEntry OBJECT-TYPE
    SYNTAX      DocsRphyCcapL2tpSessionStatsEntry
    MAX-ACCESS  not-accessible
    STATUS      current
    DESCRIPTION
            "The conceptual row of docsRphyCcapL2tpSessionStatsTable.
             This table is an augmentation of 
             docsRphyCcapL2tpSessionFlowTable."
    AUGMENTS { docsRphyCcapL2tpSessionFlowEntry }
    ::= { docsRphyCcapL2tpSessionStatsTable 1 }

DocsRphyCcapL2tpSessionStatsEntry ::= SEQUENCE
    {
    docsRphyCcapL2tpSessionStatsOutOfSeqPkts   	 Counter32,
    docsRphyCcapL2tpSessionStatsInPkts	     	 Counter64,
    docsRphyCcapL2tpSessionStatsInDiscards	 Counter64,
    docsRphyCcapL2tpSessionStatsOutPkts	     	 Counter64,
    docsRphyCcapL2tpSessionStatsOutErrors	 Counter64
    }
    
docsRphyCcapL2tpSessionStatsOutOfSeqPkts OBJECT-TYPE
    SYNTAX      Counter32
    MAX-ACCESS  read-only
    STATUS      current
    DESCRIPTION 
            "This attribute indicates the count of session packets that
             were received out of sequence from the point of view of the
             reporting entity. It is vendor dependent the re-sequence of 
             packets. Implementations that do not re-sequence packets 
             also increase the value of ifInDiscards for the respective 
             entry."
    ::= { docsRphyCcapL2tpSessionStatsEntry 1 }
    
 docsRphyCcapL2tpSessionStatsInPkts OBJECT-TYPE
    SYNTAX      Counter64
    MAX-ACCESS  read-only
    STATUS      current
    DESCRIPTION 
            "This attribute counts the number of received packets accepted 
            for processing above the L2TPv3 protocol layer. The InPackets 
            attribute count excludes packets dropped by the L2TPv3 protocol 
            layer itself (e.g. OutOfSequencePackets and InDiscards)."
    ::= { docsRphyCcapL2tpSessionStatsEntry 2 } 
    
 docsRphyCcapL2tpSessionStatsInDiscards OBJECT-TYPE
    SYNTAX      Counter64
    MAX-ACCESS  read-only
    STATUS      current
    DESCRIPTION 
            "This attribute counts the number of received packets discarded 
            by the L2TPv3 protocol layer itself, including those discarded 
            because they were out of sequence. The InDiscards attribute 
            count includes packets unable to be forwarded to a higher layer 
            for processing (e.g. unknown L2tpv3 session Id). Interpretation 
            of what discards are counted in this attribute is 
            vendor-specific."
    ::= { docsRphyCcapL2tpSessionStatsEntry 3 } 
    
 docsRphyCcapL2tpSessionStatsOutPkts OBJECT-TYPE
    SYNTAX      Counter64
    MAX-ACCESS  read-only
    STATUS      current
    DESCRIPTION 
            "This attribute counts the number of packets conceptually 
            attempted to be transmitted from above the L2TPv3 protocol layer. 
            The OutPackets attribute counts packets discarded by the L2TPv3 
            protocol layer itself (i.e. as counted by OutErrors)."
    ::= { docsRphyCcapL2tpSessionStatsEntry 4 }    
    
 docsRphyCcapL2tpSessionStatsOutErrors OBJECT-TYPE
    SYNTAX      Counter64
    MAX-ACCESS  read-only
    STATUS      current
    DESCRIPTION 
            "This attribute counts the number of packets attempted to be 
            transmitted from above the L2TPv3 protocol layer that could not 
            be transmitted below the L2TPv3 protocol layer itself. 
            Interpretation of what errors are counted in this attribute is 
            vendor specific."
    ::= { docsRphyCcapL2tpSessionStatsEntry 5 }     
    

-- ---------------------------------------------------------
-- CCAP Core CIN Downstream Latency Table 
-- ---------------------------------------------------------
                 
docsRphyCcapCinDsLatencyTable OBJECT-TYPE
    SYNTAX      SEQUENCE OF DocsRphyCcapCinDsLatencyEntry
    MAX-ACCESS  not-accessible
    STATUS      current
    DESCRIPTION
            "This table provides measurements on the latency on the CIN
             link for the session as measured by the CCAP-Core. These 
             measurements are based on the DEPI latency measurement, 
             specified in the Remote Downstream External PHY Interface
             Specification."
    ::= { docsRphyCcapMibObjects 4 }

docsRphyCcapCinDsLatencyEntry OBJECT-TYPE
    SYNTAX      DocsRphyCcapCinDsLatencyEntry
    MAX-ACCESS  not-accessible
    STATUS      current
    DESCRIPTION
            "The conceptual row of docsRphyCcapCinLatencyTable.
             A row entry is created for every session the CCAP Core 
             terminates. This table is an augmentation of 
             docsRphyCcapL2tpSessionFlowTable for the CCAP Core."
    AUGMENTS { docsRphyCcapL2tpSessionFlowEntry }
    ::= { docsRphyCcapCinDsLatencyTable 1 }

DocsRphyCcapCinDsLatencyEntry ::= SEQUENCE
    {
    docsRphyCcapCinDsLatencyLastVal           Unsigned32,
    docsRphyCcapCinDsLatencyLastValTime       TimeStamp,
    docsRphyCcapCinDsLatencyInterval          Unsigned32
    }

docsRphyCcapCinDsLatencyLastVal OBJECT-TYPE
    SYNTAX      Unsigned32
    MAX-ACCESS  read-only
    STATUS      current
    DESCRIPTION 
            "This attribute indicates the latest latency measurement
             on this session."
    ::= { docsRphyCcapCinDsLatencyEntry 1 }

docsRphyCcapCinDsLatencyLastValTime OBJECT-TYPE
    SYNTAX      TimeStamp
    MAX-ACCESS  read-only
    STATUS      current
    DESCRIPTION 
            "This attribute indicates the sysUpTime value of the last 
             time the docsRphyCcapCinLatencyPerfLastVal attribute was 
             updated."
    ::= { docsRphyCcapCinDsLatencyEntry 2 }
    
docsRphyCcapCinDsLatencyInterval OBJECT-TYPE
    SYNTAX      Unsigned32
    MAX-ACCESS  read-only
    STATUS      current
    DESCRIPTION 
            "This attribute provides the time interval used to measure
             periodically the CIN latency per DEPI session. Active 
             measurement of CIN latency applies to active DEPI sessions 
             only. This attribute is constrained to 420 seconds to 
             prevent Master Clock counter overruns. A value zero 
             indicates no CIN latency measurements are configured to 
             be performed."
    ::= { docsRphyCcapCinDsLatencyEntry 3 }
    
-- ---------------------------------------------------------
-- CCAP Core Session CIN Downstream Latency Statistics Table 
-- ---------------------------------------------------------

docsRphyCcapSessionCinDsLatencyStatsTable OBJECT-TYPE
    SYNTAX      SEQUENCE OF DocsRphyCcapSessionCinDsLatencyStatsEntry
    MAX-ACCESS  not-accessible
    STATUS      current
    DESCRIPTION
            "This table provides sequence of recent measurements of the 
             CIN latency on the network as measured by the CCAP Core. 
             When the table is full, the oldest measurement is 
             replaced with a new one. This table is based on the
             docsIfMCmtsDepiSessionCinLatencyPerfTable object defined 
             in the DOCS-IF-M-CMTS-MIB and has been extended for 
             Remote PHY."
    ::= { docsRphyCcapMibObjects 5 }

docsRphyCcapSessionCinDsLatencyStatsEntry OBJECT-TYPE
    SYNTAX      DocsRphyCcapSessionCinDsLatencyStatsEntry
    MAX-ACCESS  not-accessible
    STATUS      current
    DESCRIPTION
            "The conceptual row of docsRphyCcapSessionCinDsLatencyStatsTable.
             A row entry is created for every session the CCAP Core 
             terminates. This is an extension to 
             docsRphyCcapL2tpSessionFlowTable for the CCAP Core."
    INDEX { docsRphyCcapL2tpSessionInfoSessionIpAddrType,
            docsRphyCcapL2tpSessionInfoCcapLcceIpAddr,
            docsRphyCcapL2tpSessionInfoRpdLcceIpAddr,
            docsRphyCcapL2tpSessionInfoDirection,
            docsRphyCcapL2tpSessionInfoL2tpSessionId,
            docsRphyCcapL2tpSessionFlowPspFlowId,
            docsRphyCcapSessionCinDsLatencyStatsIntervalSeq }
    ::= { docsRphyCcapSessionCinDsLatencyStatsTable 1 }

DocsRphyCcapSessionCinDsLatencyStatsEntry ::= SEQUENCE
    {
    docsRphyCcapSessionCinDsLatencyStatsIntervalSeq       Unsigned32,
    docsRphyCcapSessionCinDsLatencyStatsVal               Unsigned32,
    docsRphyCcapSessionCinDsLatencyStatsValTime           TimeStamp
    }

docsRphyCcapSessionCinDsLatencyStatsIntervalSeq OBJECT-TYPE
    SYNTAX      Unsigned32
    MAX-ACCESS  not-accessible
    STATUS      current
    DESCRIPTION 
            "This attribute indicates the interval sequence where the 
             CIN latency measurement was taken. It is valid in an 
             implementation that overrides the oldest sequence number 
             entry with the most recent measurement."
    ::= { docsRphyCcapSessionCinDsLatencyStatsEntry 1 }

docsRphyCcapSessionCinDsLatencyStatsVal OBJECT-TYPE
    SYNTAX      Unsigned32
    MAX-ACCESS  read-only
    STATUS      current
    DESCRIPTION 
            "This attribute indicates the CIN latency value measured 
             for the session referenced by this entry."
    ::= { docsRphyCcapSessionCinDsLatencyStatsEntry 2 }
    
docsRphyCcapSessionCinDsLatencyStatsValTime OBJECT-TYPE
    SYNTAX      TimeStamp
    MAX-ACCESS  read-only
    STATUS      current
    DESCRIPTION 
            "This attribute provides the sysUpTime value for the last 
             time docsRphyCcapCinLatencyPerfVal was updated."
    ::= { docsRphyCcapSessionCinDsLatencyStatsEntry 3 }

-- ---------------------------------------------------------------------
-- Security Server Cert Objects
-- ---------------------------------------------------------------------

docsRphyCcapSecServerCertSubject   OBJECT-TYPE
   		SYNTAX      SnmpAdminString
   		MAX-ACCESS  read-only
   		STATUS      current
   		DESCRIPTION
      		"This attribute represents the subject name exactly as 
      		it is encoded in the X509 certificate. The organizationName 
      		portion of the certificate's subject name must be present.  
      		All other fields are optional.  Any optional field present 
      		must be prepended with <CR> (carriage return, U+000D) 
      		<LF> (line feed, U+000A).
			Ordering of fields present must conform to the following:
        		organizationName <CR> <LF>
       		 	countryName <CR> <LF>
        		stateOrProvinceName <CR> <LF>
        		localityName <CR> <LF>
        		organizationalUnitName <CR> <LF>
        		organizationalUnitName=<Manufacturing Location> <CR> <LF>
        		commonName
			"
   		::= { docsRphyCcapSecMibObjects 1 }
   		
docsRphyCcapSecServerCertIssuer   OBJECT-TYPE
   		SYNTAX      SnmpAdminString
   		MAX-ACCESS  read-only
   		STATUS      current
   		DESCRIPTION
      		"This attribute represents the issuer name exactly as it is 
      		encoded in the X509 certificate. The commonName portion of 
      		the certificate's issuer name must be present.  All other 
      		fields are optional.  Any optional field present must be 
      		prepended with <CR> (carriage return, U+000D) <LF> (line feed, U+000A).
			Ordering of fields present must conform to the following:
        		commonName <CR> <LF>
        		countryName <CR> <LF>
        		stateOrProvinceName <CR> <LF>
        		localityName <CR> <LF>
        		organizationalUnitName <CR> <LF>
        		organizationalUnitName=<Manufacturing Location> 
			"
   		::= { docsRphyCcapSecMibObjects 2 }
   		
docsRphyCcapSecServerCertSerialNumber   OBJECT-TYPE
   		SYNTAX      OCTET STRING (SIZE (0..32))
   		MAX-ACCESS  read-only
   		STATUS      current
   		DESCRIPTION
      		"This attribute represents the certificate's serial number, 
      		represented as an octet string. "
   		::= { docsRphyCcapSecMibObjects 3 }

docsRphyCcapSecServerCertSource   OBJECT-TYPE
   		SYNTAX      INTEGER {
                           	snmp(1),
                           	configurationFile (2),
 							externalDatabase (3),
 							other (4),
 							authentInfo (5),
 							compiledIntoCode (6)
                    }
   		MAX-ACCESS  read-only
   		STATUS      current
   		DESCRIPTION
      		"This attribute indicates how the certificate reached the 
      		CCAP Core.  Other (4) means that it originated from a source 
      		not identified above."
   		::= { docsRphyCcapSecMibObjects 4 }

docsRphyCcapSecServerCertCert   OBJECT-TYPE
   		SYNTAX      DocsX509ASN1DEREncodedCertificate 
   		MAX-ACCESS  read-only
   		STATUS      current
   		DESCRIPTION
      		"This attribute represents an X509 DER-encoded CCAP Core certificate."
   		::= { docsRphyCcapSecMibObjects 5 }
   		
docsRphyCcapSecServerCertCertThumbprint   OBJECT-TYPE
   		SYNTAX      OCTET STRING (SIZE (20))
   		MAX-ACCESS  read-only
   		STATUS      current
   		DESCRIPTION
      		"This attribute represents the SHA-1 hash of the 
      		CCAP Core certificate.  "
   		::= { docsRphyCcapSecMibObjects 6 }
    
-- ---------------------------------------------------------
-- CMTS CM Reg Status Table 
-- ---------------------------------------------------------
docsRphyCmtsCmRegStatusTable OBJECT-TYPE
		SYNTAX  SEQUENCE OF DocsRphyCmtsCmRegStatusEntry
		MAX-ACCESS  not-accessible
		STATUS  current
		DESCRIPTION
		    "This table extends docsIf3CmtsCmRegStatusTable
		    for RPHY."
		::= { docsRphyCmtsCmStatMibObjects 1 }

docsRphyCmtsCmRegStatusEntry OBJECT-TYPE
		SYNTAX  DocsRphyCmtsCmRegStatusEntry
		MAX-ACCESS  not-accessible
		STATUS  current
		DESCRIPTION
		    "The conceptual row of docsRphyCmtsCmRegStatusTable."
		INDEX   { docsIf3CmtsCmRegStatusId }
		::= { docsRphyCmtsCmRegStatusTable 1 }

DocsRphyCmtsCmRegStatusEntry ::= SEQUENCE
	    {
	     docsRphyCmtsCmRegStatusRpdUniqueId	    MacAddress
	    }


docsRphyCmtsCmRegStatusRpdUniqueId OBJECT-TYPE
		SYNTAX  MacAddress
		MAX-ACCESS  read-only
		STATUS  current
		DESCRIPTION
		    "This attribute specifies a globally unique 6-byte 
                     identifier for the RPD attached to the CM specified by the Id index."
		::= { docsRphyCmtsCmRegStatusEntry 1 }


-- ---------------------------------------------------------
-- Conformance definitions 
-- ---------------------------------------------------------

docsRphyCompliance MODULE-COMPLIANCE 
     STATUS current 
     DESCRIPTION 
          "The compliance statement for RPD management features."


MODULE -- docsRphyMib
          
-- conditionally mandatory groups


GROUP docsRphyRpdGroup 
        DESCRIPTION
            "Group of objects applicable to RPDs only.
            These objects are implemented on the CCAP Core
            but are derived from the RPD via the GCP protocol."

GROUP docsRphyCcapCoreGroup 
        DESCRIPTION
            "Group of objects applicable to CCAP Core only."
            
-- conditionally optional groups


::= { docsRphyCompliances 1}


docsRphyRpdGroup OBJECT-GROUP
        OBJECTS {
                docsRphyRpdDevInfoSysUpTime,
                docsRphyRpdDevInfoNumCrashFilesAvail,
                docsRphyRpdDevIdVendorName,     
                docsRphyRpdDevIdVendorId,            
                docsRphyRpdDevIdModelNum,            
                docsRphyRpdDevIdSerialNum,           
                docsRphyRpdDevIdDeviceAlias,         
                docsRphyRpdDevIdDeviceDescr,
                docsRphyRpdDevIdHwRev,         
                docsRphyRpdDevIdCurrSwVer,           
                docsRphyRpdDevIdBootRomVer,
                docsRphyRpdDevIdUsBurstRcvrVendorId,
                docsRphyRpdDevIdUsBurstRcvrModelNum,
                docsRphyRpdDevIdUsBurstRcvrDrivVer,
                docsRphyRpdDevIdUsBurstRcvrSerialNum,
                docsRphyRpdDevIdRcpProtocolVer,
                docsRphyRpdDevIdRcpSchemaVer,
		docsRphyRpdDevIdCurrSwImageLastUpdate,  			      
		docsRphyRpdDevIdCurrSwImageName,  		
		docsRphyRpdDevIdCurrSwImageServerType,  	
		docsRphyRpdDevIdCurrSwImageServerAddress,


                docsRphyRpdDevLocationDescr,              
                docsRphyRpdDevLocationLatitude,           
                docsRphyRpdDevLocationLongitude,
              
                docsRphyRpdDevCoresConnectedAddressType,         
                docsRphyRpdDevCoresConnectedAddress,             
                docsRphyRpdDevCoresConnectedIsPrincipal,         
                docsRphyRpdDevCoresConnectedName,
                docsRphyRpdDevCoresConnectedVendorId,
                docsRphyRpdDevCoresConnectedCoreMode,
                docsRphyRpdDevCoresConnectedInitConfigComplete,
                docsRphyRpdDevCoresConnectedCoreFunction,		

                docsRphyRpdDevCapabNumDsPorts,                 
                docsRphyRpdDevCapabNumUsPorts,                 
                docsRphyRpdDevCapabNumTenGeNsPorts,            
                docsRphyRpdDevCapabNumOneGeNsPorts,          
                docsRphyRpdDevCapabNumDsScQamChans,          
                docsRphyRpdDevCapabNumDsOfdmChans,         
                docsRphyRpdDevCapabNumUsScQamChans,          
                docsRphyRpdDevCapabNumUsOfdmaChans,          
                docsRphyRpdDevCapabNumDsOob55d1Chans,          
                docsRphyRpdDevCapabNumUsOob55d1Chans,          
                docsRphyRpdDevCapabNumDsOob55d2Modules,          
                docsRphyRpdDevCapabNumUsOob55d2Demods,          
                docsRphyRpdDevCapabNumNdfChans,              
                docsRphyRpdDevCapabNumNdrChans,     
                docsRphyRpdDevCapabNumDsPspFlowsPerChan,       
                docsRphyRpdDevCapabNumUsPspFlowsPerChan,       
                docsRphyRpdDevCapabNumAsynchVideoChans,        
                docsRphyRpdDevCapabNumCwToneGens,              
                docsRphyRpdDevCapabLowestCwToneFreq,           
                docsRphyRpdDevCapabHighestCwToneFreq,          
                docsRphyRpdDevCapabMaxPwrDedCwTone,               
                docsRphyRpdDevCapabQamAsPilot,
                docsRphyRpdDevCapabSupportsUdpEncap,
                docsRphyRpdDevCapabSupportsFlowTags,
                docsRphyRpdDevCapabSupportsFreqTilt,
                docsRphyRpdDevCapabMaxTiltValue,
                docsRphyRpdDevCapabBufferDepthMonAlertSupp,
                docsRphyRpdDevCapabBufferDepthCfgSupp,
                docsRphyRpdDevCapabRpdUcdProcTime,
                docsRphyRpdDevCapabRpdUcdChgNullGrtTime,
                docsRphyRpdDevCapabMultiSectionTimingMerRep,
		docsRphyRpdDevCapabMinPwrDedCwTone, 
		docsRphyRpdDevCapabMaxPwrQamCwTone,
		docsRphyRpdDevCapabMinPwrQamCwTone,
		docsRphyRpdDevCapabSupportsOpticalNodeRf, 
		docsRphyRpdDevCapabMaxDsFrequency, 
		docsRphyRpdDevCapabMinDsFrequency,
		docsRphyRpdDevCapabMaxBasePwr, 
		docsRphyRpdDevCapabMinTiltValue, 
		docsRphyRpdDevCapabMinPwrAdjustScQam, 
		docsRphyRpdDevCapabMaxPwrAdjustScQam, 
		docsRphyRpdDevCapabMinPwrAdjustOfdm, 
		docsRphyRpdDevCapabMaxPwrAdjustOfdm,
		docsRphyRpdDevCapabVspSelector,
                docsRphyRpdDevCapabMinBaseUsPowerTarLevel,
                docsRphyRpdDevCapabMaxBaseUsPowerTarLevel,
                docsRphyRpdDevCapabMinTarRxPowerAdjustScqam,
                docsRphyRpdDevCapabMaxTarRxPowerAdjustScqam,
                docsRphyRpdDevCapabMinTarRxPowerAdjustOfdma,
                docsRphyRpdDevCapabMaxTarRxPowerAdjustOfdma,
                docsRphyRpdDevCapabMinTarRxPowerAdjustNdr,
                docsRphyRpdDevCapabMaxTarRxPowerAdjustNdr, 
                
                docsRphyRpdDevChanReachabilityEndChanIndex,   
                       
                docsRphyRpdDevDsUsRfPortAllocScQamChans,         
                docsRphyRpdDevDsUsRfPortAllocOfdmChans,          
                docsRphyRpdDevDsUsRfPortAllocOob551Chans,            
                docsRphyRpdDevDsUsRfPortAllocNdChans,
                
                docsRphyRpdDevL2tpSessionInfoCoreId,                           
                docsRphyRpdDevL2tpSessionInfoConnCtrlID,            
                docsRphyRpdDevL2tpSessionInfoUdpPort,               
                docsRphyRpdDevL2tpSessionInfoDescr,                 
                docsRphyRpdDevL2tpSessionInfoSessionType,           
                docsRphyRpdDevL2tpSessionInfoSessionSubType,        
                docsRphyRpdDevL2tpSessionInfoMaxPayload,            
                docsRphyRpdDevL2tpSessionInfoPathPayload,           
                docsRphyRpdDevL2tpSessionInfoRpdIfMtu, 
                docsRphyRpdDevL2tpSessionInfoCoreIfMtu,             
                docsRphyRpdDevL2tpSessionInfoErrorCode,             
                docsRphyRpdDevL2tpSessionInfoCreationTime,          
                docsRphyRpdDevL2tpSessionInfoOperStatus,            
                docsRphyRpdDevL2tpSessionInfoLocalStatus,           
                docsRphyRpdDevL2tpSessionInfoLastChange,
                
                docsRphyRpdDevL2tpSessionStatsOutOfSeqPkts,  
                docsRphyRpdDevL2tpSessionStatsInPkts,
                docsRphyRpdDevL2tpSessionStatsInDiscards,
                docsRphyRpdDevL2tpSessionStatsOutPkts,
                docsRphyRpdDevL2tpSessionStatsOutErrors,
                
                docsRphyRpdDevDiagStatusProbableCause,
                docsRphyRpdDevDiagStatusAdditionalText,
                docsRphyRpdDevDiagStatusSeverityLevel,
                
                docsRphyRpdDevDepiMcastSessionLocalLcceIpAddr,
                docsRphyRpdDevDepiMcastSessionRemoteLcceIpAddr,
                docsRphyRpdDevDepiMcastSessionId,
                docsRphyRpdDevDepiMcastSessionJoinTime,
                
                docsRphyRpdDevEventLogFirstTime,
                docsRphyRpdDevEventLogLastTime,
                docsRphyRpdDevEventLogCounts,
                docsRphyRpdDevEventLogLevel,
                docsRphyRpdDevEventLogId,
                docsRphyRpdDevEventLogText,
                
                docsRphyRpdDevOob551UsChanStatusNcIpAddrType,
                docsRphyRpdDevOob551UsChanStatusNcIpAddr,
                docsRphyRpdDevOob551UsChanStatusArpdSrcIpAddrType,
                docsRphyRpdDevOob551UsChanStatusArpdSrcIpAddr,
                docsRphyRpdDevOob551UsChanStatusPerfectCellsRcvd,
                docsRphyRpdDevOob551UsChanStatusCorrectedCellsRcvd,
                docsRphyRpdDevOob551UsChanStatusUncorrectableCellsRcvd,
                docsRphyRpdDevOob551UsChanStatusTotalCellsRcvd,
                docsRphyRpdDevOob551UsChanStatusPwrLevel,
                docsRphyRpdDevOob551UsChanStatusMaxPwrLevel,
                docsRphyRpdDevOob551UsChanStatusMinPwrLevel,
                docsRphyRpdDevOob551UsChanStatusCounterDiscontinuityTime,
				
                docsRphyRpdDevCrashDataFileStatusFilename,
                docsRphyRpdDevCrashDataFileStatusFileStatus,
                
                docsRphyRpdDevUsSignalQualityRxMer,
       		docsRphyRpdDevUsSignalQualityRxMerSamples,
       		docsRphyRpdDevUsSignalQualityUnerroreds,
       		docsRphyRpdDevUsSignalQualityCorrecteds,
       		docsRphyRpdDevUsSignalQualityUncorrectables,

		docsRphyRpdDevHostResSysDate,

		docsRphyRpdDevHostResStorType,
		docsRphyRpdDevHostResStorAllocationUnits,
		docsRphyRpdDevHostResStorAllocationFailures,
		docsRphyRpdDevHostResStorSize,
		docsRphyRpdDevHostResStorUsed,
		docsRphyRpdDevHostResStorDescr,

		docsRphyRpdDevHostResSwRunType,
		docsRphyRpdDevHostResSwRunStatus,
		docsRphyRpdDevHostResSwRunPerfCpu,
		docsRphyRpdDevHostResSwRunPerfMem,
		docsRphyRpdDevHostResSwRunName,

                docsRphyRpdDevStaticPwCapMaxFwdStaticPws,
                docsRphyRpdDevStaticPwCapMaxRetStaticPws,
                docsRphyRpdDevStaticPwCapSupportsStaticMptDepiPw,
                docsRphyRpdDevStaticPwCapSupportsStaticMpt55d1RetPw,
                docsRphyRpdDevStaticPwCapSupportsStaticPspNdfPw,
                docsRphyRpdDevStaticPwCapSupportsStaticPspNdrPw,

                docsRphyRpdIfPhysEntityDescr,          
                docsRphyRpdIfPhysEntityVendorType,     
                docsRphyRpdIfPhysEntityContainedIn,    
                docsRphyRpdIfPhysEntityClass,          
                docsRphyRpdIfPhysEntityParentRelPos,   
                docsRphyRpdIfPhysEntityName,           
                docsRphyRpdIfPhysEntityHardwareRev,    
                docsRphyRpdIfPhysEntityFirmwareRev,    
                docsRphyRpdIfPhysEntitySoftwareRev,    
                docsRphyRpdIfPhysEntitySerialNum,      
                docsRphyRpdIfPhysEntityMfgName,        
                docsRphyRpdIfPhysEntityModelName,      
                docsRphyRpdIfPhysEntityAlias,          
                docsRphyRpdIfPhysEntityAssetID,        
                docsRphyRpdIfPhysEntityIsFRU,          
                docsRphyRpdIfPhysEntityMfgDate,        
                docsRphyRpdIfPhysEntityUris,           
                docsRphyRpdIfPhysEntityUUID,
                docsRphyRpdIfPhysEntityCoreIfIndex,
                
                docsRphyRpdIfPhysEntSensorType,            
                docsRphyRpdIfPhysEntSensorScale,           
                docsRphyRpdIfPhysEntSensorPrecision,       
                docsRphyRpdIfPhysEntSensorValue,           
                docsRphyRpdIfPhysEntSensorOperStatus,      
                docsRphyRpdIfPhysEntSensorUnitsDisplay,    
                docsRphyRpdIfPhysEntSensorValueTimeStamp,  
                docsRphyRpdIfPhysEntSensorValueUpdateRate,
                                
                docsRphyRpdIfEnetDescr,                 
                docsRphyRpdIfEnetName,                  
                docsRphyRpdIfEnetAlias,                 
                docsRphyRpdIfEnetType,                  
                docsRphyRpdIfEnetMtu,                                   
                docsRphyRpdIfEnetPhysAddress,           
                docsRphyRpdIfEnetAdminStatus,           
                docsRphyRpdIfEnetOperStatus,            
                docsRphyRpdIfEnetLastChange,            
                docsRphyRpdIfEnetLinkUpDownTrapEnable,  
                docsRphyRpdIfEnetHighSpeed,             
                docsRphyRpdIfEnetPromiscuousMode,      
                docsRphyRpdIfEnetConnectorPresent,
                docsRphyRpdIfEnetStatsInOctets,            
                docsRphyRpdIfEnetStatsOutOctets,           
                docsRphyRpdIfEnetStatsInFrames,            
                docsRphyRpdIfEnetStatsOutFrames,           
                docsRphyRpdIfEnetStatsInUnicastOctets,     
                docsRphyRpdIfEnetStatsOutUnicastOctets,   
                docsRphyRpdIfEnetStatsInUnicastFrames,     
                docsRphyRpdIfEnetStatsOutUnicastFrames,    
                docsRphyRpdIfEnetStatsInMulticastOctets,   
                docsRphyRpdIfEnetStatsOutMulticastOctets,  
                docsRphyRpdIfEnetStatsInMulticastFrames,   
                docsRphyRpdIfEnetStatsOutMulticastFrames,  
                docsRphyRpdIfEnetStatsInBroadcastOctets,    
                docsRphyRpdIfEnetStatsOutBroadcastOctets,  
                docsRphyRpdIfEnetStatsInBroadcastFrames,   
                docsRphyRpdIfEnetStatsOutBroadcastFrames,  
                docsRphyRpdIfEnetStatsInDiscards,          
                docsRphyRpdIfEnetStatsOutDiscards,         
                docsRphyRpdIfEnetStatsInErrors,            
                docsRphyRpdIfEnetStatsOutErrors,           
                docsRphyRpdIfEnetStatsInUnknownProtos,     
                docsRphyRpdIfEnetStatsCounterDiscontinuityTime, 
                
                docsRphyRpdIfRpdEnetToCoreEntityMapEntityIndex,
                
                docsRphyRpdIfCoreToRpdMapRpdUniqueId,
                docsRphyRpdIfCoreToRpdMapRpdRfPortDirection,
                docsRphyRpdIfCoreToRpdMapRpdRfPortIndex,
                docsRphyRpdIfCoreToRpdMapRpdRfChanType,
                docsRphyRpdIfCoreToRpdMapRpdRfChanIndex,
                
                docsRphyRpdIfRpdToCoreMapCoreIfIndex,
                
                docsRphyRpdIpv4GrpDefaultTTL,                                
                docsRphyRpdIpv4GrpInterfaceTableLastChange,
                             
                docsRphyRpdIpv6GrpIpDefaultHopLimit,        
                docsRphyRpdIpv6GrpInterfaceTableLastChange, 
                docsRphyRpdIpv6GrpIfStatsTableLastChange,     
                            
                docsRphyRpdIpv4InterfaceEnableStatus,
                docsRphyRpdIpv4InterfaceRetransmitTime,
                   
                docsRphyRpdIpv6InterfaceIdentifier,
                docsRphyRpdIpv6InterfaceEnableStatus,   
                docsRphyRpdIpv6InterfaceReachableTime,
                docsRphyRpdIpv6InterfaceRetransmitTime,        
                
                docsRphyRpdIpIfStatsInReceives,          
                docsRphyRpdIpIfStatsInOctets,            
                docsRphyRpdIpIfStatsInHdrErrors,         
                docsRphyRpdIpIfStatsInNoRoutes,          
                docsRphyRpdIpIfStatsInAddrErrors,       
                docsRphyRpdIpIfStatsInUnknownProtos,     
                docsRphyRpdIpIfStatsInTruncatedPkts,          
                docsRphyRpdIpIfStatsInDiscards,          
                docsRphyRpdIpIfStatsInDelivers,                
                docsRphyRpdIpIfStatsOutRequests,                 
                docsRphyRpdIpIfStatsOutDiscards,                  
                docsRphyRpdIpIfStatsOutTransmits,        
                docsRphyRpdIpIfStatsOutOctets,               
                docsRphyRpdIpIfStatsInMcastPkts,          
                docsRphyRpdIpIfStatsInMcastOctets,         
                docsRphyRpdIpIfStatsOutMcastPkts,        
                docsRphyRpdIpIfStatsOutMcastOctets,           
                docsRphyRpdIpIfStatsDiscontinuityTime,   
                docsRphyRpdIpIfStatsRefreshRate,         
                         
                docsRphyRpdIpAddressEnetPortIndex,    
                docsRphyRpdIpAddressPrefixLen,
                docsRphyRpdIpAddressType,
                docsRphyRpdIpAddressOrigin,    
                docsRphyRpdIpAddressStatus,
                docsRphyRpdIpAddressCreated,   
                docsRphyRpdIpAddressLastChanged,              
                
                docsRphyRpdIpNetToPhysicalPhysAddress, 
                docsRphyRpdIpNetToPhysicalLastUpdated,
                docsRphyRpdIpNetToPhysicalType,        
                docsRphyRpdIpNetToPhysicalState,            
                
                docsRphyRpdIpDefaultRouterLifetime, 
                docsRphyRpdIpDefaultRouterPreference,
                
                docsRphyRpdIpIcmpMsgStatsInPkts, 
                docsRphyRpdIpIcmpMsgStatsOutPkts             
        }
        STATUS      current
        DESCRIPTION
            "Group of objects implemented in CCAP Cores which
            represent RPD managed objects derived via the GCP 
            protocol."
        ::= { docsRphyGroups 1 }

docsRphyCcapCoreGroup OBJECT-GROUP
        OBJECTS {      
                docsRphyCcapL2tpSessionInfoCoreId,                
                docsRphyCcapL2tpSessionInfoConnCtrlID,            
                docsRphyCcapL2tpSessionInfoUdpPort,               
                docsRphyCcapL2tpSessionInfoDescr,                 
                docsRphyCcapL2tpSessionInfoSessionType,           
                docsRphyCcapL2tpSessionInfoSessionSubType,        
                docsRphyCcapL2tpSessionInfoMaxPayload,            
                docsRphyCcapL2tpSessionInfoPathPayload, 
                docsRphyCcapL2tpSessionInfoRpdIfMtu,                 
                docsRphyCcapL2tpSessionInfoCoreIfMtu,             
                docsRphyCcapL2tpSessionInfoIncludeDOCSISMsgs,     
                docsRphyCcapL2tpSessionInfoErrorCode,             
                docsRphyCcapL2tpSessionInfoCreationTime,          
                docsRphyCcapL2tpSessionInfoOperStatus,            
                docsRphyCcapL2tpSessionInfoLocalStatus,           
                docsRphyCcapL2tpSessionInfoLastChange,
                
	        	docsRphyCcapL2tpSessionFlowPhbId,
                
                docsRphyCcapL2tpSessionStatsOutOfSeqPkts,
                docsRphyCcapL2tpSessionStatsInPkts,
                docsRphyCcapL2tpSessionStatsInDiscards,
                docsRphyCcapL2tpSessionStatsOutPkts,
                docsRphyCcapL2tpSessionStatsOutErrors,
                
                docsRphyCcapCinDsLatencyLastVal,           
                docsRphyCcapCinDsLatencyLastValTime,       
                docsRphyCcapCinDsLatencyInterval,
                
                docsRphyCcapSessionCinDsLatencyStatsVal,               
                docsRphyCcapSessionCinDsLatencyStatsValTime                    
        }
        STATUS      current
        DESCRIPTION
            "Group of objects implemented in CCAP Cores."
        ::= { docsRphyGroups 2 }
        
docsRphyCcapSecGroup OBJECT-GROUP
        OBJECTS {
        	 docsRphyCcapSecServerCertSubject,
        	 docsRphyCcapSecServerCertIssuer,
        	 docsRphyCcapSecServerCertSerialNumber,
        	 docsRphyCcapSecServerCertSource,
        	 docsRphyCcapSecServerCertCert,
        	 docsRphyCcapSecServerCertCertThumbprint
        }
        STATUS      current
        DESCRIPTION
            "Group of objects implemented to support security in CCAP Core."
        ::= { docsRphyGroups 3 }


docsRphyCmtsCmStatGroup OBJECT-GROUP
        OBJECTS {
        	docsRphyCmtsCmRegStatusRpdUniqueId	
        }
        STATUS      current
        DESCRIPTION
            "Group of objects implemented to support CMTS Status in CCAP Core."
        ::= { docsRphyGroups 4 }
    

        END
