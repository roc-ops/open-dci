DOCS-RPHY-PTP-MIB DEFINITIONS ::= BEGIN
IMPORTS
    MODULE-IDENTITY, 
    OBJECT-TYPE, 
    Unsigned32,
    Gauge32,
    Counter32,
    Counter64,
    Integer32,
    TimeTicks
        FROM SNMPv2-SMI         -- RFC 2578
    TruthValue, 
    MacAddress,
    TimeStamp,
    AutonomousType,
    DateAndTime,
    PhysAddress,
    TEXTUAL-CONVENTION
        FROM SNMPv2-TC 
    OBJECT-GROUP, 
    MODULE-COMPLIANCE 
        FROM SNMPv2-CONF
    SnmpAdminString
        FROM SNMP-FRAMEWORK-MIB -- RFC 3411
    InetAddressType,
    InetAddress,
    InetPortNumber,
    InetVersion,
    InetAddressPrefixLength
        FROM INET-ADDRESS-MIB   -- RFC 4001
    UUIDorZero
        FROM UUID-TC-MIB        -- RFC 6933
    IANAPhysicalClass
        FROM IANA-ENTITY-MIB    -- RFC 6933
    IANAifType                               
        FROM IANAifType-MIB
    InterfaceIndex,
    ifIndex,
    InterfaceIndexOrZero
        FROM IF-MIB
    IfDirection
        FROM DOCS-IF3-MIB
    clabProjDocsis
        FROM CLAB-DEF-MIB
    docsRphyRpdDevInfoUniqueId
        FROM DOCS-RPHY-MIB;


docsRphyPtpMib MODULE-IDENTITY 
    LAST-UPDATED    "201901240000Z" -- January 24, 2019
    ORGANIZATION    "Cable Television Laboratories, Inc" 
    CONTACT-INFO 
         "
         Postal: Cable Television Laboratories, Inc. 
         400 Centennial Parkway 
         Louisville, Colorado 80027-1266 
         U.S.A. 
         Phone: +1 303-661-9100 
         Fax: +1 303-661-9199 
         E-mail: mibs@cablelabs.com" 
    DESCRIPTION 
        "This MIB module contains the status and reporting objects
         for the Remote PHY CCAP Core and RPD PTP management.
         Copyright 2017-2018 Cable Television Laboratories, Inc.
         All rights reserved."
    REVISION "201901240000Z" -- January 24, 2019
    DESCRIPTION 
        "This version includes modifications 
         per ECN DOCS-RPHY-PTP-MIB-N-18.1986-2."
    REVISION "201804120000Z" -- April 12, 2018
    DESCRIPTION 
        "This version includes modifications 
         per ECN DOCS-RPHY-PTP-MIB-N-18.1896-2." 
    REVISION "201708100000Z" -- August 10, 2017
    DESCRIPTION 
        "This version includes modifications 
         per ECN DOCS-RPHY-PTP-MIB-N-17.1782-2."     
    REVISION "201704130000Z" -- April 13, 2017
    DESCRIPTION 
        "Initial version, created by R-OSSI-N-17.1721-3."
::= { clabProjDocsis 32 }


-- ---------------------------------------------------------
-- Textual Conventions
-- ---------------------------------------------------------

                         
-- ---------------------------------------------------------------------
-- Main Groups
-- ---------------------------------------------------------------------
docsRphyPtpNotifications        OBJECT IDENTIFIER ::= { docsRphyPtpMib 0}
docsRphyPtpObjects              OBJECT IDENTIFIER ::= { docsRphyPtpMib 1}
docsRphyPtpConformance          OBJECT IDENTIFIER ::= { docsRphyPtpMib 2}

docsRphyPtpRpdMibObjects        OBJECT IDENTIFIER ::= { docsRphyPtpObjects 1}
docsRphyPtpCcapMibObjects       OBJECT IDENTIFIER ::= { docsRphyPtpObjects 2}

docsRphyPtpCompliances          OBJECT IDENTIFIER ::= { docsRphyPtpConformance 1 } 
docsRphyPtpGroups               OBJECT IDENTIFIER ::= { docsRphyPtpConformance 2 }


-- ---------------------------------------------------------------------
-- Notification Objects
-- ---------------------------------------------------------------------

-- ---------------------------------------------------------------------
-- CCAP Core Group Objects
-- ---------------------------------------------------------------------

-- ---------------------------------------------------------------------
-- Default DataSet Group
-- ---------------------------------------------------------------------

docsRphyPtpCcapDefaultDataSet OBJECT IDENTIFIER ::= {docsRphyPtpCcapMibObjects 1}

docsRphyPtpCcapDefaultDataSetTwoStepFlag     OBJECT-TYPE 
	SYNTAX      TruthValue
	MAX-ACCESS  read-only 
     	STATUS      current
     	DESCRIPTION
        		"This attribute specifies whether the Two Step process is 
                    used (i.e., the clock is a two-step clock)."
	::= {docsRphyPtpCcapDefaultDataSet 1}

docsRphyPtpCcapDefaultDataSetClockIdentity   OBJECT-TYPE 
    SYNTAX      OCTET STRING(SIZE(8))
    MAX-ACCESS  read-only	   
    STATUS      current
    DESCRIPTION
        "This attribute specifies the default Dataset clock identity."
    ::= {docsRphyPtpCcapDefaultDataSet 2}

docsRphyPtpCcapDefaultDataSetPriority1       OBJECT-TYPE 
     SYNTAX      Unsigned32
     MAX-ACCESS  read-only
     STATUS      current
     DESCRIPTION
          "This attribute specifies the default Dataset clock Priority1. 
          Lower values take precedence."
     ::= {docsRphyPtpCcapDefaultDataSet 3}

docsRphyPtpCcapDefaultDataSetPriority2       OBJECT-TYPE 
     SYNTAX      Unsigned32
     MAX-ACCESS  read-only      
     STATUS      current
     DESCRIPTION
          "This attribute specifies the default Dataset clock Priority2. 
          Lower values take precedence."
     ::= {docsRphyPtpCcapDefaultDataSet 4}

docsRphyPtpCcapDefaultDataSetSlaveOnly       OBJECT-TYPE 
     SYNTAX      TruthValue
     MAX-ACCESS  read-only      
     STATUS      current
     DESCRIPTION
	"This attribute specifies whether the SlaveOnly flag is set."
     ::= {docsRphyPtpCcapDefaultDataSet 5}

docsRphyPtpCcapDefaultDataSetQualityClass    OBJECT-TYPE 
     SYNTAX      Unsigned32(0..255)
     MAX-ACCESS  read-only      
     STATUS      current
     DESCRIPTION
	"This attribute of an ordinary or boundary clock denotes the traceability 
          of the time or frequency distributed by the grandmaster clock. 
          See section 7.6.2.4 in [IEEE 1588]."	
     ::= {docsRphyPtpCcapDefaultDataSet 6}

docsRphyPtpCcapDefaultDataSetQualityAccuracy OBJECT-TYPE 
     SYNTAX      Unsigned32
     MAX-ACCESS  read-only      
     STATUS      current
     DESCRIPTION
        "This attribute characterizes a clock for the purpose of the best master
        clock (BMC) algorithm. See section 7.6.2.5 in [IEEE 1588]."
     ::= {docsRphyPtpCcapDefaultDataSet 7}

docsRphyPtpCcapDefaultDataSetQualityOffset   OBJECT-TYPE 
     SYNTAX      Unsigned32(0..65535)
     MAX-ACCESS  read-only      
     STATUS      current
     DESCRIPTION
          "This attribute is the offset, scaled, logarithmic representation of 
          the clock variance. See Section 7.6.3.5 in [IEEE 1588]."
     ::= {docsRphyPtpCcapDefaultDataSet 8}

-- ---------------------------------------------------------------------
-- Current DataSet Group
-- ---------------------------------------------------------------------
docsRphyPtpCcapCurrentDataSet OBJECT IDENTIFIER ::= {docsRphyPtpCcapMibObjects 2}

docsRphyPtpCcapCurrentDataSetStepsRemoved OBJECT-TYPE     
     SYNTAX      Unsigned32
     UNITS       "steps"
     MAX-ACCESS  read-only      
     STATUS      current
     DESCRIPTION
	"This attribute is the number of communication paths traversed between the 
          local clock and the grandmaster clock. The initialization value is 0."
     ::= {docsRphyPtpCcapCurrentDataSet 1}

docsRphyPtpCcapCurrentDataSetOffsetFromMaster OBJECT-TYPE 
     SYNTAX      Integer32
     UNITS       "Nanoseconds"
     MAX-ACCESS  read-only      
     STATUS      current
     DESCRIPTION
	"This attribute is an implementation-specific representation of the current
          value of the time difference between a master and a slave as computed by 
          the slave."
     ::= {docsRphyPtpCcapCurrentDataSet 2}

docsRphyPtpCcapCurrentDataSetMeanPathDelay OBJECT-TYPE    
     SYNTAX      Unsigned32
     UNITS       "Nanoseconds"
     MAX-ACCESS  read-only      
     STATUS      current
     DESCRIPTION
	"This attribute is an implementation-specific representation of the current
          value of the mean propagation time between a master and slave clock as 
          computed by the slave. Zero means that the path delay is unavailable."
     ::= {docsRphyPtpCcapCurrentDataSet 3}

-- ---------------------------------------------------------------------
-- Parent DataSet Group
-- ---------------------------------------------------------------------

docsRphyPtpCcapParentDataSet OBJECT IDENTIFIER ::= {docsRphyPtpCcapMibObjects 3}

docsRphyPtpCcapParentDataSetParentClockId OBJECT-TYPE 
     SYNTAX      OCTET STRING(SIZE(8))
     MAX-ACCESS  read-only      
     STATUS      current
     DESCRIPTION
	"This attribute is the clock identifier of the clock port on the master that
          issues the Sync messages used in synchronizing this clock."
     ::= {docsRphyPtpCcapParentDataSet 1}

docsRphyPtpCcapParentDataSetParentPortNumber OBJECT-TYPE 
     SYNTAX      Unsigned32
     MAX-ACCESS  read-only      
     STATUS      current
     DESCRIPTION
	"This attribute is the port number of the clock port on the master that issues
          the Sync messages used in synchronizing this clock."
     ::= {docsRphyPtpCcapParentDataSet 2}

docsRphyPtpCcapParentDataSetParentStats OBJECT-TYPE 
     SYNTAX      TruthValue
     MAX-ACCESS  read-only      
     STATUS      current
     DESCRIPTION
	"This attribute is set to True if the clock has a port in the slave state and 
           the clock has computed statistically valid estimates of the ClockOffset 
           Scaled Log Variance and the Clock PhaseChangeRate. If either the ClockOffset 
           Scaled Log Variance or the Clock PhaseChangeRate is not computed, then the
           CCAP core MUST set the value of ParentStats to false."
     ::= {docsRphyPtpCcapParentDataSet 3}

docsRphyPtpCcapParentDataSetClockOffset OBJECT-TYPE 
     SYNTAX      Integer32
     UNITS       "Nanoseconds"
     MAX-ACCESS  read-only      
     STATUS      current
     DESCRIPTION
	"This attribute represents the value of the observed Parent Offset Scaled Log Variance, 
           which is an estimate of the parent clock's PTP variance as observed by the slave clock. 
           The computation of this value is optional, but if not computed, the value of parentStats 
           is FALSE. The initialization value of ClockOffset is 0xFFFF."
     ::= {docsRphyPtpCcapParentDataSet 4}

docsRphyPtpCcapParentDataSetPhaseChangeRate OBJECT-TYPE 
     SYNTAX      Integer32
     UNITS       "Nanoseconds"
     MAX-ACCESS  read-only      
     STATUS      current
     DESCRIPTION
	"This attribute represents the value of Phase Change Rate, which is an estimate 
          of the parent clock's phase change rate as observed by the slave clock. If the 
          estimate exceeds the capacity of its data type, this value is set to 0x7FFF FFFF. 
          A positive sign indicates that the parent clock's phase change rate is greater 
          than the rate of the slave clock. The computation of this value is optional, but 
          if not computed,the value of parentStats is FALSE."
     ::= {docsRphyPtpCcapParentDataSet 5}

docsRphyPtpCcapParentDataSetGmClockIdentity OBJECT-TYPE 
     SYNTAX      OCTET STRING(SIZE(8))
     MAX-ACCESS  read-only      
     STATUS      current
     DESCRIPTION
	"This attribute represents the clock Identity of the grandmaster clock."
     ::= {docsRphyPtpCcapParentDataSet 6}

docsRphyPtpCcapParentDataSetGmPriority1 OBJECT-TYPE 
     SYNTAX      Unsigned32
     MAX-ACCESS  read-only      
     STATUS      current
     DESCRIPTION
	"This attribute represents the priority1 of the grandmaster clock. Lower values take precedence."
     ::= {docsRphyPtpCcapParentDataSet 7}

docsRphyPtpCcapParentDataSetGmPriority2 OBJECT-TYPE 
     SYNTAX      Unsigned32
     MAX-ACCESS  read-only      
     STATUS      current
     DESCRIPTION
	"This attribute represents the priority2 of the grandmaster clock. Lower values take precedence."
     ::= {docsRphyPtpCcapParentDataSet 8}

docsRphyPtpCcapParentDataSetGmQualityClass OBJECT-TYPE 
     SYNTAX      Unsigned32
     MAX-ACCESS  read-only      
     STATUS      current
     DESCRIPTION
	"This attribute is the clock class for the grandmaster clock. The clock class 
           attribute of an ordinary or boundary clock denotes the 
           traceability of the time or frequency distributed by the 
           grandmaster clock. See section 7.6.2.4 in [IEEE 1588]."
     ::= {docsRphyPtpCcapParentDataSet 9}

docsRphyPtpCcapParentDataSetGmQualityAccuracy OBJECT-TYPE 
     SYNTAX      Unsigned32
     MAX-ACCESS  read-only      
     STATUS      current
     DESCRIPTION
	"This attribute characterizes the grandmaster clock for the purpose of the best 
          master clock (BMC) algorithm. See section 7.6.2.5 in [IEEE 1588]."
     ::= {docsRphyPtpCcapParentDataSet 10}

docsRphyPtpCcapParentDataSetGmQualityOffset OBJECT-TYPE 
     SYNTAX      Unsigned32
     MAX-ACCESS  read-only      
     STATUS      current
     DESCRIPTION
	"This attribute represents the offset, scaled, logarithmic representation of the 
          grandmaster clock variance. See Section 7.6.3.5 in [IEEE 1588]."
     ::= {docsRphyPtpCcapParentDataSet 11}

-- ---------------------------------------------------------------------
-- Time Properties Group
-- ---------------------------------------------------------------------
docsRphyPtpCcapTimeProperties OBJECT IDENTIFIER ::= {docsRphyPtpCcapMibObjects 4}

docsRphyPtpCcapTimePropertiesCurrentUtcOffsetValid OBJECT-TYPE
	SYNTAX		TruthValue
	MAX-ACCESS	read-only
	STATUS		current
	DESCRIPTION
		"This attribute represents the value of currentUtcOffsetValid is TRUE if the
                    currentUtcOffset is known to be correct."
	::= {docsRphyPtpCcapTimeProperties 1}

docsRphyPtpCcapTimePropertiesCurrentUtcOffset OBJECT-TYPE
	SYNTAX		Integer32
	UNITS		"Seconds"
	MAX-ACCESS	read-only
	STATUS		current
	DESCRIPTION
		"This attribute represents the offset between International Atomic Time (TAI) 
                    and Universal Coordinated Time (UTC)."
	::= {docsRphyPtpCcapTimeProperties 2}

docsRphyPtpCcapTimePropertiesLeap59 OBJECT-TYPE
	SYNTAX		TruthValue
	MAX-ACCESS	read-only
	STATUS		current
	DESCRIPTION
               	"This attribute represents whether or not there are 59 seconds 
               	in the last minute of the current UTC day for PTP systems 
               	whose epoch is the PTP epoch,; a TRUE value for Leap59 indicates 
               	that the last minute of the current UTC day contains 59 seconds."
	::= {docsRphyPtpCcapTimeProperties 3}

docsRphyPtpCcapTimePropertiesLeap61 OBJECT-TYPE
	SYNTAX		TruthValue
	MAX-ACCESS	read-only
	STATUS		current
	DESCRIPTION
	      	"This attribute represents whether or not there are 61 seconds in the last 
                    minute of the current UTC day for PTP systems whose epoch is the PTP epoch; 
		a TRUE value for Leap61 indicates that the last minute of the current UTC day 
		contains 61 seconds."
	::= {docsRphyPtpCcapTimeProperties 4 }

docsRphyPtpCcapTimePropertiesTimeTraceable OBJECT-TYPE
	SYNTAX		TruthValue
	MAX-ACCESS	read-only
	STATUS		current
	DESCRIPTION
		"This attribute represents whether the timescale and the value of currentUtcOffset 
		are traceable to a primary reference. TimeTraceable is TRUE if the timescale and the 
		value of currentUtcOffset are traceable to a primary reference; otherwise, the value 
		is FALSE."
	::= {docsRphyPtpCcapTimeProperties 5 }

docsRphyPtpCcapTimePropertiesFreqTraceable OBJECT-TYPE
	SYNTAX		TruthValue
	MAX-ACCESS	read-only
	STATUS		current
	DESCRIPTION
		"This attribute represents whether the frequency determining the timescale is traceable 
		to a primary reference. The value of FrequencyTraceable is TRUE if the frequency determining 
		the timescale is traceable to a primary reference; otherwise, the value is FALSE."
	DEFVAL { true }
	::= {docsRphyPtpCcapTimeProperties 6}

docsRphyPtpCcapTimePropertiesPtpTimescale OBJECT-TYPE
	SYNTAX		TruthValue
	MAX-ACCESS	read-only
	STATUS		current
	DESCRIPTION
		"This attribute is always true for grandmaster clocks with a clock timescale of PTP."
	::= {docsRphyPtpCcapTimeProperties 7}

docsRphyPtpCcapTimePropertiesTimeSource OBJECT-TYPE
	SYNTAX		Unsigned32 (0..255)
	MAX-ACCESS	read-only
	STATUS		current
	DESCRIPTION
		"This attribute represents the source of time used by the grandmaster clock. See Table 7 in [IEEE 1588]. 
		If the time source of the grandmaster clock is unknown, the CCAP Core MUST set the TimeSource value to 
		INTERNAL_OSCILLATOR (0xA0)."
	::= {docsRphyPtpCcapTimeProperties 8}

-- ---------------------------------------------------------------------
-- Port Data Set Table
-- ---------------------------------------------------------------------

docsRphyPtpCcapPortDataSetTable OBJECT-TYPE
     	SYNTAX 		SEQUENCE OF DocsRphyPtpCcapPortDataSetEntry
     	MAX-ACCESS         	not-accessible
     	STATUS             	current
     	DESCRIPTION
		"See section 8.2.5 in [IEEE 1588] for details of the 1588 port dataset."
     	::={docsRphyPtpCcapMibObjects 5} 

docsRphyPtpCcapPortDataSetEntry OBJECT-TYPE
	SYNTAX		DocsRphyPtpCcapPortDataSetEntry
	MAX-ACCESS	not-accessible
	STATUS		current
	DESCRIPTION
		"The conceptual row of docsRphyPtpCcapPortDataSetTable."
	INDEX		{docsRphyPtpCcapPortDataSetPortNumber}
	::= {docsRphyPtpCcapPortDataSetTable 1}

DocsRphyPtpCcapPortDataSetEntry ::= SEQUENCE
	{
	docsRphyPtpCcapPortDataSetPortNumber	Unsigned32,
	docsRphyPtpCcapPortDataSetPortState	Unsigned32,
	docsRphyPtpCcapPortDataSetMeanPathDelay	Integer32
	}

docsRphyPtpCcapPortDataSetPortNumber OBJECT-TYPE
	SYNTAX		Unsigned32 (0..65535)
	MAX-ACCESS	not-accessible
	STATUS		current
	DESCRIPTION
		"This key attribute is the port number of the local clock port. 
		Port numbers 0 and 65,535 are reserved and cannot be used for real clock ports. 
		See [IEEE 1588] for more information. When a PTP clock has N ports, 
		the CCAP Core MUST set the port number to a value in the interval 1..N."
	
	::= {docsRphyPtpCcapPortDataSetEntry 1}

docsRphyPtpCcapPortDataSetPortState OBJECT-TYPE
	SYNTAX		Unsigned32 (0..255)
	MAX-ACCESS	read-only
	STATUS		current
	DESCRIPTION
		"This attribute is the state of this PTP clock port. See Table 8 in [IEEE 1588]."	
	::= {docsRphyPtpCcapPortDataSetEntry 2}

docsRphyPtpCcapPortDataSetMeanPathDelay OBJECT-TYPE
	SYNTAX		Integer32
	MAX-ACCESS	read-only
	STATUS		current
	DESCRIPTION
		"This attribute is an implementation-specific representation of the current 
		value of the mean propagation time between a master and slave clock as computed 
		by the slave. Zero means that the path delay is unavailable."
	::= {docsRphyPtpCcapPortDataSetEntry 3}

-- ---------------------------------------------------------------------
-- Clock Status Group
-- ---------------------------------------------------------------------

docsRphyPtpCcapClockStatus OBJECT IDENTIFIER ::= {docsRphyPtpCcapMibObjects 6}

docsRphyPtpCcapClockStatusClockState   OBJECT-TYPE
    	SYNTAX        	INTEGER { 
			freerun(1),
			holdover(2),
			acquiring(3),
			freqLocked(4),
			phaseAligned(5)
      			}
	MAX-ACCESS    	read-only
    	STATUS        	current
    	DESCRIPTION
        		"This attribute represents the current state of the clock."
    	::= {docsRphyPtpCcapClockStatus 1 }

docsRphyPtpCcapClockStatusLastStateChange OBJECT-TYPE
    	SYNTAX        	TimeTicks        
	MAX-ACCESS    	read-only
    	STATUS        	current
    	DESCRIPTION
        		"This attribute represents the value in TimeTicks when the clock state last changed."
    	::= {docsRphyPtpCcapClockStatus 2 }

docsRphyPtpCcapClockStatusPacketsSent OBJECT-TYPE
    	SYNTAX        	Counter64
	UNITS           "Packets"
	MAX-ACCESS    	read-only
    	STATUS        	current
    	DESCRIPTION
        		"This attribute represents the number of PTP packets sent for this clock."
    	::= {docsRphyPtpCcapClockStatus 3 }

docsRphyPtpCcapClockStatusPacketsReceived OBJECT-TYPE
    	SYNTAX        	Counter64
	UNITS           "Packets"
	MAX-ACCESS    	read-only
    	STATUS        	current
    	DESCRIPTION
        		"This attribute represents the number of PTP packets received for this clock."
    	::= {docsRphyPtpCcapClockStatus 4 }

docsRphyPtpCcapClockStatusCounterDiscontinuityTime OBJECT-TYPE
    	SYNTAX        	DateAndTime
	MAX-ACCESS    	read-only
    	STATUS        	current
    	DESCRIPTION
        		"This attribute reports the date and time at which any
                         one or more of the counters in this group were created or
                         last reset to zero. If the RPD does not acquire time of day
                         it can report an initial CounterDiscontinuityTime of Jan 1 1970. 
                         If the value returned by the RPD is the initial Epoch of Jan 1 1970, 
                         the CCAP Core can convert this value to the real time of day based
                         on a calculation using the RPD's reported sysUpTime."
    	::= {docsRphyPtpCcapClockStatus 5 }

-- ---------------------------------------------------------
-- Port Status Table 
-- ---------------------------------------------------------

docsRphyPtpCcapCorePtpPortStatusTable OBJECT-TYPE
    SYNTAX         SEQUENCE OF DocsRphyPtpCcapCorePtpPortStatusEntry
    MAX-ACCESS     not-accessible
    STATUS         current
    DESCRIPTION
        "CorePtpCoreStatus is an instantiation of the abstract class PtpPortStatus and inherits those common attributes"
    ::={docsRphyPtpCcapMibObjects 7 }

docsRphyPtpCcapCorePtpPortStatusEntry OBJECT-TYPE
    SYNTAX        DocsRphyPtpCcapCorePtpPortStatusEntry
    MAX-ACCESS    not-accessible
    STATUS        current
    DESCRIPTION
        "The conceptual row of docsRphyPtpCcapCorePtpPortStatusTable ."
    INDEX        {docsRphyPtpCcapCorePtpPortStatusPortNumber }
    ::= {docsRphyPtpCcapCorePtpPortStatusTable 1}

DocsRphyPtpCcapCorePtpPortStatusEntry ::= SEQUENCE
                                       {
				         docsRphyPtpCcapCorePtpPortStatusPortNumber		        Unsigned32,
                                         docsRphyPtpCcapCorePtpPortStatusPacketsSent 		        Counter64,
                                         docsRphyPtpCcapCorePtpPortStatusPacketsReceived		Counter64,
                                         docsRphyPtpCcapCorePtpPortStatusCounterDiscontinuityTime	DateAndTime
                                       }

docsRphyPtpCcapCorePtpPortStatusPortNumber  OBJECT-TYPE
    	SYNTAX        Unsigned32 (0..65535)        
    	MAX-ACCESS    not-accessible
    	STATUS        current
    	DESCRIPTION
       		"This key attribute is the port number of the local clock port."
    	::= {docsRphyPtpCcapCorePtpPortStatusEntry 1 }

docsRphyPtpCcapCorePtpPortStatusPacketsSent OBJECT-TYPE
    	SYNTAX        Counter64
    	UNITS         "Packets"
    	MAX-ACCESS    read-only
    	STATUS            current
    	DESCRIPTION
       		"This attribute represents the number of PTP packets sent for this clock port."
    	::= {docsRphyPtpCcapCorePtpPortStatusEntry 2 }

docsRphyPtpCcapCorePtpPortStatusPacketsReceived OBJECT-TYPE
    	SYNTAX        Counter64
    	UNITS         "Packets"
    	MAX-ACCESS    read-only
    	STATUS            current
    	DESCRIPTION
       		"This attribute represents the number of PTP packets received for this clock port."
    	::= {docsRphyPtpCcapCorePtpPortStatusEntry 3 }

docsRphyPtpCcapCorePtpPortStatusCounterDiscontinuityTime OBJECT-TYPE
    	SYNTAX        DateAndTime 
    	MAX-ACCESS    read-only
    	STATUS        current
    	DESCRIPTION
        		"This attribute reports the date and time at which any
                         one or more of the counters in this group were created or
                         last reset to zero. If the RPD does not acquire time of day
                         it can report an initial CounterDiscontinuityTime of Jan 1 1970. 
                         If the value returned by the RPD is the initial Epoch of Jan 1 1970, 
                         the CCAP Core can convert this value to the real time of day based
                         on a calculation using the RPD's reported sysUpTime."
    	::= {docsRphyPtpCcapCorePtpPortStatusEntry 4 }

-- ---------------------------------------------------------------------
-- PortMasterClockStatus Table
-- ---------------------------------------------------------------------

docsRphyPtpCcapPortMasterClockStatusTable OBJECT-TYPE
        	SYNTAX        	SEQUENCE OF DocsRphyPtpCcapPortMasterClockStatusEntry
        	MAX-ACCESS         	not-accessible
        	STATUS             	current
        	DESCRIPTION
              "This table contains Port MasterClock Status attributes."
        	::={docsRphyPtpCcapMibObjects 8 }

docsRphyPtpCcapPortMasterClockStatusEntry OBJECT-TYPE
   	SYNTAX    	DocsRphyPtpCcapPortMasterClockStatusEntry       
   	MAX-ACCESS    	not-accessible
   	STATUS       	current
   	DESCRIPTION
      		"The conceptual row of docsRphyPtpCcapPortMasterClockStatusTable."
   	INDEX       {docsRphyPtpCcapCorePtpPortStatusPortNumber, docsRphyPtpCcapPortMasterClockStatusMasterPriority}
   	::= {docsRphyPtpCcapPortMasterClockStatusTable 1}

DocsRphyPtpCcapPortMasterClockStatusEntry ::= SEQUENCE
{
	docsRphyPtpCcapPortMasterClockStatusMasterPriority         		Unsigned32,
	docsRphyPtpCcapPortMasterClockStatusPacketsSent            		Counter64,
	docsRphyPtpCcapPortMasterClockStatusPacketsReceived        		Counter64,
	docsRphyPtpCcapPortMasterClockStatusMasterClockId        		OCTET STRING,
	docsRphyPtpCcapPortMasterClockStatusMasterClockPortNumber   		Unsigned32,
	docsRphyPtpCcapPortMasterClockStatusTwoStepFlag            		TruthValue,
	docsRphyPtpCcapPortMasterClockStatusIsBmc            			TruthValue,
	docsRphyPtpCcapPortMasterClockStatusIsMasterConnected       		TruthValue,
	docsRphyPtpCcapPortMasterClockStatusStatusDomain        		Unsigned32, 
	docsRphyPtpCcapPortMasterClockStatusFreqOffset            		Unsigned32, 
	docsRphyPtpCcapPortMasterClockStatusCounterDiscontinuityTime    	DateAndTime,
	docsRphyPtpCcapPortMasterClockStatusGmClockIdentity     		OCTET STRING,
	docsRphyPtpCcapPortMasterClockStatusGmPriority1         		Integer32,
	docsRphyPtpCcapPortMasterClockStatusGmPriority2         		Integer32,
	docsRphyPtpCcapPortMasterClockStatusGmQualityClass   			Integer32,
	docsRphyPtpCcapPortMasterClockStatusGmQualityAccuracy   		Integer32,
	docsRphyPtpCcapPortMasterClockStatusGmQualityOffset     		Integer32,
	docsRphyPtpCcapPortMasterClockStatusGmStepsRemoved      		Integer32

}

docsRphyPtpCcapPortMasterClockStatusMasterPriority OBJECT-TYPE
   	SYNTAX          Unsigned32 (1..5)    
   	MAX-ACCESS    	not-accessible
   	STATUS       	current
   	DESCRIPTION
      		"This key attribute is the priority of the master clock configured for the PTP template 
		assigned to this PTP clock port. Low numbers are higher priority."
   	::= {docsRphyPtpCcapPortMasterClockStatusEntry 1 }

docsRphyPtpCcapPortMasterClockStatusPacketsSent OBJECT-TYPE
   	SYNTAX       	Counter64
   	UNITS    	"Packets" 
   	MAX-ACCESS    	read-only
   	STATUS       	current
   	DESCRIPTION
      		"This attribute represents the number of PTP packets sent to this master for this slave clock port."
   	::= {docsRphyPtpCcapPortMasterClockStatusEntry 2 }

docsRphyPtpCcapPortMasterClockStatusPacketsReceived OBJECT-TYPE
          SYNTAX       	Counter64
          UNITS    	"Packets"
	MAX-ACCESS    	read-only
   	STATUS       	current
   	DESCRIPTION
      		"This attribute represents the number of PTP packets received from this master for this slave clock port."
   	::= {docsRphyPtpCcapPortMasterClockStatusEntry 3 }

docsRphyPtpCcapPortMasterClockStatusMasterClockId OBJECT-TYPE
   	SYNTAX       	OCTET STRING(SIZE(8)) 
   	MAX-ACCESS    	read-only
   	STATUS       	current
   	DESCRIPTION
      		"This attribute specifies the clock identifier of this master clock.
                 This value is used in Best Master Clock algorithm and is populated 
                 from the Announce message received from the master clock. This value 
                 is set to ClockIdentity from the PtpDefaultDataset Object if no 
                 announce messages have been received."
   	::= {docsRphyPtpCcapPortMasterClockStatusEntry 4 } 

docsRphyPtpCcapPortMasterClockStatusMasterClockPortNumber OBJECT-TYPE
   	SYNTAX       	Unsigned32 (0..65535)
   	MAX-ACCESS    	read-only
   	STATUS       	current
   	DESCRIPTION
      		"This attribute specifies master clock's port number."
   	::= {docsRphyPtpCcapPortMasterClockStatusEntry 5 }

docsRphyPtpCcapPortMasterClockStatusTwoStepFlag OBJECT-TYPE
   	SYNTAX       	TruthValue 
   	MAX-ACCESS    	read-only
   	STATUS       	current
   	DESCRIPTION
      		"This attribute specifies whether the Two Step process is used (i.e., 
                 the clock is a two-step clock)."
   	::= {docsRphyPtpCcapPortMasterClockStatusEntry 6 }

docsRphyPtpCcapPortMasterClockStatusIsBmc OBJECT-TYPE
   	SYNTAX  	TruthValue     
   	MAX-ACCESS    	read-only
   	STATUS       	current
  	DESCRIPTION
      		"This attribute represents whether or not this master is the current 
                 Best Master Clock (i.e., the master clock currently in use for this 
                 slave clock)."
   	::= {docsRphyPtpCcapPortMasterClockStatusEntry 7 }

docsRphyPtpCcapPortMasterClockStatusIsMasterConnected OBJECT-TYPE
   	SYNTAX       	TruthValue
   	MAX-ACCESS    	read-only
   	STATUS       	current
   	DESCRIPTION
      		"This attribute is set to TRUE if a signaling session with the master 
                 is successfully established. When a slave node receives an announce 
                 and a sync message from the master, the CCAP Core SHOULD consider 
		 the session to be successfully established."
   	::= {docsRphyPtpCcapPortMasterClockStatusEntry 8 }


docsRphyPtpCcapPortMasterClockStatusStatusDomain OBJECT-TYPE
   	SYNTAX       	Unsigned32 
   	MAX-ACCESS    	read-only
   	STATUS       	current
   	DESCRIPTION
      		"This attribute is the PTP master domain."
   	::= {docsRphyPtpCcapPortMasterClockStatusEntry 9 }

docsRphyPtpCcapPortMasterClockStatusFreqOffset OBJECT-TYPE
   	SYNTAX       	Unsigned32
   	UNITS    	"PPM"
	MAX-ACCESS    	read-only
   	STATUS       	current
   	DESCRIPTION
      		"This attribute specifies the frequency offset that the locking algorithm 
		computed per master in the last 60 sec interval.  0xFFFFFFFF means offset unknown."
   	::= {docsRphyPtpCcapPortMasterClockStatusEntry 10 }

docsRphyPtpCcapPortMasterClockStatusCounterDiscontinuityTime OBJECT-TYPE
   	SYNTAX       	DateAndTime 
   	MAX-ACCESS    	read-only
   	STATUS       	current
   	DESCRIPTION
        		"This attribute reports the date and time at which any
                         one or more of the counters in this group were created or
                         last reset to zero. If the RPD does not acquire time of day
                         it can report an initial CounterDiscontinuityTime of Jan 1 1970. 
                         If the value returned by the RPD is the initial Epoch of Jan 1 1970, 
                         the CCAP Core can convert this value to the real time of day based
                         on a calculation using the RPD's reported sysUpTime."
	    ::= {docsRphyPtpCcapPortMasterClockStatusEntry 11 }

docsRphyPtpCcapPortMasterClockStatusGmClockIdentity OBJECT-TYPE
	SYNTAX  OCTET STRING(SIZE(8))
	MAX-ACCESS  read-only
	STATUS  current
	DESCRIPTION
	    "This attribute represents the clock Identity of the grandmaster
             clock. This value is used in Best Master Clock algorithm and
             is populated from the Announce message received from the 
             master clock. This value is set to ClockIdentity from the 
             PtpDefaultDataset Object if no announce messages have been
             received."
	::= { docsRphyPtpCcapPortMasterClockStatusEntry 12 }



docsRphyPtpCcapPortMasterClockStatusGmPriority1 OBJECT-TYPE
	SYNTAX  Integer32 (0..255)
	MAX-ACCESS  read-only
	STATUS  current
	DESCRIPTION
	    "This attribute represents the priority1 of the grandmaster
             clock. Lower values take precedence. This value is used in
             Best Master Clock algorithm and is populated from the Announce
             message received from the master clock. This value is set to
             Priority1 from the PtpDefaultDataset Object if no announce
             messages have been received."
	::= { docsRphyPtpCcapPortMasterClockStatusEntry 13 }



docsRphyPtpCcapPortMasterClockStatusGmPriority2 OBJECT-TYPE
	SYNTAX  Integer32 (0..255)
	MAX-ACCESS  read-only
	STATUS  current
	DESCRIPTION
	    "This attribute represents the priority2 of the grandmaster
             clock. Lower values take precedence. This value is used in
             Best Master Clock algorithm and is populated from the Announce
             message received from the master clock. This value is set to
             Priority2 from the PtpDefaultDataset Object if no announce
             messages have been received."
	::= { docsRphyPtpCcapPortMasterClockStatusEntry 14 }



docsRphyPtpCcapPortMasterClockStatusGmQualityClass OBJECT-TYPE
	SYNTAX  Integer32 (0..255)
	MAX-ACCESS  read-only
	STATUS  current
	DESCRIPTION
	    "This attribute is the clock class for the grandmaster clock.
             The clock class attribute of an ordinary or boundary clock 
             denotes the traceability of the time or frequency distributed
             by the grandmaster clock. See section 7.6.2.4 in [IEEE 1588].
             This value is used in Best Master Clock algorithm and is
             populated from the Announce message received from the master
             clock. This value is set to QualityClass from the 
             PtpDefaultDataset Object if no announce messages have 
             been received."
	::= { docsRphyPtpCcapPortMasterClockStatusEntry 15 }


docsRphyPtpCcapPortMasterClockStatusGmQualityAccuracy OBJECT-TYPE
	SYNTAX  Integer32 (0..255)
	MAX-ACCESS  read-only
	STATUS  current
	DESCRIPTION
	    "This attribute characterizes the grandmaster clock for the
             purpose of the best master clock (BMC) algorithm. See 
             section 7.6.2.5 in [IEEE 1588]. This value is used in 
             Best Master Clock algorithm and is populated from the 
             Announce message received from the master clock. This 
             value is set to QualityAccuracy from the PtpDefaultDataset
             Object if no announce messages have been received."
	::= { docsRphyPtpCcapPortMasterClockStatusEntry 16 }


docsRphyPtpCcapPortMasterClockStatusGmQualityOffset OBJECT-TYPE
	SYNTAX  Integer32 (0..65535)
	MAX-ACCESS  read-only
	STATUS  current
	DESCRIPTION
	    "This attribute represents the offset, scaled, logarithmic
             representation of the grandmaster clock variance. 
             See Section 7.6.3.5 in [IEEE 1588]. This value is used in 
             Best Master Clock algorithm and is populated from the Announce 
             message received from the master clock. This value is set to 
             QualityOffset from the PtpDefaultDataset Object if no announce
             messages have been received."
	::= { docsRphyPtpCcapPortMasterClockStatusEntry 17 }


docsRphyPtpCcapPortMasterClockStatusGmStepsRemoved OBJECT-TYPE
	SYNTAX  Integer32
	MAX-ACCESS  read-only
	STATUS  current
	DESCRIPTION
	    "This attribute is the number of communication paths traversed
             between the local clock and the grandmaster clock. This value
             is used in Best Master Clock algorithm and is populated from
             the Announce message received from the master clock. 
             This value is set to zero if no announce messages have been received."
	::= { docsRphyPtpCcapPortMasterClockStatusEntry 18 }
-- ---------------------------------------------------------------------
-- CCAP Core RPD Group Objects
-- ---------------------------------------------------------------------	

-- ---------------------------------------------------------------------
-- RPD Current DataSet Table
-- ---------------------------------------------------------------------
docsRphyPtpRpdCurrentDataSetTable OBJECT-TYPE
     	SYNTAX 		SEQUENCE OF DocsRphyPtpRpdCurrentDataSetEntry
     	MAX-ACCESS         	not-accessible
     	STATUS             	current
     	DESCRIPTION
		"See section 8.2.5 in [IEEE 1588] for details of the 1588 port dataset."
     	::={docsRphyPtpRpdMibObjects 1} 

docsRphyPtpRpdCurrentDataSetEntry OBJECT-TYPE
	SYNTAX		DocsRphyPtpRpdCurrentDataSetEntry
	MAX-ACCESS	not-accessible
	STATUS		current
	DESCRIPTION
		"The conceptual row of docsRphyPtpRpdCurrentDataSetTable."
	INDEX		{docsRphyRpdDevInfoUniqueId}
	::= {docsRphyPtpRpdCurrentDataSetTable 1}

DocsRphyPtpRpdCurrentDataSetEntry ::= SEQUENCE
			{
			docsRphyPtpRpdCurrentDataSetStepsRemoved Unsigned32,
			docsRphyPtpRpdCurrentDataSetOffsetFromMaster Integer32,
			docsRphyPtpRpdCurrentDataSetMeanPathDelay Unsigned32
			}

docsRphyPtpRpdCurrentDataSetStepsRemoved OBJECT-TYPE     
     SYNTAX      Unsigned32
     UNITS       "steps"
     MAX-ACCESS  read-only      
     STATUS      current
     DESCRIPTION
	"This attribute is the number of communication paths traversed between the 
          local clock and the grandmaster clock. The initialization value is 0."
     ::= {docsRphyPtpRpdCurrentDataSetEntry 1}

docsRphyPtpRpdCurrentDataSetOffsetFromMaster OBJECT-TYPE 
     SYNTAX      Integer32
     UNITS       "Nanoseconds"
     MAX-ACCESS  read-only      
     STATUS      current
     DESCRIPTION
	"This attribute is an implementation-specific representation of the current
          value of the time difference between a master and a slave as computed by 
          the slave."
     ::= {docsRphyPtpRpdCurrentDataSetEntry 2}

docsRphyPtpRpdCurrentDataSetMeanPathDelay OBJECT-TYPE    
     SYNTAX      Unsigned32
     UNITS       "Nanoseconds"
     MAX-ACCESS  read-only      
     STATUS      current
     DESCRIPTION
	"This attribute is an implementation-specific representation of the current
          value of the mean propagation time between a master and slave clock as 
          computed by the slave. Zero means that the path delay is unavailable."
     ::= {docsRphyPtpRpdCurrentDataSetEntry 3}

-- ---------------------------------------------------------------------
-- RPD Clock Status Table
-- ---------------------------------------------------------------------

docsRphyPtpRpdClockStatusTable OBJECT-TYPE
     	SYNTAX 		SEQUENCE OF DocsRphyPtpRpdClockStatusEntry
     	MAX-ACCESS         	not-accessible
     	STATUS             	current
     	DESCRIPTION
		"See section 8.2.5 in [IEEE 1588] for details of the 1588 port dataset."
     	::={docsRphyPtpRpdMibObjects 2} 

docsRphyPtpRpdClockStatusEntry OBJECT-TYPE
	SYNTAX		DocsRphyPtpRpdClockStatusEntry
	MAX-ACCESS	not-accessible
	STATUS		current
	DESCRIPTION
		"The conceptual row of docsRphyPtpRpdClockStatusTable."
	INDEX		{docsRphyRpdDevInfoUniqueId}
	::= {docsRphyPtpRpdClockStatusTable 1}

DocsRphyPtpRpdClockStatusEntry ::= SEQUENCE
		{
		docsRphyPtpRpdClockStatusClockState          	INTEGER,
		docsRphyPtpRpdClockStatusLastStateChange        TimeTicks,
		docsRphyPtpRpdClockStatusPacketsSent        	Counter64,
		docsRphyPtpRpdClockStatusPacketsReceived       	Counter64,
		docsRphyPtpRpdClockStatusCounterDiscontinuityTime DateAndTime
		}

docsRphyPtpRpdClockStatusClockState   OBJECT-TYPE
    	SYNTAX        	INTEGER { 
			freerun(1),
			holdover(2),
			acquiring(3),
			freqLocked(4),
			phaseAligned(5)
      			}
	MAX-ACCESS    	read-only
    	STATUS        	current
    	DESCRIPTION
        		"This attribute represents the current state of the clock."
    	::= {docsRphyPtpRpdClockStatusEntry 1 }

docsRphyPtpRpdClockStatusLastStateChange OBJECT-TYPE
    	SYNTAX        	TimeTicks        
	MAX-ACCESS    	read-only
    	STATUS        	current
    	DESCRIPTION
        		"This attribute represents the value in TimeTicks when the clock state last changed."
    	::= {docsRphyPtpRpdClockStatusEntry 2 }

docsRphyPtpRpdClockStatusPacketsSent OBJECT-TYPE
    	SYNTAX        	Counter64
	UNITS           "Packets"
	MAX-ACCESS    	read-only
    	STATUS        	current
    	DESCRIPTION
        		"This attribute represents the number of PTP packets sent for this clock."
    	::= {docsRphyPtpRpdClockStatusEntry 3 }

docsRphyPtpRpdClockStatusPacketsReceived OBJECT-TYPE
    	SYNTAX        	Counter64
	UNITS           "Packets"
	MAX-ACCESS    	read-only
    	STATUS        	current
    	DESCRIPTION
        		"This attribute represents the number of PTP packets received for this clock."
    	::= {docsRphyPtpRpdClockStatusEntry 4 }

docsRphyPtpRpdClockStatusCounterDiscontinuityTime OBJECT-TYPE
    	SYNTAX        	DateAndTime
	MAX-ACCESS    	read-only
    	STATUS        	current
    	DESCRIPTION
        		"This attribute reports the date and time at which any
                         one or more of the counters in this group were created or
                         last reset to zero. If the RPD does not acquire time of day
                         it can report an initial CounterDiscontinuityTime of Jan 1 1970. 
                         If the value returned by the RPD is the initial Epoch of Jan 1 1970, 
                         the CCAP Core can convert this value to the real time of day based
                         on a calculation using the RPD's reported sysUpTime."
    	::= {docsRphyPtpRpdClockStatusEntry 5 }

-- ---------------------------------------------------------------------
-- RPD Port Data Set Table
-- ---------------------------------------------------------------------

docsRphyPtpRpdPortDataSetTable OBJECT-TYPE
     	SYNTAX 		SEQUENCE OF DocsRphyPtpRpdPortDataSetEntry
     	MAX-ACCESS         	not-accessible
     	STATUS             	current
     	DESCRIPTION
		"See section 8.2.5 in [IEEE 1588] for details of the 1588 port dataset."
     	::={docsRphyPtpRpdMibObjects 3} 

docsRphyPtpRpdPortDataSetEntry OBJECT-TYPE
	SYNTAX		DocsRphyPtpRpdPortDataSetEntry
	MAX-ACCESS	not-accessible
	STATUS		current
	DESCRIPTION
		"The conceptual row of docsRphyPtpRpdPortDataSetTable."
	INDEX		{docsRphyRpdDevInfoUniqueId ,docsRphyPtpRpdPortDataSetPortNumber}
	::= {docsRphyPtpRpdPortDataSetTable 1}

DocsRphyPtpRpdPortDataSetEntry ::= SEQUENCE
	{
	docsRphyPtpRpdPortDataSetPortNumber	Unsigned32,
	docsRphyPtpRpdPortDataSetPortState	Unsigned32,
	docsRphyPtpRpdPortDataSetMeanPathDelay	Integer32
	}

docsRphyPtpRpdPortDataSetPortNumber OBJECT-TYPE
	SYNTAX		Unsigned32 (0..65535)
	MAX-ACCESS	not-accessible
	STATUS		current
	DESCRIPTION
		"This key attribute is the port number of the local clock port. 
		Port numbers 0 and 65,535 are reserved and cannot be used for real clock ports. 
		See [IEEE 1588] for more information. When a PTP clock has N ports, 
		the CCAP Core MUST set the port number to a value in the interval 1..N."
	
	::= {docsRphyPtpRpdPortDataSetEntry 1}

docsRphyPtpRpdPortDataSetPortState OBJECT-TYPE
	SYNTAX		Unsigned32 (0..255)
	MAX-ACCESS	read-only
	STATUS		current
	DESCRIPTION
		"This attribute is the state of this PTP clock port. See Table 8 in [IEEE 1588]."
	
	::= {docsRphyPtpRpdPortDataSetEntry 2}

docsRphyPtpRpdPortDataSetMeanPathDelay OBJECT-TYPE
	SYNTAX		Integer32
	MAX-ACCESS	read-only
	STATUS		current
	DESCRIPTION
		"This attribute is an implementation-specific representation of the current 
		value of the mean propagation time between a master and slave clock as computed 
		by the slave. Zero means that the path delay is unavailable."
	::= {docsRphyPtpRpdPortDataSetEntry 3}

-- ---------------------------------------------------------
-- RPD Port Status Table 
-- ---------------------------------------------------------

docsRphyPtpRpdPtpPortStatusTable OBJECT-TYPE
    SYNTAX         SEQUENCE OF DocsRphyPtpRpdPtpPortStatusEntry
    MAX-ACCESS     not-accessible
    STATUS         current
    DESCRIPTION
        "Port Ptp Status is an instantiation of the abstract class PtpPortStatus and inherits those common attributes"
    ::={docsRphyPtpRpdMibObjects 4 }

docsRphyPtpRpdPtpPortStatusEntry OBJECT-TYPE
    SYNTAX        DocsRphyPtpRpdPtpPortStatusEntry
    MAX-ACCESS    not-accessible
    STATUS        current
    DESCRIPTION
        "The conceptual row of docsRphyPtpRpdCorePtpPortStatusTable ."
    INDEX        {
               docsRphyRpdDevInfoUniqueId,
               docsRphyPtpRpdPtpPortStatusRpdEnetPortIndex,
               docsRphyPtpRpdPtpPortStatusRpdPtpPortIndex

             }
    ::= {docsRphyPtpRpdPtpPortStatusTable 1}


DocsRphyPtpRpdPtpPortStatusEntry ::= SEQUENCE
                                       {
  				docsRphyPtpRpdPtpPortStatusRpdEnetPortIndex       	Unsigned32,
               			docsRphyPtpRpdPtpPortStatusRpdPtpPortIndex 		Unsigned32,
                                docsRphyPtpRpdPtpPortStatusPacketsSent 		        Counter64,
                                docsRphyPtpRpdPtpPortStatusPacketsReceived		Counter64,
                                docsRphyPtpRpdPtpPortStatusCounterDiscontinuityTime	DateAndTime
                                       }


docsRphyPtpRpdPtpPortStatusRpdEnetPortIndex  OBJECT-TYPE
    	SYNTAX        Unsigned32 (0..255)        
    	MAX-ACCESS    not-accessible
    	STATUS        current
    	DESCRIPTION
       		"This key attribute is the RPD's Ethernet port 
                 used for this PTP clock port. If not set, any RPD 
                 Ethernet port may be used for this PTP clock port. "
    	::= {docsRphyPtpRpdPtpPortStatusEntry 1 }

docsRphyPtpRpdPtpPortStatusRpdPtpPortIndex  OBJECT-TYPE
    	SYNTAX        Unsigned32 (0..255)        
    	MAX-ACCESS    not-accessible
    	STATUS        current
    	DESCRIPTION
       		"This key attribute is the port number of the local clock port."
    	::= {docsRphyPtpRpdPtpPortStatusEntry 2 }

docsRphyPtpRpdPtpPortStatusPacketsSent OBJECT-TYPE
    	SYNTAX        Counter64
    	UNITS         "Packets"
    	MAX-ACCESS    read-only
    	STATUS            current
    	DESCRIPTION
       		"This attribute represents the number of PTP packets sent for this clock port."
    	::= {docsRphyPtpRpdPtpPortStatusEntry 3 }

docsRphyPtpRpdPtpPortStatusPacketsReceived OBJECT-TYPE
    	SYNTAX        Counter64
    	UNITS         "Packets"
    	MAX-ACCESS    read-only
    	STATUS            current
    	DESCRIPTION
       		"This attribute represents the number of PTP packets received for this clock port."
    	::= {docsRphyPtpRpdPtpPortStatusEntry 4 }

docsRphyPtpRpdPtpPortStatusCounterDiscontinuityTime OBJECT-TYPE
    	SYNTAX        DateAndTime
    	MAX-ACCESS    read-only
    	STATUS        current
    	DESCRIPTION
        		"This attribute reports the date and time at which any
                         one or more of the counters in this group were created or
                         last reset to zero. If the RPD does not acquire time of day
                         it can report an initial CounterDiscontinuityTime of Jan 1 1970. 
                         If the value returned by the RPD is the initial Epoch of Jan 1 1970, 
                         the CCAP Core can convert this value to the real time of day based
                         on a calculation using the RPD's reported sysUpTime."
    	::= {docsRphyPtpRpdPtpPortStatusEntry 5 }

-- ---------------------------------------------------------------------
-- RPD PortMasterClockStatus Table
-- ---------------------------------------------------------------------

docsRphyPtpRpdPortMasterClockStatusTable OBJECT-TYPE
        	SYNTAX        	SEQUENCE OF DocsRphyPtpRpdPortMasterClockStatusEntry
        	MAX-ACCESS         	not-accessible
        	STATUS             	current
        	DESCRIPTION
              "This table contains Port MasterClock Status attributes."
        	::={docsRphyPtpRpdMibObjects 5 }

docsRphyPtpRpdPortMasterClockStatusEntry OBJECT-TYPE
   	SYNTAX    	DocsRphyPtpRpdPortMasterClockStatusEntry       
   	MAX-ACCESS    	not-accessible
   	STATUS       	current
   	DESCRIPTION
      		"The conceptual row of docsRphyPtpRpdPortMasterClockStatusTable."
        INDEX       {
               docsRphyRpdDevInfoUniqueId,
	     docsRphyPtpRpdPtpPortStatusRpdEnetPortIndex,
	     docsRphyPtpRpdPtpPortStatusRpdPtpPortIndex,               
	     docsRphyPtpRpdPortMasterClockStatusMasterPriority           
             }
   	::= {docsRphyPtpRpdPortMasterClockStatusTable 1}


DocsRphyPtpRpdPortMasterClockStatusEntry ::= SEQUENCE
		{
		docsRphyPtpRpdPortMasterClockStatusMasterPriority         		Unsigned32,
		docsRphyPtpRpdPortMasterClockStatusPacketsSent            		Counter64,
		docsRphyPtpRpdPortMasterClockStatusPacketsReceived        		Counter64,
		docsRphyPtpRpdPortMasterClockStatusMasterClockId        		OCTET STRING,
		docsRphyPtpRpdPortMasterClockStatusMasterClockPortNumber   		Unsigned32,
		docsRphyPtpRpdPortMasterClockStatusTwoStepFlag            		TruthValue,
		docsRphyPtpRpdPortMasterClockStatusIsBmc            		        TruthValue,
		docsRphyPtpRpdPortMasterClockStatusIsMasterConnected       		TruthValue,
		docsRphyPtpRpdPortMasterClockStatusStatusDomain        		        Unsigned32, 
		docsRphyPtpRpdPortMasterClockStatusFreqOffset            		Unsigned32, 
		docsRphyPtpRpdPortMasterClockStatusCounterDiscontinuityTime    	        DateAndTime,
                docsRphyPtpRpdPortMasterClockStatusGmClockIdentity                      OCTET STRING,
                docsRphyPtpRpdPortMasterClockStatusGmPriority1                          Integer32,
                docsRphyPtpRpdPortMasterClockStatusGmPriority2                          Integer32,
                docsRphyPtpRpdPortMasterClockStatusGmQualityClass                       Integer32,
                docsRphyPtpRpdPortMasterClockStatusGmQualityAccuracy                    Integer32,
                docsRphyPtpRpdPortMasterClockStatusGmQualityOffset                      Integer32,
                docsRphyPtpRpdPortMasterClockStatusGmStepsRemoved                       Integer32
		}

docsRphyPtpRpdPortMasterClockStatusMasterPriority OBJECT-TYPE
   	SYNTAX  		Unsigned32 (1..5)    
   	MAX-ACCESS    	not-accessible
   	STATUS       	current
   	DESCRIPTION
      		"This key attribute is the priority of the master clock configured for the PTP template 
		assigned to this PTP clock port. Low numbers are higher priority."
   	::= {docsRphyPtpRpdPortMasterClockStatusEntry 1 }

docsRphyPtpRpdPortMasterClockStatusPacketsSent OBJECT-TYPE
   	SYNTAX       	Counter64
   	UNITS    		"Packets" 
   	MAX-ACCESS    	read-only
   	STATUS       	current
   	DESCRIPTION
      		"This attribute represents the number of PTP packets sent to this master for this slave clock port."
   	::= {docsRphyPtpRpdPortMasterClockStatusEntry 2 }

docsRphyPtpRpdPortMasterClockStatusPacketsReceived OBJECT-TYPE
   	SYNTAX       	Counter64
   	UNITS    		"Packets"
	MAX-ACCESS    	read-only
   	STATUS       	current
   	DESCRIPTION
      		"This attribute represents the number of PTP packets received from this master for this slave clock port."
   	::= {docsRphyPtpRpdPortMasterClockStatusEntry 3 }

docsRphyPtpRpdPortMasterClockStatusMasterClockId OBJECT-TYPE
   	SYNTAX       	OCTET STRING(SIZE(8)) 
   	MAX-ACCESS    	read-only
   	STATUS       	current
   	DESCRIPTION
      		"This attribute specifies the clock identifier of this master clock."
   	::= {docsRphyPtpRpdPortMasterClockStatusEntry 4 } 

docsRphyPtpRpdPortMasterClockStatusMasterClockPortNumber OBJECT-TYPE
   	SYNTAX       	Unsigned32 (0..65535)
   	MAX-ACCESS    	read-only
   	STATUS       	current
   	DESCRIPTION
      		"This attribute specifies master clock's port number."
   	::= {docsRphyPtpRpdPortMasterClockStatusEntry 5 }

docsRphyPtpRpdPortMasterClockStatusTwoStepFlag OBJECT-TYPE
   	SYNTAX       	TruthValue 
   	MAX-ACCESS    	read-only
   	STATUS       	current
   	DESCRIPTION
      		"This attribute specifies whether the Two Step process is used (i.e., the clock is a two-step clock)."
   	::= {docsRphyPtpRpdPortMasterClockStatusEntry 6 }

docsRphyPtpRpdPortMasterClockStatusIsBmc OBJECT-TYPE
   	SYNTAX  		TruthValue     
   	MAX-ACCESS    	read-only
   	STATUS       	current
  	DESCRIPTION
      		"This attribute represents whether or not this master is the current Best Master Clock (i.e., 
		the master clock currently in use for this slave clock)."
   	::= {docsRphyPtpRpdPortMasterClockStatusEntry 7 }

docsRphyPtpRpdPortMasterClockStatusIsMasterConnected OBJECT-TYPE
   	SYNTAX       	TruthValue
   	MAX-ACCESS    	read-only
   	STATUS       	current
   	DESCRIPTION
      		"This attribute is set to TRUE if a signaling session with the master is successfully established. 
		When a slave node receives an announce and a sync message from the master, the CCAP Core SHOULD consider 
		the session to be successfully established."
   	::= {docsRphyPtpRpdPortMasterClockStatusEntry 8 }

docsRphyPtpRpdPortMasterClockStatusStatusDomain OBJECT-TYPE
   	SYNTAX       	Unsigned32 
   	MAX-ACCESS    	read-only
   	STATUS       	current
   	DESCRIPTION
      		"This attribute is the PTP master domain."
   	::= {docsRphyPtpRpdPortMasterClockStatusEntry 9 }

docsRphyPtpRpdPortMasterClockStatusFreqOffset OBJECT-TYPE
   	SYNTAX       	Unsigned32  -- Last 60 second interval
   	UNITS    		"PPM"
	MAX-ACCESS    	read-only
   	STATUS       	current
   	DESCRIPTION
      		"This attribute specifies the frequency offset that the locking algorithm 
		computed per master in the last 60 sec interval.  0xFFFFFFFF means offset unknown."
   	::= {docsRphyPtpRpdPortMasterClockStatusEntry 10 }

docsRphyPtpRpdPortMasterClockStatusCounterDiscontinuityTime OBJECT-TYPE
   	SYNTAX       	DateAndTime
   	MAX-ACCESS    	read-only
   	STATUS       	current
   	DESCRIPTION
        		"This attribute reports the date and time at which any
                         one or more of the counters in this group were created or
                         last reset to zero. If the RPD does not acquire time of day
                         it can report an initial CounterDiscontinuityTime of Jan 1 1970. 
                         If the value returned by the RPD is the initial Epoch of Jan 1 1970, 
                         the CCAP Core can convert this value to the real time of day based
                         on a calculation using the RPD's reported sysUpTime."
   	::= {docsRphyPtpRpdPortMasterClockStatusEntry 11 }

docsRphyPtpRpdPortMasterClockStatusGmClockIdentity OBJECT-TYPE
	SYNTAX  OCTET STRING(SIZE(8))
	MAX-ACCESS  read-only
	STATUS  current
	DESCRIPTION
	    "This attribute represents the clock Identity of the grandmaster
             clock. This value is used in Best Master Clock algorithm and
             is populated from the Announce message received from the 
             master clock. This value is set to ClockIdentity from the 
             PtpDefaultDataset Object if no announce messages have been
             received."
	::= { docsRphyPtpRpdPortMasterClockStatusEntry 12 }

docsRphyPtpRpdPortMasterClockStatusGmPriority1 OBJECT-TYPE
	SYNTAX  Integer32 (0..255)
	MAX-ACCESS  read-only
	STATUS  current
	DESCRIPTION
	    "This attribute represents the priority1 of the grandmaster
             clock. Lower values take precedence. This value is used in
             Best Master Clock algorithm and is populated from the Announce
             message received from the master clock. This value is set to
             Priority1 from the PtpDefaultDataset Object if no announce
             messages have been received."
	::= { docsRphyPtpRpdPortMasterClockStatusEntry 13 }

docsRphyPtpRpdPortMasterClockStatusGmPriority2 OBJECT-TYPE
	SYNTAX  Integer32 (0..255)
	MAX-ACCESS  read-only
	STATUS  current
	DESCRIPTION
	    "This attribute represents the priority2 of the grandmaster
             clock. Lower values take precedence. This value is used in
             Best Master Clock algorithm and is populated from the Announce
             message received from the master clock. This value is set to
             Priority2 from the PtpDefaultDataset Object if no announce
             messages have been received."
	::= { docsRphyPtpRpdPortMasterClockStatusEntry 14 }

docsRphyPtpRpdPortMasterClockStatusGmQualityClass OBJECT-TYPE
	SYNTAX  Integer32 (0..255)
	MAX-ACCESS  read-only
	STATUS  current
	DESCRIPTION
	    "This attribute is the clock class for the grandmaster clock.
             The clock class attribute of an ordinary or boundary clock 
             denotes the traceability of the time or frequency distributed
             by the grandmaster clock. See section 7.6.2.4 in [IEEE 1588].
             This value is used in Best Master Clock algorithm and is
             populated from the Announce message received from the master
             clock. This value is set to QualityClass from the 
             PtpDefaultDataset Object if no announce messages have 
             been received."
	::= { docsRphyPtpRpdPortMasterClockStatusEntry 15 }

docsRphyPtpRpdPortMasterClockStatusGmQualityAccuracy OBJECT-TYPE
	SYNTAX  Integer32 (0..255)
	MAX-ACCESS  read-only
	STATUS  current
	DESCRIPTION
	    "This attribute characterizes the grandmaster clock for the
             purpose of the best master clock (BMC) algorithm. See 
             section 7.6.2.5 in [IEEE 1588]. This value is used in 
             Best Master Clock algorithm and is populated from the 
             Announce message received from the master clock. This 
             value is set to QualityAccuracy from the PtpDefaultDataset
             Object if no announce messages have been received."
	::= { docsRphyPtpRpdPortMasterClockStatusEntry 16 }

docsRphyPtpRpdPortMasterClockStatusGmQualityOffset OBJECT-TYPE
	SYNTAX  Integer32 (0..65535)
	MAX-ACCESS  read-only
	STATUS  current
	DESCRIPTION
	    "This attribute represents the offset, scaled, logarithmic
             representation of the grandmaster clock variance. 
             See Section 7.6.3.5 in [IEEE 1588]. This value is used in 
             Best Master Clock algorithm and is populated from the Announce 
             message received from the master clock. This value is set to 
             QualityOffset from the PtpDefaultDataset Object if no announce
             messages have been received."
	::= { docsRphyPtpRpdPortMasterClockStatusEntry 17 }

docsRphyPtpRpdPortMasterClockStatusGmStepsRemoved OBJECT-TYPE
	SYNTAX  Integer32
	MAX-ACCESS  read-only
	STATUS  current
	DESCRIPTION
	    "This attribute is the number of communication paths traversed
             between the local clock and the grandmaster clock. This value
             is used in Best Master Clock algorithm and is populated from
             the Announce message received from the master clock. 
             This value is set to zero if no announce messages have been received."
	::= { docsRphyPtpRpdPortMasterClockStatusEntry 18 }







-- ---------------------------------------------------------
-- Conformance definitions 
-- ---------------------------------------------------------

docsRphyPtpCompliance MODULE-COMPLIANCE 
     STATUS current 
     DESCRIPTION 
          "The compliance statement for CCAP Core and RPD PTP features."

MODULE -- docsRphyPtpMib
          
-- conditionally mandatory groups

GROUP docsRphyPtpRpdGroup 
        DESCRIPTION
            "Group of objects applicable to RPDs only.
            These objects are implemented on the CCAP Core
            but are derived from the RPD via the GCP protocol."

GROUP docsRphyPtpCcapCoreGroup 
        DESCRIPTION
            "Group of objects applicable to CCAP Core only."
            
-- conditionally optional groups


::= { docsRphyPtpCompliances 1}


docsRphyPtpRpdGroup OBJECT-GROUP
        OBJECTS {
          	docsRphyPtpRpdCurrentDataSetStepsRemoved,
		docsRphyPtpRpdCurrentDataSetOffsetFromMaster,
		docsRphyPtpRpdCurrentDataSetMeanPathDelay,

		docsRphyPtpRpdClockStatusClockState,
		docsRphyPtpRpdClockStatusLastStateChange,
		docsRphyPtpRpdClockStatusPacketsSent,
		docsRphyPtpRpdClockStatusPacketsReceived,
		docsRphyPtpRpdClockStatusCounterDiscontinuityTime,

		docsRphyPtpRpdPortDataSetPortState,
		docsRphyPtpRpdPortDataSetMeanPathDelay,

          	docsRphyPtpRpdPtpPortStatusPacketsSent,
          	docsRphyPtpRpdPtpPortStatusPacketsReceived,
          	docsRphyPtpRpdPtpPortStatusCounterDiscontinuityTime,

		docsRphyPtpRpdPortMasterClockStatusPacketsSent,
		docsRphyPtpRpdPortMasterClockStatusPacketsReceived,
		docsRphyPtpRpdPortMasterClockStatusMasterClockId,
		docsRphyPtpRpdPortMasterClockStatusMasterClockPortNumber,
		docsRphyPtpRpdPortMasterClockStatusTwoStepFlag,
		docsRphyPtpRpdPortMasterClockStatusIsBmc,
		docsRphyPtpRpdPortMasterClockStatusIsMasterConnected,
		docsRphyPtpRpdPortMasterClockStatusStatusDomain, 
		docsRphyPtpRpdPortMasterClockStatusFreqOffset, 
		docsRphyPtpRpdPortMasterClockStatusCounterDiscontinuityTime,
                docsRphyPtpRpdPortMasterClockStatusGmClockIdentity,
                docsRphyPtpRpdPortMasterClockStatusGmPriority1,
                docsRphyPtpRpdPortMasterClockStatusGmPriority2,
                docsRphyPtpRpdPortMasterClockStatusGmQualityClass,
                docsRphyPtpRpdPortMasterClockStatusGmQualityAccuracy,
                docsRphyPtpRpdPortMasterClockStatusGmQualityOffset,
                docsRphyPtpRpdPortMasterClockStatusGmStepsRemoved                      
        }
        STATUS      current
        DESCRIPTION
            "Group of objects implemented in CCAP Cores which
            represent RPD managed objects derived via the GCP 
            protocol."
        ::= { docsRphyPtpGroups 1 }

docsRphyPtpCcapCoreGroup OBJECT-GROUP
        OBJECTS {
                	docsRphyPtpCcapDefaultDataSetTwoStepFlag,
                	docsRphyPtpCcapDefaultDataSetClockIdentity,
			docsRphyPtpCcapDefaultDataSetPriority1,
                	docsRphyPtpCcapDefaultDataSetPriority2,
                	docsRphyPtpCcapDefaultDataSetSlaveOnly,
                	docsRphyPtpCcapDefaultDataSetQualityClass,
                	docsRphyPtpCcapDefaultDataSetQualityAccuracy,
                	docsRphyPtpCcapDefaultDataSetQualityOffset,

			docsRphyPtpCcapCurrentDataSetStepsRemoved,
                	docsRphyPtpCcapCurrentDataSetOffsetFromMaster,
                	docsRphyPtpCcapCurrentDataSetMeanPathDelay,

                	docsRphyPtpCcapParentDataSetParentClockId,
                	docsRphyPtpCcapParentDataSetParentPortNumber,
                	docsRphyPtpCcapParentDataSetParentStats,
			docsRphyPtpCcapParentDataSetClockOffset,
                	docsRphyPtpCcapParentDataSetPhaseChangeRate,
                	docsRphyPtpCcapParentDataSetGmClockIdentity,
                	docsRphyPtpCcapParentDataSetGmPriority1,
                	docsRphyPtpCcapParentDataSetGmPriority2,
                	docsRphyPtpCcapParentDataSetGmQualityClass,
                	docsRphyPtpCcapParentDataSetGmQualityAccuracy,
                	docsRphyPtpCcapParentDataSetGmQualityOffset,

                	docsRphyPtpCcapTimePropertiesCurrentUtcOffsetValid,
                	docsRphyPtpCcapTimePropertiesCurrentUtcOffset,
                	docsRphyPtpCcapTimePropertiesLeap59,
                	docsRphyPtpCcapTimePropertiesLeap61,
                	docsRphyPtpCcapTimePropertiesTimeTraceable,
                	docsRphyPtpCcapTimePropertiesFreqTraceable,
                	docsRphyPtpCcapTimePropertiesPtpTimescale,
                	docsRphyPtpCcapTimePropertiesTimeSource,

			docsRphyPtpCcapPortDataSetPortState,
			docsRphyPtpCcapPortDataSetMeanPathDelay,

			docsRphyPtpCcapClockStatusClockState,          
			docsRphyPtpCcapClockStatusLastStateChange,        
			docsRphyPtpCcapClockStatusPacketsSent,        
			docsRphyPtpCcapClockStatusPacketsReceived,             
			docsRphyPtpCcapClockStatusCounterDiscontinuityTime,    

			docsRphyPtpCcapCorePtpPortStatusPacketsSent, 
			docsRphyPtpCcapCorePtpPortStatusPacketsReceived,
			docsRphyPtpCcapCorePtpPortStatusCounterDiscontinuityTime,

			docsRphyPtpCcapPortMasterClockStatusPacketsSent,
			docsRphyPtpCcapPortMasterClockStatusPacketsReceived,
			docsRphyPtpCcapPortMasterClockStatusMasterClockId,
			docsRphyPtpCcapPortMasterClockStatusMasterClockPortNumber,
			docsRphyPtpCcapPortMasterClockStatusTwoStepFlag,
			docsRphyPtpCcapPortMasterClockStatusIsBmc,
			docsRphyPtpCcapPortMasterClockStatusIsMasterConnected,
			docsRphyPtpCcapPortMasterClockStatusStatusDomain,
			docsRphyPtpCcapPortMasterClockStatusFreqOffset,
			docsRphyPtpCcapPortMasterClockStatusCounterDiscontinuityTime,
			docsRphyPtpCcapPortMasterClockStatusGmClockIdentity, 
			docsRphyPtpCcapPortMasterClockStatusGmPriority1,         
			docsRphyPtpCcapPortMasterClockStatusGmPriority2,         
			docsRphyPtpCcapPortMasterClockStatusGmQualityClass,   
			docsRphyPtpCcapPortMasterClockStatusGmQualityAccuracy,   
			docsRphyPtpCcapPortMasterClockStatusGmQualityOffset,    
			docsRphyPtpCcapPortMasterClockStatusGmStepsRemoved 
        }
        STATUS      current
        DESCRIPTION
            "Group of objects implemented in CCAP Cores."
        ::= { docsRphyPtpGroups 2 }
        END
