DOCS-RPHY-MIB DEFINITIONS ::= BEGIN
IMPORTS
    MODULE-IDENTITY, 
    OBJECT-TYPE, 
    Unsigned32,
    Gauge32
        FROM SNMPv2-SMI 
    TruthValue, 
    MacAddress,
    TimeStamp,
    AutonomousType,
    DateAndTime,
    PhysAddress,
    DisplayString
        FROM SNMPv2-TC 
    OBJECT-GROUP, 
    MODULE-COMPLIANCE 
        FROM SNMPv2-CONF
    SnmpAdminString
        FROM SNMP-FRAMEWORK-MIB -- RFC 3411
    InetAddressType,
    InetAddress,
    InetPortNumber,
    InetVersion
        FROM INET-ADDRESS-MIB   -- RFC 4001
    UUIDorZero
        FROM UUID-TC-MIB        -- RFC 6933
    IANAPhysicalClass
        FROM IANA-ENTITY-MIB    -- RFC 6933
    IANAifType                               
        FROM IANAifType-MIB
    PhysicalIndex,
    PhysicalIndexOrZero
        FROM ENTITY-MIB         -- RFC 6933
    EntitySensorDataType,
    EntitySensorDataScale,
    EntitySensorPrecision,
    EntitySensorValue,
    EntitySensorStatus
        FROM ENTITY-SENSOR-MIB  -- RFC 3433
    IpAddressOriginTC,
    IpAddressStatusTC,
    IpAddressPrefixOriginTC,
    Ipv6AddressIfIdentifierTC
        FROM IP-MIB             -- RFC 4293
    InterfaceIndex,
    InterfaceIndexOrZero
        FROM IF-MIB
    IfDirection
        FROM DOCS-IF3-MIB
    clabProjDocsis
        FROM CLAB-DEF-MIB;


docsRphyMib MODULE-IDENTITY 
    LAST-UPDATED    "201604210000Z" -- April 21, 2016
    ORGANIZATION    "Cable Television Laboratories, Inc" 
    CONTACT-INFO 
         "
         Postal: Cable Television Laboratories, Inc. 
         400 Centennial Parkway 
         Louisville, Colorado 80027-1266 
         U.S.A. 
         Phone: +1 303-661-9100 
         Fax: +1 303-661-9199 
         E-mail: mibs@cablelabs.com" 
    DESCRIPTION 
        "This MIB module contains the management objects for
         the Remote PHY Device (RPD) management.
         Copyright 2016 Cable Television Laboratories, Inc.
         All rights reserved."
    REVISION "201604210000Z" 
    DESCRIPTION 
        "Initial version, created by R-OSSI-N-16.1461-3."
::= { clabProjDocsis 30 }


-- ---------------------------------------------------------
-- Textual Conventions
-- ---------------------------------------------------------


-- ---------------------------------------------------------------------
-- Main Groups
-- ---------------------------------------------------------------------

docsRphyMibObjects           OBJECT IDENTIFIER ::= { docsRphyMib 1}
docsRphyRpdMibObjects        OBJECT IDENTIFIER ::= { docsRphyMibObjects 1}
docsRphyRpdPhysMibObjects    OBJECT IDENTIFIER ::= { docsRphyMibObjects 2}
docsRphyRpdIfMibObjects      OBJECT IDENTIFIER ::= { docsRphyMibObjects 3}
docsRphyRpdIpMibObjects      OBJECT IDENTIFIER ::= { docsRphyMibObjects 4}
docsRphyRpdIpIcmpMibObjects  OBJECT IDENTIFIER ::= { docsRphyRpdIpMibObjects 9 }
docsRphyCcapMibObjects       OBJECT IDENTIFIER ::= { docsRphyMibObjects 5}
docsRphyNotifications        OBJECT IDENTIFIER ::= { docsRphyMib 2}
docsRphyConformance          OBJECT IDENTIFIER ::= { docsRphyMib 3}


-- ---------------------------------------------------------------------
-- Notification Objects
-- ---------------------------------------------------------------------

-- ---------------------------------------------------------------------
-- RPD Group Objects
-- ---------------------------------------------------------------------

-- ---------------------------------------------------------------------
-- RPD Info Table
-- ---------------------------------------------------------------------

docsRphyRpdInfoTable OBJECT-TYPE
        SYNTAX      SEQUENCE OF DocsRphyRpdInfoEntry
        MAX-ACCESS  not-accessible
        STATUS      current
        DESCRIPTION
            "This table identifies the RPD for which the details
             and statistics are being provided."
        ::= { docsRphyRpdMibObjects 1 }


docsRphyRpdInfoEntry OBJECT-TYPE
        SYNTAX     DocsRphyRpdInfoEntry
        MAX-ACCESS not-accessible
        STATUS     current
        DESCRIPTION
            "The conceptual row of docsRphyRpdInfoTable."
        INDEX { docsRphyRpdInfoUniqueId }
        ::= { docsRphyRpdInfoTable 1 }


DocsRphyRpdInfoEntry ::= SEQUENCE
       {
       docsRphyRpdInfoUniqueId              MacAddress,
       docsRphyRpdInfoSysUpTime             TimeStamp
       }
        
docsRphyRpdInfoUniqueId OBJECT-TYPE
        SYNTAX      MacAddress
        MAX-ACCESS  not-accessible 
        STATUS      current 
        DESCRIPTION 
            "This attribute specifies the MAC address associated with 
             the lowest numbered CIN facing Ethernet port."
        ::= { docsRphyRpdInfoEntry 1 }


docsRphyRpdInfoSysUpTime OBJECT-TYPE
        SYNTAX      TimeStamp
        MAX-ACCESS  read-only
        STATUS      current
        DESCRIPTION 
            "This attribute is the time (in hundredths of a second) 
             since the RPD was last re-initialized. This value is 
             reported by the RPD."
        ::= { docsRphyRpdInfoEntry 2 }
        
-- ---------------------------------------------------------------------
-- RPD Identification Table
-- ---------------------------------------------------------------------

docsRphyRpdIdentificationTable OBJECT-TYPE
        SYNTAX      SEQUENCE OF DocsRphyRpdIdentificationEntry
        MAX-ACCESS  not-accessible
        STATUS      current
        DESCRIPTION
            "This table provides data that uniquely identifies the RPD."
        ::= { docsRphyRpdMibObjects 2 }


docsRphyRpdIdentificationEntry OBJECT-TYPE
        SYNTAX     DocsRphyRpdIdentificationEntry
        MAX-ACCESS not-accessible
        STATUS     current
        DESCRIPTION
            "The conceptual row of docsRphyRpdIdentificationTable."
        INDEX { docsRphyRpdInfoUniqueId }
        ::= { docsRphyRpdIdentificationTable 1 }


DocsRphyRpdIdentificationEntry ::= SEQUENCE
       {
       docsRphyRpdIdVendorName          SnmpAdminString,
       docsRphyRpdIdVendorId            Unsigned32,
       docsRphyRpdIdModelNum            SnmpAdminString,
       docsRphyRpdIdSerialNum           SnmpAdminString,
       docsRphyRpdIdDeviceAlias         SnmpAdminString,
       docsRphyRpdIdDeviceDescr         SnmpAdminString,
       docsRphyRpdIdHwRev               SnmpAdminString,
       docsRphyRpdIdCurrSwVer           SnmpAdminString,
       docsRphyRpdIdBootRomVer          SnmpAdminString
       }
        
docsRphyRpdIdVendorName OBJECT-TYPE
        SYNTAX      SnmpAdminString
        MAX-ACCESS  read-only 
        STATUS      current 
        DESCRIPTION 
            "This attribute identifies the RPD manufacturer. 
             The format is vendor proprietary."
        ::= { docsRphyRpdIdentificationEntry 1 }


docsRphyRpdIdVendorId OBJECT-TYPE
        SYNTAX      Unsigned32
        MAX-ACCESS  read-only
        STATUS      current
        DESCRIPTION 
            "This attribute is the IANA-assigned SMI Network Management 
             Private Enterprise Code of the vendor, as specified in
             RFC 1700."
        ::= { docsRphyRpdIdentificationEntry 2 }

docsRphyRpdIdModelNum OBJECT-TYPE
        SYNTAX      SnmpAdminString
        MAX-ACCESS  read-only 
        STATUS      current 
        DESCRIPTION 
            "This attribute is the model name and number used by the 
             vendor to identify the RPD. The format is vendor 
             proprietary."
        ::= { docsRphyRpdIdentificationEntry 3 }

docsRphyRpdIdSerialNum OBJECT-TYPE
        SYNTAX      SnmpAdminString
        MAX-ACCESS  read-only 
        STATUS      current 
        DESCRIPTION 
            "This attribute is the serial number of the RPD. 
             The format is vendor proprietary."
        ::= { docsRphyRpdIdentificationEntry 4 }
        
docsRphyRpdIdDeviceAlias OBJECT-TYPE
        SYNTAX      SnmpAdminString
        MAX-ACCESS  read-only 
        STATUS      current 
        DESCRIPTION 
            "This attribute is a device name assigned by the operator 
             via the management interface. The attribute provides a 
             non-volatile 'handle' for the RPD."
        ::= { docsRphyRpdIdentificationEntry 5 }
        
docsRphyRpdIdDeviceDescr OBJECT-TYPE
        SYNTAX      SnmpAdminString
        MAX-ACCESS  read-only 
        STATUS      current 
        DESCRIPTION 
            "This attribute is a short text description of the RPD
             provided by the RPD manufacturer."
        ::= { docsRphyRpdIdentificationEntry 6 }
        
docsRphyRpdIdHwRev OBJECT-TYPE
        SYNTAX      SnmpAdminString
        MAX-ACCESS  read-only 
        STATUS      current 
        DESCRIPTION 
            "This attribute is the revision number of the hardware 
             of the RPD. The format is vendor proprietary."
        ::= { docsRphyRpdIdentificationEntry 7 }
        
docsRphyRpdIdCurrSwVer OBJECT-TYPE
        SYNTAX      SnmpAdminString
        MAX-ACCESS  read-only 
        STATUS      current 
        DESCRIPTION 
            "This attribute is the version number of the software 
             currently running on the RPD. The format is vendor 
             proprietary."
        ::= { docsRphyRpdIdentificationEntry 8 }
        
docsRphyRpdIdBootRomVer OBJECT-TYPE
        SYNTAX      SnmpAdminString
        MAX-ACCESS  read-only 
        STATUS      current 
        DESCRIPTION 
            "The version number of the boot ROM currently installed
             on the RPD. The format is vendor proprietary."
        ::= { docsRphyRpdIdentificationEntry 9 }

-- ---------------------------------------------------------------------
-- RPD Location Table
-- ---------------------------------------------------------------------

docsRphyRpdLocationTable OBJECT-TYPE
        SYNTAX      SEQUENCE OF DocsRphyRpdLocationEntry
        MAX-ACCESS  not-accessible
        STATUS      current
        DESCRIPTION
            "This table provides location details for the RPD."
        ::= { docsRphyRpdMibObjects 3 }


docsRphyRpdLocationEntry OBJECT-TYPE
        SYNTAX     DocsRphyRpdLocationEntry
        MAX-ACCESS not-accessible
        STATUS     current
        DESCRIPTION
            "The conceptual row of docsRphyRpdLocationTable."
        INDEX { docsRphyRpdInfoUniqueId }
        ::= { docsRphyRpdLocationTable 1 }


DocsRphyRpdLocationEntry ::= SEQUENCE
       {
       docsRphyRpdLocationDescr              SnmpAdminString,
       docsRphyRpdLocationLatitude           SnmpAdminString,
       docsRphyRpdLocationLongitude          SnmpAdminString
       }
        
docsRphyRpdLocationDescr OBJECT-TYPE
        SYNTAX      SnmpAdminString
        MAX-ACCESS  read-only 
        STATUS      current 
        DESCRIPTION 
            "This attribute is short text description of where the RPD
             has been installed, such as a street address. The format 
             is specific to the operator."
        ::= { docsRphyRpdLocationEntry 1 }


docsRphyRpdLocationLatitude OBJECT-TYPE
        SYNTAX      SnmpAdminString
        MAX-ACCESS  read-only
        STATUS      current
        DESCRIPTION 
            "This attribute is the latitudinal coordinate of the RPD 
             location, expressed as a 6-byte long string as described
             in ISO 6709-2008 (6 digit degrees, minutes, 
             seconds: ±DDMMSS.S). For  example: -750015.1"
        ::= { docsRphyRpdLocationEntry 2 }
        
docsRphyRpdLocationLongitude OBJECT-TYPE
        SYNTAX      SnmpAdminString
        MAX-ACCESS  read-only
        STATUS      current
        DESCRIPTION 
            "This attribute is the longitudinal coordinate of the RPD 
             location, expressed as a 7-byte long string as described 
             in ISO 6709-2008 (7 digits degrees, minutes, 
             seconds: ±DDDMMSS.S).  For example: -0750015.1"
        ::= { docsRphyRpdLocationEntry 3 }
        
-- ---------------------------------------------------------------------
-- RPD Cores Connected Table
-- ---------------------------------------------------------------------

docsRphyRpdCoresConnectedTable OBJECT-TYPE
        SYNTAX      SEQUENCE OF DocsRphyRpdCoresConnectedEntry
        MAX-ACCESS  not-accessible
        STATUS      current
        DESCRIPTION
            "This table provides a list of CCAP-Cores to which the RPD
             is authenticated, including the CCAP-Core on which the MIB 
             is polled. For each CCAP-Core entry, the RPD indicates if 
             that CCAP-Core is the principal Core. These values are 
             provided by the CCAP-Core on initialization."
        ::= { docsRphyRpdMibObjects 4 }


docsRphyRpdCoresConnectedEntry OBJECT-TYPE
        SYNTAX     DocsRphyRpdCoresConnectedEntry
        MAX-ACCESS not-accessible
        STATUS     current
        DESCRIPTION
            "The conceptual row of docsRphyRpdCoresConnectedTable."
        INDEX { docsRphyRpdInfoUniqueId, docsRphyRpdCoresConnectedCoreId }
        ::= { docsRphyRpdCoresConnectedTable 1 }


DocsRphyRpdCoresConnectedEntry ::= SEQUENCE
       {
       docsRphyRpdCoresConnectedCoreId              MacAddress,
       docsRphyRpdCoresConnectedAddressType         InetAddressType,
       docsRphyRpdCoresConnectedAddress             InetAddress,
       docsRphyRpdCoresConnectedIsPrincipal         TruthValue,
       docsRphyRpdCoresConnectedName	            SnmpAdminString,
       docsRphyRpdCoresConnectedVendorId	        Unsigned32
       }
        
docsRphyRpdCoresConnectedCoreId OBJECT-TYPE
        SYNTAX      MacAddress
        MAX-ACCESS  not-accessible 
        STATUS      current 
        DESCRIPTION 
            "This attribute provides the MAC address of the CCAP-Core
             identified in the row entry and acts as a key."
        ::= { docsRphyRpdCoresConnectedEntry 1 }


docsRphyRpdCoresConnectedAddressType OBJECT-TYPE
        SYNTAX      InetAddressType
        MAX-ACCESS  read-only
        STATUS      current
        DESCRIPTION 
            "This attribute specifies the IP address 
             type for docsRphyRpdCoresConnectedAddress."
        ::= { docsRphyRpdCoresConnectedEntry 2 }
        
docsRphyRpdCoresConnectedAddress OBJECT-TYPE
        SYNTAX      InetAddress
        MAX-ACCESS  read-only
        STATUS      current
        DESCRIPTION 
            "This attribute provides the IPv4 or IPv6 address 
             of the CCAP-Core."
        ::= { docsRphyRpdCoresConnectedEntry 3 }
        
docsRphyRpdCoresConnectedIsPrincipal OBJECT-TYPE
        SYNTAX      TruthValue
        MAX-ACCESS  read-only
        STATUS      current
        DESCRIPTION 
            "This attribute indicates if the CCAP-Core is the
             principal core. If true, this attribute indicates 
             that this CCAP-Core is the principal core."
        ::= { docsRphyRpdCoresConnectedEntry 4 }
        
docsRphyRpdCoresConnectedName OBJECT-TYPE
        SYNTAX      SnmpAdminString
        MAX-ACCESS  read-only
        STATUS      current
        DESCRIPTION 
            "This attribute provides the name of the CCAP-Core 
             as conveyed to the RPD."
        ::= { docsRphyRpdCoresConnectedEntry 5 }
        
docsRphyRpdCoresConnectedVendorId OBJECT-TYPE
        SYNTAX      Unsigned32
        MAX-ACCESS  read-only
        STATUS      current
        DESCRIPTION 
            "This attribute provides the IANA-assigned SMI Network 
             Management Private Enterprise Code of the vendor, as 
             specified in RFC 1700."
        ::= { docsRphyRpdCoresConnectedEntry 6 }
        
-- ---------------------------------------------------------------------
-- RPD Capabilities Table
-- ---------------------------------------------------------------------

docsRphyRpdCapabilitiesTable OBJECT-TYPE
        SYNTAX      SEQUENCE OF DocsRphyRpdCapabilitiesEntry
        MAX-ACCESS  not-accessible
        STATUS      current
        DESCRIPTION
            "This table provides information about the principal 
             capabilities and constraints of the RPD."
        ::= { docsRphyRpdMibObjects 5 }


docsRphyRpdCapabilitiesEntry OBJECT-TYPE
        SYNTAX     DocsRphyRpdCapabilitiesEntry
        MAX-ACCESS not-accessible
        STATUS     current
        DESCRIPTION
            "The conceptual row of docsRphyRpdCapabilitiesTable."
        INDEX { docsRphyRpdInfoUniqueId }
        ::= { docsRphyRpdCapabilitiesTable 1 }


DocsRphyRpdCapabilitiesEntry ::= SEQUENCE
       {
       docsRphyRpdCapabNumBiDirPorts              Unsigned32,
       docsRphyRpdCapabNumDsPorts                 Unsigned32,
       docsRphyRpdCapabNumUsPorts                 Unsigned32,
       docsRphyRpdCapabNumTenGeNsPorts            Unsigned32,
       docsRphyRpdCapabNumOneGeNsPorts	          Unsigned32,
       docsRphyRpdCapabNumDsScQamChans	          Unsigned32,
       docsRphyRpdCapabNumDsOfdmChans	          Unsigned32,
       docsRphyRpdCapabNumUsScQamChans	          Unsigned32,
       docsRphyRpdCapabNumUsOfdmaChans	          Unsigned32,
       docsRphyRpdCapabNumDsOob551Chans	          Unsigned32,
       docsRphyRpdCapabNumUsOob551Chans	          Unsigned32,
       docsRphyRpdCapabNumDsOob552Chans	          Unsigned32,
       docsRphyRpdCapabNumUsOob552Chans	          Unsigned32,
       docsRphyRpdCapabNumNdfChans	              Unsigned32,
       docsRphyRpdCapabNumNdrChans	              Unsigned32,
       docsRphyRpdCapabSupportsUdpEncap	          TruthValue,
       docsRphyRpdCapabNumDsPspFlowsPerChan       Unsigned32,
       docsRphyRpdCapabNumUsPspFlowsPerChan       Unsigned32,
       docsRphyRpdCapabNumAsynchVideoChans        Unsigned32,
       docsRphyRpdCapabNumCwToneGens              Unsigned32,
       docsRphyRpdCapabLowestCwToneFreq           Unsigned32,
       docsRphyRpdCapabHighestCwToneFreq          Unsigned32,
       docsRphyRpdCapabMaxCwTonePwr               Unsigned32,
       docsRphyRpdCapabQamAsPilot                 TruthValue
       }
        
docsRphyRpdCapabNumBiDirPorts OBJECT-TYPE
        SYNTAX      Unsigned32
        MAX-ACCESS  read-only 
        STATUS      current 
        DESCRIPTION 
            "This attribute provides the number of bidirectional
             RF ports available on the RPD."
        ::= { docsRphyRpdCapabilitiesEntry 1 }


docsRphyRpdCapabNumDsPorts OBJECT-TYPE
        SYNTAX      Unsigned32
        MAX-ACCESS  read-only
        STATUS      current
        DESCRIPTION 
            "This attribute provides the number of downstream 
             unidirectional RF ports available on the RPD."
        ::= { docsRphyRpdCapabilitiesEntry 2 }
        
docsRphyRpdCapabNumUsPorts OBJECT-TYPE
        SYNTAX      Unsigned32
        MAX-ACCESS  read-only
        STATUS      current
        DESCRIPTION 
            "This attribute provides the number of upstream 
             unidirectional RF ports available on the RPD."
        ::= { docsRphyRpdCapabilitiesEntry 3 }
        
docsRphyRpdCapabNumTenGeNsPorts OBJECT-TYPE
        SYNTAX      Unsigned32
        MAX-ACCESS  read-only
        STATUS      current
        DESCRIPTION 
            "This attribute provides the number of 10 Gigabit 
             Ethernet ports supported by the RPD."
        ::= { docsRphyRpdCapabilitiesEntry 4 }
        
docsRphyRpdCapabNumOneGeNsPorts OBJECT-TYPE
        SYNTAX      Unsigned32
        MAX-ACCESS  read-only
        STATUS      current
        DESCRIPTION 
            "This attribute provides the number 1 Gigabit 
             Ethernet ports supported by the RPD."
        ::= { docsRphyRpdCapabilitiesEntry 5 }
        
docsRphyRpdCapabNumDsScQamChans OBJECT-TYPE
        SYNTAX      Unsigned32
        MAX-ACCESS  read-only
        STATUS      current
        DESCRIPTION 
            "This attribute provides the number of downstream 
             SC-QAM channels supported per downstream RF port."
        ::= { docsRphyRpdCapabilitiesEntry 6 }
        
docsRphyRpdCapabNumDsOfdmChans OBJECT-TYPE
        SYNTAX      Unsigned32
        MAX-ACCESS  read-only
        STATUS      current
        DESCRIPTION 
            "This attribute provides the number of downstream 
             DOCSIS 3.1 channels supported per downstream RF port."
        ::= { docsRphyRpdCapabilitiesEntry 7 }
        
docsRphyRpdCapabNumUsScQamChans OBJECT-TYPE
        SYNTAX      Unsigned32
        MAX-ACCESS  read-only
        STATUS      current
        DESCRIPTION 
            "This attribute provides the number of upstream 
             SC-QAM channels supported per upstream RF port."
        ::= { docsRphyRpdCapabilitiesEntry 8 }
        
docsRphyRpdCapabNumUsOfdmaChans OBJECT-TYPE
        SYNTAX      Unsigned32
        MAX-ACCESS  read-only
        STATUS      current
        DESCRIPTION 
            "This attribute provides the number of upstream 
             DOCSIS 3.1 channels supported per upstream RF port."
        ::= { docsRphyRpdCapabilitiesEntry 9 }
        
docsRphyRpdCapabNumDsOob551Chans OBJECT-TYPE
        SYNTAX      Unsigned32
        MAX-ACCESS  read-only
        STATUS      current
        DESCRIPTION 
            "This attribute provides the number of downstream
             SCTE 55-1 channels supported per downstream RF port."
        ::= { docsRphyRpdCapabilitiesEntry 10 }
        
docsRphyRpdCapabNumUsOob551Chans OBJECT-TYPE
        SYNTAX      Unsigned32
        MAX-ACCESS  read-only
        STATUS      current
        DESCRIPTION 
            "This attribute provides the number of upstream
             SCTE 55-1 channels supported per upstream RF port."
        ::= { docsRphyRpdCapabilitiesEntry 11 }
        
docsRphyRpdCapabNumDsOob552Chans OBJECT-TYPE
        SYNTAX      Unsigned32
        MAX-ACCESS  read-only
        STATUS      current
        DESCRIPTION 
            "This attribute provides the number of downstream
             SCTE 55-2 channels supported per downstream RF port."
        ::= { docsRphyRpdCapabilitiesEntry 12 }
        
docsRphyRpdCapabNumUsOob552Chans OBJECT-TYPE
        SYNTAX      Unsigned32
        MAX-ACCESS  read-only
        STATUS      current
        DESCRIPTION 
            "This attribute provides the number of upstream
             SCTE 55-2 channels supported per upstream RF port."
        ::= { docsRphyRpdCapabilitiesEntry 13 }
        
docsRphyRpdCapabNumNdfChans OBJECT-TYPE
        SYNTAX      Unsigned32
        MAX-ACCESS  read-only
        STATUS      current
        DESCRIPTION 
            "This attribute provides the number of narrowband digital
             forward channels supported per downstream RF port."
        ::= { docsRphyRpdCapabilitiesEntry 14 }
        
docsRphyRpdCapabNumNdrChans OBJECT-TYPE
        SYNTAX      Unsigned32
        MAX-ACCESS  read-only
        STATUS      current
        DESCRIPTION 
            "This attribute provides the number of narrowband digital
             return channels supported per upstream RF port."
        ::= { docsRphyRpdCapabilitiesEntry 15 }
        
docsRphyRpdCapabSupportsUdpEncap OBJECT-TYPE
        SYNTAX      TruthValue
        MAX-ACCESS  read-only
        STATUS      current
        DESCRIPTION 
            "This attribute indicates RPD support of UDP encapsulation 
             on L2TPv3 pseudowires. If true, this attribute indicates 
             the RPD supports UDP encapsulation on L2TPv3 pseudowires."
        ::= { docsRphyRpdCapabilitiesEntry 16 }
        
docsRphyRpdCapabNumDsPspFlowsPerChan OBJECT-TYPE
        SYNTAX      Unsigned32
        MAX-ACCESS  read-only
        STATUS      current
        DESCRIPTION 
            "This attribute provides the number of distinct PSP flows
             supported by the RPD on downstream data pseudowires."
        ::= { docsRphyRpdCapabilitiesEntry 17 }
        
docsRphyRpdCapabNumUsPspFlowsPerChan OBJECT-TYPE
        SYNTAX      Unsigned32
        MAX-ACCESS  read-only
        STATUS      current
        DESCRIPTION 
            "This attribute provides the number of distinct PSP flows
             supported by the RPD on upstream data pseudowires."
        ::= { docsRphyRpdCapabilitiesEntry 18 }
        
docsRphyRpdCapabNumAsynchVideoChans OBJECT-TYPE
        SYNTAX      Unsigned32
        MAX-ACCESS  read-only
        STATUS      current
        DESCRIPTION 
            "This attribute provides the number of asynchronous 
             MPEG video channels supported per downstream RF port."
        ::= { docsRphyRpdCapabilitiesEntry 19 }
        
docsRphyRpdCapabNumCwToneGens OBJECT-TYPE
        SYNTAX      Unsigned32
        MAX-ACCESS  read-only
        STATUS      current
        DESCRIPTION 
            "This attribute provides the number of CW tone generators
             supported per downstream RF port."
        ::= { docsRphyRpdCapabilitiesEntry 20 }
        
docsRphyRpdCapabLowestCwToneFreq OBJECT-TYPE
        SYNTAX      Unsigned32
        UNITS       "Hz"
        MAX-ACCESS  read-only
        STATUS      current
        DESCRIPTION 
            "This attribute provides the lowest frequency supported
             by the CW tone generators."
        ::= { docsRphyRpdCapabilitiesEntry 21 }
        
docsRphyRpdCapabHighestCwToneFreq OBJECT-TYPE
        SYNTAX      Unsigned32
        UNITS       "Hz"
        MAX-ACCESS  read-only
        STATUS      current
        DESCRIPTION 
            "This attribute provides the highest frequency supported
             by the CW tone generators."
        ::= { docsRphyRpdCapabilitiesEntry 22 }
        
docsRphyRpdCapabMaxCwTonePwr OBJECT-TYPE
        SYNTAX      Unsigned32
        UNITS       "TenthdBmV"
        MAX-ACCESS  read-only
        STATUS      current
        DESCRIPTION 
            "This attribute provides the maximum power level supported
             by the dedicated CW tone generators, expressed in 
             TenthdBmV."
        ::= { docsRphyRpdCapabilitiesEntry 23 }
        
docsRphyRpdCapabQamAsPilot OBJECT-TYPE
        SYNTAX      TruthValue
        MAX-ACCESS  read-only
        STATUS      current
        DESCRIPTION 
            "This attribute indicates if a QAM channel can be configured
             as a CW tone. If true, this attribute indicates that a QAM 
             channel can be configured as a CW tone."
        ::= { docsRphyRpdCapabilitiesEntry 24 }
         
-- ---------------------------------------------------------------------
-- RPD Channel Reachability Table
-- ---------------------------------------------------------------------

docsRphyRpdChanReachabilityTable OBJECT-TYPE
        SYNTAX      SEQUENCE OF DocsRphyRpdChanReachabilityEntry
        MAX-ACCESS  not-accessible
        STATUS      current
        DESCRIPTION
            "This table provides RPD channel reachability constraints. 
             In some RPD implementations, an Ethernet interface might 
             not have connectivity to all channels on a port of the RPD.
             This table is only populated if reachability constraints 
             exist on the RPD."
        ::= { docsRphyRpdMibObjects 6 }


docsRphyRpdChanReachabilityEntry OBJECT-TYPE
        SYNTAX     DocsRphyRpdChanReachabilityEntry
        MAX-ACCESS not-accessible
        STATUS     current
        DESCRIPTION
            "The conceptual row of docsRphyRpdChanReachabilityTable."
        INDEX { docsRphyRpdInfoUniqueId,
                docsRphyRpdChanReachabilityEnetPortIndex,
                docsRphyRpdChanReachabilityRfPortIndex,
                docsRphyRpdChanReachabilityChanType }
        ::= { docsRphyRpdChanReachabilityTable 1 }


DocsRphyRpdChanReachabilityEntry ::= SEQUENCE
       {
       docsRphyRpdChanReachabilityEnetPortIndex       Unsigned32,
       docsRphyRpdChanReachabilityRfPortIndex         Unsigned32,
       docsRphyRpdChanReachabilityChanType            INTEGER,
       docsRphyRpdChanReachabilityStartChanIndex      Unsigned32,
       docsRphyRpdChanReachabilityEndChanIndex	      Unsigned32
       }
        
docsRphyRpdChanReachabilityEnetPortIndex OBJECT-TYPE
        SYNTAX      Unsigned32
        MAX-ACCESS  not-accessible 
        STATUS      current 
        DESCRIPTION 
            "This attribute identifies the Ethernet port on the RPD
             that has the connectivity constraint."
        ::= { docsRphyRpdChanReachabilityEntry 1 }


docsRphyRpdChanReachabilityRfPortIndex OBJECT-TYPE
        SYNTAX      Unsigned32
        MAX-ACCESS  not-accessible
        STATUS      current
        DESCRIPTION 
            "This attribute identifies the RF port with which the 
             Ethernet port has a connectivity constraint."
        ::= { docsRphyRpdChanReachabilityEntry 2 }
        
docsRphyRpdChanReachabilityChanType OBJECT-TYPE
        SYNTAX      INTEGER {
                      dsScQam(1),
                      dsOfdm(2),
                      dsOob551(3),
                      dsOob552(4),
                      ndf(5),
                      usScQam(6),
                      usOfdma(7),
                      usOob551(8),
                      usOob552(9),
                      ndr(10) }
        MAX-ACCESS  not-accessible
        STATUS      current
        DESCRIPTION 
            "This attribute identifies the type of channel that is supported
             within the specified channel index range on this RF port from the 
             specified Ethernet interface. A row entry will be created for each 
             channel type with a constraint. Absence of a row for a channel type 
             means there is no constraint for that channel type."
        ::= { docsRphyRpdChanReachabilityEntry 3 }
        
docsRphyRpdChanReachabilityStartChanIndex OBJECT-TYPE
        SYNTAX      Unsigned32
        MAX-ACCESS  read-only
        STATUS      current
        DESCRIPTION 
            "This attribute identifies the first channel of the 
             specified channel type in the range of channels that 
             does not have connectivity to the specified Ethernet port."
        ::= { docsRphyRpdChanReachabilityEntry 4 }
        
docsRphyRpdChanReachabilityEndChanIndex OBJECT-TYPE
        SYNTAX      Unsigned32
        MAX-ACCESS  read-only
        STATUS      current
        DESCRIPTION 
            "This attribute identifies the last channel of the 
             specified channel type in the range of channels that 
             does not have connectivity to the specified Ethernet port."
        ::= { docsRphyRpdChanReachabilityEntry 5 }
        
        
-- ---------------------------------------------------------------------
-- RPD DS/US RF Port Allocation Table
-- ---------------------------------------------------------------------

docsRphyRpdDsUsRfPortAllocTable OBJECT-TYPE
        SYNTAX      SEQUENCE OF DocsRphyRpdDsUsRfPortAllocEntry
        MAX-ACCESS  not-accessible
        STATUS      current
        DESCRIPTION
            "This table provides the allocation status for downstream
             and upstream channel resources on the RPD on a per DS or
             US RF port basis."
        ::= { docsRphyRpdMibObjects 7 }


docsRphyRpdDsUsRfPortAllocEntry OBJECT-TYPE
        SYNTAX     DocsRphyRpdDsUsRfPortAllocEntry
        MAX-ACCESS not-accessible
        STATUS     current
        DESCRIPTION
            "The conceptual row of docsRphyRpdDsUsRfPortAllocTable."
        INDEX { docsRphyRpdInfoUniqueId, 
                docsRphyRpdDsUsRfPortAllocIndex, 
                docsRphyRpdDsUsRfPortAllocDirection }
        ::= { docsRphyRpdDsUsRfPortAllocTable 1 }


DocsRphyRpdDsUsRfPortAllocEntry ::= SEQUENCE
       {
       docsRphyRpdDsUsRfPortAllocIndex              Unsigned32,
       docsRphyRpdDsUsRfPortAllocDirection          IfDirection,
       docsRphyRpdDsUsRfPortAllocScQamChans         Unsigned32,
       docsRphyRpdDsUsRfPortAllocOfdmChans          Unsigned32,
       docsRphyRpdDsUsRfPortAllocOob551Chans        Unsigned32,
       docsRphyRpdDsUsRfPortAllocOob552Chans	    Unsigned32,
       docsRphyRpdDsUsRfPortAllocNdChans	        Unsigned32
       }
        
docsRphyRpdDsUsRfPortAllocIndex OBJECT-TYPE
        SYNTAX      Unsigned32
        MAX-ACCESS  not-accessible 
        STATUS      current 
        DESCRIPTION 
            "This attribute provides the index of the downstream or
             upstream RF port for which resource allocation is being 
             reported."
        ::= { docsRphyRpdDsUsRfPortAllocEntry 1 }
        
docsRphyRpdDsUsRfPortAllocDirection OBJECT-TYPE
        SYNTAX      IfDirection
        MAX-ACCESS  not-accessible 
        STATUS      current 
        DESCRIPTION 
            "This attribute indicates whether the allocation
             applies to the upstream or downstream RF Port."
        ::= { docsRphyRpdDsUsRfPortAllocEntry 2 }

docsRphyRpdDsUsRfPortAllocScQamChans OBJECT-TYPE
        SYNTAX      Unsigned32
        MAX-ACCESS  read-only
        STATUS      current
        DESCRIPTION 
            "This attribute provides the number of allocated SC-QAM
             channels on this RF port."
        ::= { docsRphyRpdDsUsRfPortAllocEntry 3 }
        
docsRphyRpdDsUsRfPortAllocOfdmChans OBJECT-TYPE
        SYNTAX      Unsigned32
        MAX-ACCESS  read-only
        STATUS      current
        DESCRIPTION 
            "This attribute provides the number of allocated DOCSIS 3.1
             channels on this RF port."
        ::= { docsRphyRpdDsUsRfPortAllocEntry 4 }
        
docsRphyRpdDsUsRfPortAllocOob551Chans OBJECT-TYPE
        SYNTAX      Unsigned32
        MAX-ACCESS  read-only
        STATUS      current
        DESCRIPTION 
            "This attribute provides the number of allocated SCTE 55-1
             channels on this RF port."
        ::= { docsRphyRpdDsUsRfPortAllocEntry 5 }
        
docsRphyRpdDsUsRfPortAllocOob552Chans OBJECT-TYPE
        SYNTAX      Unsigned32
        MAX-ACCESS  read-only
        STATUS      current
        DESCRIPTION 
            "This attribute provides the number of allocated SCTE 55-2 
             channels on this RF port."
        ::= { docsRphyRpdDsUsRfPortAllocEntry 6 }
        
docsRphyRpdDsUsRfPortAllocNdChans OBJECT-TYPE
        SYNTAX      Unsigned32
        MAX-ACCESS  read-only
        STATUS      current
        DESCRIPTION 
            "This attribute provides the number of allocated narrowband
             digital forward channels (for DS RF Ports) or narrowband
             digital return channels (for US RF Ports) on this RF port."
        ::= { docsRphyRpdDsUsRfPortAllocEntry 7 }
  
-- ---------------------------------------------------------
-- RPD L2TP Session Info Table 
-- ---------------------------------------------------------
                 
docsRphyRpdL2tpSessionInfoTable OBJECT-TYPE
    SYNTAX      SEQUENCE OF DocsRphyRpdL2tpSessionInfoEntry
    MAX-ACCESS  not-accessible
    STATUS      current
    DESCRIPTION
            "This table provides details about each tunnel 
             session between the RPD and each CCAP Core with which the 
             RPD is associated from the RPD's point of view
             The attributes in this table are used to create an entry 
             for each L2TPv3 tunnel (session) terminated at an R-PHY 
             entity (RPD)."
    ::= { docsRphyRpdMibObjects 8 }

docsRphyRpdL2tpSessionInfoEntry OBJECT-TYPE
    SYNTAX      DocsRphyRpdL2tpSessionInfoEntry
    MAX-ACCESS  not-accessible
    STATUS      current
    DESCRIPTION
            "The conceptual row of docsRphyRpdL2tpSessionInfoTable.
             A row entry is created for every session the RPD 
             terminates and there may be entries for sessions with 
             different CCAP-Cores if the RPD is connected with one 
             or more auxiliary cores."
    INDEX { docsRphyRpdInfoUniqueId,
            docsRphyRpdL2tpSessionInfoLocalLcceIpAddrType,
            docsRphyRpdL2tpSessionInfoLocalLcceIpAddr,
            docsRphyRpdL2tpSessionInfoLocalId }
    ::= { docsRphyRpdL2tpSessionInfoTable 1 }

DocsRphyRpdL2tpSessionInfoEntry ::= SEQUENCE
    {
    docsRphyRpdL2tpSessionInfoLocalLcceIpAddrType   InetAddressType,
    docsRphyRpdL2tpSessionInfoLocalLcceIpAddr       InetAddress,
    docsRphyRpdL2tpSessionInfoLocalId               Unsigned32,
    docsRphyRpdL2tpSessionInfoRemoteLcceIpAddrType  InetAddressType,
    docsRphyRpdL2tpSessionInfoRemoteLcceIpAddr      InetAddress,
    docsRphyRpdL2tpSessionInfoRemoteId              Unsigned32,
    docsRphyRpdL2tpSessionInfoConnCtrlID            Unsigned32,
    docsRphyRpdL2tpSessionInfoUdpPort               InetPortNumber,
    docsRphyRpdL2tpSessionInfoDescr                 SnmpAdminString,
    docsRphyRpdL2tpSessionInfoSessionType           INTEGER,
    docsRphyRpdL2tpSessionInfoSessionSubType        INTEGER,
    docsRphyRpdL2tpSessionInfoMaxPayload            Unsigned32,
    docsRphyRpdL2tpSessionInfoPathPayload           Unsigned32,
    docsRphyRpdL2tpSessionInfoRpdIfMtu              Unsigned32,
    docsRphyRpdL2tpSessionInfoErrorCode             INTEGER,
    docsRphyRpdL2tpSessionInfoCreationTime          TimeStamp,
    docsRphyRpdL2tpSessionInfoOperStatus            INTEGER,
    docsRphyRpdL2tpSessionInfoLocalStatus           BITS,
    docsRphyRpdL2tpSessionInfoLastChange            TimeTicks
    }

docsRphyRpdL2tpSessionInfoLocalLcceIpAddrType OBJECT-TYPE
    SYNTAX      InetAddressType
    MAX-ACCESS  not-accessible
    STATUS      current
    DESCRIPTION 
            "This attribute indicates whether the IP address provide in 
             docsRphyRpdL2tpSessionInfoLocalLcceIpAddr is IPv4 or IPv6."
    ::= { docsRphyRpdL2tpSessionInfoEntry 1 }

docsRphyRpdL2tpSessionInfoLocalLcceIpAddr OBJECT-TYPE
    SYNTAX      InetAddress
    MAX-ACCESS  not-accessible
    STATUS      current
    DESCRIPTION 
            "This attribute provides the local LCCE IP address on the 
             RPD of the session detailed in the row entry."
    ::= { docsRphyRpdL2tpSessionInfoEntry 2 }
    
docsRphyRpdL2tpSessionInfoLocalId OBJECT-TYPE
    SYNTAX      Unsigned32
    MAX-ACCESS  not-accessible
    STATUS      current
    DESCRIPTION 
            "This attribute provides the value of the session ID 
             assigned to the session by the RPD."
    ::= { docsRphyRpdL2tpSessionInfoEntry 3 }
    
docsRphyRpdL2tpSessionInfoRemoteLcceIpAddrType OBJECT-TYPE
    SYNTAX      InetAddressType
    MAX-ACCESS  read-only
    STATUS      current
    DESCRIPTION 
            "This attribute indicates whether the IP address provide in 
             docsRphyRpdL2tpSessionInfoRemoteLcceIpAddr is IPv4 or IPv6."
    ::= { docsRphyRpdL2tpSessionInfoEntry 4 }

docsRphyRpdL2tpSessionInfoRemoteLcceIpAddr OBJECT-TYPE
    SYNTAX      InetAddress
    MAX-ACCESS  read-only
    STATUS      current
    DESCRIPTION 
            "This attribute provides the remote-side LCCE IP address
             of the session detailed in the row entry."
    ::= { docsRphyRpdL2tpSessionInfoEntry 5 }
    
docsRphyRpdL2tpSessionInfoRemoteId OBJECT-TYPE
    SYNTAX      Unsigned32
    MAX-ACCESS  read-only
    STATUS      current
    DESCRIPTION 
            "This attribute provides the value of the session ID 
             assigned to the session by the remote peer 
             (RPD)."
    ::= { docsRphyRpdL2tpSessionInfoEntry 6 }
    
docsRphyRpdL2tpSessionInfoConnCtrlID OBJECT-TYPE
    SYNTAX      Unsigned32
    MAX-ACCESS  read-only
    STATUS      current
    DESCRIPTION 
            "This attribute indicates the control connection
             identifier (CCID) for this session."
    ::= { docsRphyRpdL2tpSessionInfoEntry 7 }
    
docsRphyRpdL2tpSessionInfoUdpPort OBJECT-TYPE
    SYNTAX      InetPortNumber
    MAX-ACCESS  read-only
    STATUS      current
    DESCRIPTION 
            "This attribute provides the UDP Port reported by the RPD
             when the DEPI session uses L2TPv3 Header Over
             UDP. This attribute reports a value of 0 when the session 
             is running with the L2TPv3 Session IP Header. 
             This port number is negotiated between the CCAP Core and 
             the RPD according to the L2TPv3 RFC."
    ::= { docsRphyRpdL2tpSessionInfoEntry 8 }
    
docsRphyRpdL2tpSessionInfoDescr OBJECT-TYPE
    SYNTAX      SnmpAdminString
    MAX-ACCESS  read-only
    STATUS      current
    DESCRIPTION 
            "This attribute provides an ASCII string constructed with
             the form:
             
             RemoteEndId=(pp:mmm:ccc),…  
                  { repeated for multiple endpoints } 

             where
             pp is the 0-based port num signaled in the RemoteEndId AVP
             mmm is the channel-type enum value from the RemoteEndId AVP 
             ccc is the channel number from the RemoteEndId AVP."
    ::= { docsRphyRpdL2tpSessionInfoEntry 9 }
    
docsRphyRpdL2tpSessionInfoSessionType OBJECT-TYPE
    SYNTAX      INTEGER {
                           psp(1),
                           mpt(2)
                        }
    MAX-ACCESS  read-only
    STATUS      current
    DESCRIPTION 
            "This attribute specifies whether the session is an MPT 
             session or PSP session."
    ::= { docsRphyRpdL2tpSessionInfoEntry 10 }
    
docsRphyRpdL2tpSessionInfoSessionSubType OBJECT-TYPE
    SYNTAX      INTEGER {
                           mptLegacy(1),
                           pspLegacy(2),
                           mcm(3),
                           pspDepiMultichannel(4),
                           pspUepiScQam(5),
                           pspUepiOfdma(6),
                           pspBwReqScQam(7),
                           pspBwReqOfdma(8),
                           pspProbe(9),
                           pspRngReqScQam(10),
                           pspRngReqOfdma(11),
                           pspMapScQam(12),
                           pspMapOfdma(13),
                           pspSpecman(14),
                           pspPnm(15),
                           psp551Fwd(16),
                           psp551Ret(17),
                           psp552Fwd(18),
                           psp552Ret(19),
                           pspNdf(20),
                           pspNdr(21)
                        }
    MAX-ACCESS  read-only
    STATUS      current
    DESCRIPTION 
            "This attribute specifies the type of DEPI MPT or DEPI 
             PSP session."
    ::= { docsRphyRpdL2tpSessionInfoEntry 11 }

docsRphyRpdL2tpSessionInfoMaxPayload OBJECT-TYPE
    SYNTAX      Unsigned32
    MAX-ACCESS  read-only
    STATUS      current
    DESCRIPTION 
            "This attribute indicates the maximum MTU negotiated between
             the CCAP Core and the RPD during the session establishment 
             process. It considers the header subtractions as indicated 
             in the DEPI specification."
    REFERENCE
            "DEPI specification, Signaling
             DEPI specification Annex A."
    ::= { docsRphyRpdL2tpSessionInfoEntry 12 }

docsRphyRpdL2tpSessionInfoPathPayload OBJECT-TYPE
    SYNTAX      Unsigned32
    MAX-ACCESS  read-only
    STATUS      current
    DESCRIPTION 
            "This attribute indicates the maximum MTU traversing the CIN
             from CCAP Core to the RPD. This is calculated by the CCAP 
             Core by procedures such as MTU discovery as described in 
             the DEPI specification."
    REFERENCE
            "DEPI specification, Network MTU"
    ::= { docsRphyRpdL2tpSessionInfoEntry 13 }
    
docsRphyRpdL2tpSessionInfoRpdIfMtu OBJECT-TYPE
    SYNTAX      Unsigned32
    MAX-ACCESS  read-only
    STATUS      current
    DESCRIPTION 
            "This attribute provides the RPD's CIN interface MTU and is
             read as the value of the following L2TPV3 AVP transmitted 
             by the RPD during session setup:
             
             DEPI Downstream PW          UEPI Upstream PW
             DEPI Remote MTU AVP (ICRP)  UEPI Remote MTU AVP (ICRP)."
    ::= { docsRphyRpdL2tpSessionInfoEntry 14 }

docsRphyRpdL2tpSessionInfoErrorCode OBJECT-TYPE
    SYNTAX      INTEGER {
        none(1),
        invalidMACInterfaceValue(2),
        invalidInterfaceValue(3),
        noResourcesForInterfaceIndex(4),
        l2tpv3Error(5),
        ifAdminStatusSetToDown(6)
        }
    MAX-ACCESS  read-only
    STATUS      current
    DESCRIPTION 
            "The error code raised when the session is in an error
            state. 
            'invalidMACInterfaceValue'  
               Indicates wrong assignment of the CCAP Core MAC interface
               ifIndex.
            'invalidInterfaceValue'  
               Indicates wrong assignment of the CCAP Core Downstream 
               interface ifIndex
            'noResourcesForInterfaceIfIndex' 
               Indicates the CCAP Core has no more resources to
               assign a session to this entry.
            'l2tpv3Error'
               An L2TPv3 StopCCN or CDN message was issued 
            'ifAdminStatusSetToDown'
               Indicates the ifAdminStatus was set to down and the
               session was torn down."
    ::= { docsRphyRpdL2tpSessionInfoEntry 15 }

docsRphyRpdL2tpSessionInfoCreationTime OBJECT-TYPE
    SYNTAX      TimeStamp
    MAX-ACCESS  read-only
    STATUS      current
    DESCRIPTION 
            "The attribute contains the sysUptime when the entry was 
             turned active."
    ::= { docsRphyRpdL2tpSessionInfoEntry 16 }
    
docsRphyRpdL2tpSessionInfoOperStatus OBJECT-TYPE
    SYNTAX      INTEGER {
                          other(0),
                          up(1),
                          down(2),
                          testing(3),
                          dormant(4),
                          notPresent(5),
                          lowerLayerDown(6)
                         }
    MAX-ACCESS  read-only
    STATUS      current
    DESCRIPTION 
            "This attribute provides the current status of the 
             pseudowire from the point of view of the specific 
             reporting entity (RPD). 
             Values are as follows:
             'other' 
                 indicates a vendor-specific operational status.
             'up'         
                 indicates that the pseudowire is ready to pass packets.
             'down' 
                 indicates that pseudowire signaling is not yet finished, 
                 or indications available at the service level indicate 
                 that the pseudowire is not passing packets.
             'testing' 
                 indicates that AdminStatus at the pseudowire level is 
                 set to test.
             'dormant' 
                 indicates that the pseudowire is not in a condition to 
                 pass packets but is in a 'pending' state, waiting for 
                 some external event.
             'notPresent' 
                 indicates that some component is missing to accomplish 
                 the setup of the pseudowire.  It can be a configuration 
                 error, incomplete configuration, or a missing H/W 
                 component.
             'lowerLayerDown' 
                 indicates one or more of the lower-layer 
                 interfaces responsible for running the underlying PSN
                 is not in OperStatus 'up' state."
    ::= { docsRphyRpdL2tpSessionInfoEntry 17 }

docsRphyRpdL2tpSessionInfoLocalStatus OBJECT-TYPE
    SYNTAX      BITS {
                      other(0),
                      pwNotForwarding(1), 
                      servicePwRxFault(2), 
                      servicePwTxFault(3), 
                      psnPwRxFault(4), 
                      psnPwTxFault(5)
    }
    MAX-ACCESS  read-only
    STATUS      current
    DESCRIPTION 
            "The attribute provides the status of the pseudowire 
             in the local node. If the 'other' bit is set, it indicates
             that an additional vendor-specific status is reported. 
             If none of the bits are set, it indicates no faults are 
             reported."
    ::= { docsRphyRpdL2tpSessionInfoEntry 18 }
    
docsRphyRpdL2tpSessionInfoLastChange OBJECT-TYPE
    SYNTAX      TimeTicks
    MAX-ACCESS  read-only
    STATUS      current
    DESCRIPTION 
            "The attribute provides the value of sysUpTime 
             when the session entered its current OperStatus 
             state from the point of view of the specific 
             reporting entity (RPD)."
    ::= { docsRphyRpdL2tpSessionInfoEntry 19 }
    
-- ---------------------------------------------------------
-- RPD L2TP Session Statistics Table 
-- ---------------------------------------------------------
                 
docsRphyRpdL2tpSessionStatsTable OBJECT-TYPE
    SYNTAX      SEQUENCE OF DocsRphyRpdL2tpSessionStatsEntry
    MAX-ACCESS  not-accessible
    STATUS      current
    DESCRIPTION
            "This table provides statistics about each tunnel 
             session between the RPD and each CCAP Core with which the 
             RPD is associated from the RPD's point of view."
    ::= { docsRphyRpdMibObjects 9 }

docsRphyRpdL2tpSessionStatsEntry OBJECT-TYPE
    SYNTAX      DocsRphyRpdL2tpSessionStatsEntry
    MAX-ACCESS  not-accessible
    STATUS      current
    DESCRIPTION
            "The conceptual row of docsRphyRpdL2tpSessionStatsTable.
             This table is an augmentation of 
             docsRphyL2tpSessionInfoTable."
    AUGMENTS { docsRphyL2tpSessionInfoEntry }
    ::= { docsRphyRpdL2tpSessionStatsTable 1 }

DocsRphyRpdL2tpSessionStatsEntry ::= SEQUENCE
    {
    docsRphyRpdL2tpSessionStatsOutOfSeqPkts   Counter32
    }
    
docsRphyRpdL2tpSessionStatsOutOfSeqPkts OBJECT-TYPE
    SYNTAX      Counter32
    MAX-ACCESS  read-only
    STATUS      current
    DESCRIPTION 
            "This attribute indicates the count of session packets that
             were received out of sequence from the point of view of the
             reporting entity. It is vendor dependent the re-sequence of 
             packets. Implementations that do not re-sequence packets 
             also increase the value of ifInDiscards for the respective 
             entry."
    ::= { docsRphyRpdL2tpSessionStatsEntry 1 }
    
-- ---------------------------------------------------------------------
-- RPD Physical Group Objects
-- ---------------------------------------------------------------------  

-- ---------------------------------------------------------------------
-- RPD Physical Entity Table extracted from RFC 6933 ENTITY-MIB
-- ---------------------------------------------------------------------

docsRphyRpdPhysEntityTable OBJECT-TYPE
    SYNTAX      SEQUENCE OF DocsRphyRpdPhysEntityEntry
    MAX-ACCESS  not-accessible
    STATUS      current
    DESCRIPTION
            "This table contains one row per physical entity.  There is
            always at least one row for an 'overall' physical entity."
    ::= { docsRphyRpdPhysMibObjects 1 }

docsRphyRpdPhysEntityEntry       OBJECT-TYPE
    SYNTAX      DocsRphyRpdPhysEntityEntry
    MAX-ACCESS  not-accessible
    STATUS      current
    DESCRIPTION
            "Information about a particular physical entity.

            Each entry provides objects (docsRphyRpdPhysEntityDescr,
            docsRphyRpdPhysEntityVendorType, and docsRphyRpdPhysEntityClass) to help an NMS
            identify and characterize the entry and objects
            (docsRphyRpdPhysEntityContainedIn and docsRphyRpdPhysEntityParentRelPos) to help
            an NMS relate the particular entry to other entries in this
            table."
    INDEX   { docsRphyRpdInfoUniqueId,
              docsRphyRpdPhysEntityIndex }
    ::= { docsRphyRpdPhysEntityTable 1 }

DocsRphyRpdPhysEntityEntry ::= SEQUENCE {
      docsRphyRpdPhysEntityIndex          PhysicalIndex,
      docsRphyRpdPhysEntityDescr          SnmpAdminString,
      docsRphyRpdPhysEntityVendorType     AutonomousType,
      docsRphyRpdPhysEntityContainedIn    PhysicalIndexOrZero,
      docsRphyRpdPhysEntityClass          IANAPhysicalClass,
      docsRphyRpdPhysEntityParentRelPos   Integer32,
      docsRphyRpdPhysEntityName           SnmpAdminString,
      docsRphyRpdPhysEntityHardwareRev    SnmpAdminString,
      docsRphyRpdPhysEntityFirmwareRev    SnmpAdminString,
      docsRphyRpdPhysEntitySoftwareRev    SnmpAdminString,
      docsRphyRpdPhysEntitySerialNum      SnmpAdminString,
      docsRphyRpdPhysEntityMfgName        SnmpAdminString,
      docsRphyRpdPhysEntityModelName      SnmpAdminString,
      docsRphyRpdPhysEntityAlias          SnmpAdminString,
      docsRphyRpdPhysEntityAssetID        SnmpAdminString,
      docsRphyRpdPhysEntityIsFRU          TruthValue,
      docsRphyRpdPhysEntityMfgDate        DateAndTime,
      docsRphyRpdPhysEntityUris           OCTET STRING,
      docsRphyRpdPhysEntityUUID           UUIDorZero,
      docsRphyRpdPhysEntityIfIndex        InterfaceIndexOrZero
}

docsRphyRpdPhysEntityIndex    OBJECT-TYPE
    SYNTAX      PhysicalIndex
    MAX-ACCESS  not-accessible
    STATUS      current
    DESCRIPTION
            "The index for this entry."
    ::= { docsRphyRpdPhysEntityEntry 1 }

docsRphyRpdPhysEntityDescr OBJECT-TYPE
    SYNTAX      SnmpAdminString
    MAX-ACCESS  read-only
    STATUS      current
    DESCRIPTION
            "A textual description of physical entity.  This object
            should contain a string that identifies the manufacturer's
            name for the physical entity and should be set to a
            distinct value for each version or model of the physical
            entity."
    ::= { docsRphyRpdPhysEntityEntry 2 }

docsRphyRpdPhysEntityVendorType OBJECT-TYPE
    SYNTAX      AutonomousType
    MAX-ACCESS  read-only
    STATUS      current
    DESCRIPTION
            "An indication of the vendor-specific hardware type of the
            physical entity.  Note that this is different from the
            definition of MIB-II's sysObjectID.

            An agent should set this object to an enterprise-specific
            registration identifier value indicating the specific
            equipment type in detail.  The associated instance of
            docsRphyRpdPhysEntityClass is used to indicate the general type of
            hardware device.

            If no vendor-specific registration identifier exists for
            this physical entity, or the value is unknown by this agent,
            then the value { 0 0 } is returned."
    ::= { docsRphyRpdPhysEntityEntry 3 }

docsRphyRpdPhysEntityContainedIn OBJECT-TYPE
    SYNTAX      PhysicalIndexOrZero
    MAX-ACCESS  read-only
    STATUS      current
    DESCRIPTION
            "The value of docsRphyRpdPhysEntityIndex for the physical entity that
            'contains' this physical entity.  A value of zero indicates
            this physical entity is not contained in any other physical
            entity.  Note that the set of 'containment' relationships
            define a strict hierarchy; that is, recursion is not
            allowed.

            In the event that a physical entity is contained by more
            than one physical entity (e.g., double-wide modules), this
            object should identify the containing entity with the lowest
            value of docsRphyRpdPhysEntityIndex."
    ::= { docsRphyRpdPhysEntityEntry 4 }

docsRphyRpdPhysEntityClass OBJECT-TYPE
    SYNTAX      IANAPhysicalClass
    MAX-ACCESS  read-only
    STATUS      current
    DESCRIPTION
            "An indication of the general hardware type of the physical
            entity.

            An agent should set this object to the standard enumeration
            value that most accurately indicates the general class of
            the physical entity, or the primary class if there is more
            than one entity.

            If no appropriate standard registration identifier exists
            for this physical entity, then the value 'other(1)' is
            returned.  If the value is unknown by this agent, then the
            value 'unknown(2)' is returned."
    ::= { docsRphyRpdPhysEntityEntry 5 }

docsRphyRpdPhysEntityParentRelPos OBJECT-TYPE
    SYNTAX      Integer32 (-1..2147483647)
    MAX-ACCESS  read-only
    STATUS      current
    DESCRIPTION
            "An indication of the relative position of this 'child'
            component among all its 'sibling' components.  Sibling
            components are defined as docsRphyRpdPhysEntityEntries that share the
            same instance values of each of the docsRphyRpdPhysEntityContainedIn
            and docsRphyRpdPhysEntityClass objects.

            An NMS can use this object to identify the relative ordering
            for all sibling components of a particular parent
            (identified by the docsRphyRpdPhysEntityContainedIn instance in each
            sibling entry).

            If possible, this value should match any external labeling
            of the physical component.  For example, for a container
            (e.g., card slot) labeled as 'slot #3',
            docsRphyRpdPhysEntityParentRelPos should have the value '3'.  Note
            that the docsRphyRpdPhysEntityEntry for the module plugged in slot 3
            should have an docsRphyRpdPhysEntityParentRelPos value of '1'.

            If the physical position of this component does not match
            any external numbering or clearly visible ordering, then
            user documentation or other external reference material
            should be used to determine the parent-relative position.
            If this is not possible, then the agent should assign a
            consistent (but possibly arbitrary) ordering to a given set
            of 'sibling' components, perhaps based on internal
            representation of the components.

            If the agent cannot determine the parent-relative position
            for some reason, or if the associated value of
            docsRphyRpdPhysEntityContainedIn is '0', then the value '-1' is
            returned.  Otherwise, a non-negative integer is returned,
            indicating the parent-relative position of this physical
            entity.

            Parent-relative ordering normally starts from '1' and
            continues to 'N', where 'N' represents the highest
            positioned child entity.  However, if the physical entities
            (e.g., slots) are labeled from a starting position of zero,
            then the first sibling should be associated with an
            docsRphyRpdPhysEntityParentRelPos value of '0'.  Note that this
            ordering may be sparse or dense, depending on agent
            implementation.

            The actual values returned are not globally meaningful, as
            each 'parent' component may use different numbering
            algorithms.  The ordering is only meaningful among siblings
            of the same parent component.

            The agent should retain parent-relative position values
            across reboots, either through algorithmic assignment or use
            of non-volatile storage."
    ::= { docsRphyRpdPhysEntityEntry 6 }

docsRphyRpdPhysEntityName OBJECT-TYPE
    SYNTAX      SnmpAdminString
    MAX-ACCESS  read-only
    STATUS      current
    DESCRIPTION
            "The textual name of the physical entity.  The value of this
            object should be the name of the component as assigned by
            the local device and should be suitable for use in commands
            entered at the device's 'console'.  This might be a text
            name (e.g., 'console') or a simple component number (e.g.,
            port or module number, such as '1'), depending on the
            physical component naming syntax of the device.

            If there is no local name, or if this object is otherwise
            not applicable, then this object contains a zero-length
            string.

            Note that the value of docsRphyRpdPhysEntityName for two physical
            entities will be the same in the event that the console
            interface does not distinguish between them, e.g., slot-1
            and the card in slot-1."
    ::= { docsRphyRpdPhysEntityEntry 7 }

docsRphyRpdPhysEntityHardwareRev    OBJECT-TYPE
    SYNTAX      SnmpAdminString
    MAX-ACCESS  read-only
    STATUS      current
    DESCRIPTION
            "The vendor-specific hardware revision string for the
            physical entity.  The preferred value is the hardware
            revision identifier actually printed on the component itself
            (if present).

            Note that if revision information is stored internally in a
            non-printable (e.g., binary) format, then the agent must
            convert such information to a printable format in an
            implementation-specific manner.

            If no specific hardware revision string is associated with
            the physical component, or if this information is unknown to
            the agent, then this object will contain a zero-length
            string."
    ::= { docsRphyRpdPhysEntityEntry 8 }

docsRphyRpdPhysEntityFirmwareRev    OBJECT-TYPE
    SYNTAX      SnmpAdminString
    MAX-ACCESS  read-only
    STATUS      current
    DESCRIPTION
            "The vendor-specific firmware revision string for the
            physical entity.

            Note that if revision information is stored internally in a
            non-printable (e.g., binary) format, then the agent must
            convert such information to a printable format in an
            implementation-specific manner.

            If no specific firmware programs are associated with the
            physical component, or if this information is unknown to the
            agent, then this object will contain a zero-length string."
    ::= { docsRphyRpdPhysEntityEntry 9 }

docsRphyRpdPhysEntitySoftwareRev    OBJECT-TYPE
    SYNTAX      SnmpAdminString
    MAX-ACCESS  read-only
    STATUS      current
    DESCRIPTION
            "The vendor-specific software revision string for the
            physical entity.

            Note that if revision information is stored internally in a
            non-printable (e.g., binary) format, then the agent must
            convert such information to a printable format in an
            implementation-specific manner.

            If no specific software programs are associated with the
            physical component, or if this information is unknown to the
            agent, then this object will contain a zero-length string."
    ::= { docsRphyRpdPhysEntityEntry 10 }

docsRphyRpdPhysEntitySerialNum   OBJECT-TYPE
    SYNTAX      SnmpAdminString (SIZE (0..32))
    MAX-ACCESS  read-write
    STATUS      current
    DESCRIPTION
            "The vendor-specific serial number string for the physical
            entity.  The preferred value is the serial number string
            actually printed on the component itself (if present).

            On the first instantiation of a physical entity, the value
            of docsRphyRpdPhysEntitySerialNum associated with that entity is set
            to the correct vendor-assigned serial number, if this
            information is available to the agent.  If a serial number
            is unknown or non-existent, the docsRphyRpdPhysEntitySerialNum will be
            set to a zero-length string instead.

            Note that implementations that can correctly identify the
            serial numbers of all installed physical entities do not
            need to provide write access to the docsRphyRpdPhysEntitySerialNum
            object.  Agents that cannot provide non-volatile storage
            for the docsRphyRpdPhysEntitySerialNum strings are not required to
            implement write access for this object.

            Not every physical component will have a serial number, or
            even need one.  Physical entities for which the associated
            value of the docsRphyRpdPhysEntityIsFRU object is equal to 'false(2)'
            (e.g., the repeater ports within a repeater module) do not
            need their own unique serial numbers.  An agent does not
            have to provide write access for such entities and may
            return a zero-length string.

            If write access is implemented for an instance of
            docsRphyRpdPhysEntitySerialNum and a value is written into the
            instance, the agent must retain the supplied value in the
            docsRphyRpdPhysEntitySerialNum instance (associated with the same
            physical entity) for as long as that entity remains
            instantiated.  This includes instantiations across all
            re-initializations/reboots of the network management system,
            including those resulting in a change of the physical
            entity's docsRphyRpdPhysEntityIndex value."
    ::= { docsRphyRpdPhysEntityEntry 11 }

docsRphyRpdPhysEntityMfgName   OBJECT-TYPE
    SYNTAX      SnmpAdminString
    MAX-ACCESS  read-only
    STATUS      current
    DESCRIPTION
            "The name of the manufacturer of this physical component.
            The preferred value is the manufacturer name string actually
            printed on the component itself (if present).

            Note that comparisons between instances of the
            docsRphyRpdPhysEntityModelName, docsRphyRpdPhysEntityFirmwareRev,
            docsRphyRpdPhysEntitySoftwareRev, and the docsRphyRpdPhysEntitySerialNum
            objects are only meaningful amongst docsRphyRpdPhysEntityEntries with
            the same value of docsRphyRpdPhysEntityMfgName.

            If the manufacturer name string associated with the physical
            component is unknown to the agent, then this object will
            contain a zero-length string."
    ::= { docsRphyRpdPhysEntityEntry 12 }

docsRphyRpdPhysEntityModelName   OBJECT-TYPE
    SYNTAX      SnmpAdminString
    MAX-ACCESS  read-only
    STATUS      current
    DESCRIPTION
            "The vendor-specific model name identifier string associated
            with this physical component.  The preferred value is the
            customer-visible part number, which may be printed on the
            component itself.

            If the model name string associated with the physical
            component is unknown to the agent, then this object will
            contain a zero-length string."
    ::= { docsRphyRpdPhysEntityEntry 13 }

docsRphyRpdPhysEntityAlias    OBJECT-TYPE
    SYNTAX      SnmpAdminString (SIZE (0..32))
    MAX-ACCESS  read-write
    STATUS      current
    DESCRIPTION
            "This object is an 'alias' name for the physical entity, as
            specified by a network manager, and provides a non-volatile
            'handle' for the physical entity.

            On the first instantiation of a physical entity, the value
            of docsRphyRpdPhysEntityAlias associated with that entity is set to
            the zero-length string.  However, the agent may set the
            value to a locally unique default value, instead of a
            zero-length string.

            If write access is implemented for an instance of
            docsRphyRpdPhysEntityAlias and a value is written into the instance,
            the agent must retain the supplied value in the
            docsRphyRpdPhysEntityAlias instance (associated with the same physical
            entity) for as long as that entity remains instantiated.
            This includes instantiations across all
            re-initializations/reboots of the network management system,
            including those resulting in a change of the physical
            entity's docsRphyRpdPhysEntityIndex value."
    ::= { docsRphyRpdPhysEntityEntry 14 }

docsRphyRpdPhysEntityAssetID OBJECT-TYPE
    SYNTAX      SnmpAdminString (SIZE (0..32))
    MAX-ACCESS  read-write
    STATUS      current
    DESCRIPTION
            "This object is a user-assigned asset tracking identifier
            (as specified by a network manager) for the physical entity
            and provides non-volatile storage of this information.

            On the first instantiation of a physical entity, the value
            of docsRphyRpdPhysEntityAssetID associated with that entity is set to
            the zero-length string.

            Not every physical component will have an asset tracking
            identifier or even need one.  Physical entities for which
            the associated value of the docsRphyRpdPhysEntityIsFRU object is equal
            to 'false(2)' (e.g., the repeater ports within a repeater
            module) do not need their own unique asset tracking
            identifier.  An agent does not have to provide write access
            for such entities and may instead return a zero-length
            string.

            If write access is implemented for an instance of
            docsRphyRpdPhysEntityAssetID and a value is written into the
            instance, the agent must retain the supplied value in the
            docsRphyRpdPhysEntityAssetID instance (associated with the same
            physical entity) for as long as that entity remains
            instantiated.  This includes instantiations across all
            re-initializations/reboots of the network management system,
            including those resulting in a change of the physical
            entity's docsRphyRpdPhysEntityIndex value.

            If no asset tracking information is associated with the
            physical component, then this object will contain a
            zero-length string."
    ::= { docsRphyRpdPhysEntityEntry 15 }

docsRphyRpdPhysEntityIsFRU OBJECT-TYPE
    SYNTAX      TruthValue
    MAX-ACCESS  read-only
    STATUS      current
    DESCRIPTION
            "This object indicates whether or not this physical entity
            is considered a 'field replaceable unit' by the vendor.
            If this object contains the value 'true(1)', then this
            docsRphyRpdPhysEntityEntry identifies a field replaceable unit.  For
            all docsRphyRpdPhysEntityEntries that represent components
            permanently contained within a field replaceable unit, the
            value 'false(2)' should be returned for this object."
    ::= { docsRphyRpdPhysEntityEntry 16 }

docsRphyRpdPhysEntityMfgDate  OBJECT-TYPE
    SYNTAX      DateAndTime
    MAX-ACCESS  read-only
    STATUS      current
    DESCRIPTION
            "This object contains the date of manufacturing of the
            managed entity.  If the manufacturing date is unknown or
            not supported, the object is not instantiated.  The special
            value '0000000000000000'H may also be returned in this
            case."
    ::= { docsRphyRpdPhysEntityEntry 17 }

docsRphyRpdPhysEntityUris OBJECT-TYPE
    SYNTAX      OCTET STRING
    MAX-ACCESS  read-write
    STATUS      current
    DESCRIPTION
            "This object contains identification
            information about the physical entity.  The object
            contains URIs; therefore, the syntax of this object
            must conform to RFC 3986, Section 3.

            Multiple URIs may be present and are separated by white
            space characters.  Leading and trailing white space
            characters are ignored.

            If no URI identification information is known
            about the physical entity, the object is not
            instantiated.  A zero-length octet string may also be
            returned in this case."
    REFERENCE
            "RFC 3986, Uniform Resource Identifiers (URI): Generic
            Syntax, Section 2, August 1998."
    ::= { docsRphyRpdPhysEntityEntry 18 }

docsRphyRpdPhysEntityUUID OBJECT-TYPE
    SYNTAX      UUIDorZero
    MAX-ACCESS  read-only
    STATUS      current
    DESCRIPTION
            "This object contains identification information
            about the physical entity.  The object contains a
            Universally Unique Identifier, the syntax of this object
            must conform to RFC 4122, Section 4.1.

            A zero-length octet string is returned if no UUID
            information is known."
    REFERENCE
            "RFC 4122, A Universally Unique IDentifier (UUID) URN
            Namespace, Section 4.1, July 2005."
    ::= { docsRphyRpdPhysEntityEntry 19 }
    
docsRphyRpdPhysEntityIfIndex OBJECT-TYPE
    SYNTAX     InterfaceIndexOrZero
    MAX-ACCESS read-only
    STATUS     current
    DESCRIPTION
           "The index value that uniquely identifies the interface to
            which this entry is applicable.  The interface identified by
            a particular value of this index is the same interface as
            identified by the same value of the IF-MIB's ifIndex.
            If no IfIndex is assigned, the value is zero."
    ::= { docsRphyRpdPhysEntityEntry 20 }
    
-- ---------------------------------------------------------------------
-- RPD Entity Sensor Table extracted from RFC 3433 ENTITY-SENSOR-MIB
-- ---------------------------------------------------------------------

docsRphyRpdPhysEntSensorTable OBJECT-TYPE
    SYNTAX        SEQUENCE OF DocsRphyRpdPhysEntSensorEntry
    MAX-ACCESS    not-accessible
    STATUS        current
    DESCRIPTION
            "This table contains one row per physical sensor represented
            by an associated row in the entPhysicalTable."
    ::= { docsRphyRpdPhysMibObjects 2 }

docsRphyRpdPhysEntSensorEntry OBJECT-TYPE
    SYNTAX        DocsRphyRpdPhysEntSensorEntry
    MAX-ACCESS    not-accessible
    STATUS        current
    DESCRIPTION
            "Information about a particular physical sensor.

            An entry in this table describes the present reading of a
            sensor, the measurement units and scale, and sensor
            operational status.

            Entries are created in this table by the agent.  An entry
            for each physical sensor SHOULD be created at the same time
            as the associated entPhysicalEntry.  An entry SHOULD be
            destroyed if the associated entPhysicalEntry is destroyed."
    INDEX  { docsRphyRpdInfoUniqueId,
             docsRphyRpdPhysEntityIndex }    -- SPARSE-AUGMENTS
    ::= { docsRphyRpdPhysEntSensorTable 1 }

DocsRphyRpdPhysEntSensorEntry ::= SEQUENCE {
        docsRphyRpdPhysEntSensorType            EntitySensorDataType,
        docsRphyRpdPhysEntSensorScale           EntitySensorDataScale,
        docsRphyRpdPhysEntSensorPrecision       EntitySensorPrecision,
        docsRphyRpdPhysEntSensorValue           EntitySensorValue,
        docsRphyRpdPhysEntSensorOperStatus      EntitySensorStatus,
        docsRphyRpdPhysEntSensorUnitsDisplay    SnmpAdminString,
        docsRphyRpdPhysEntSensorValueTimeStamp  TimeStamp,
        docsRphyRpdPhysEntSensorValueUpdateRate Unsigned32
}

docsRphyRpdPhysEntSensorType OBJECT-TYPE
    SYNTAX        EntitySensorDataType
    MAX-ACCESS    read-only
    STATUS        current
    DESCRIPTION
            "The type of data returned by the associated
            docsRphyRpdEntPhySensorValue object.

            This object SHOULD be set by the agent during entry
            creation, and the value SHOULD NOT change during operation."
    ::= { docsRphyRpdPhysEntSensorEntry 1 }

docsRphyRpdPhysEntSensorScale OBJECT-TYPE
    SYNTAX        EntitySensorDataScale
    MAX-ACCESS    read-only
    STATUS        current
    DESCRIPTION
            "The exponent to apply to values returned by the associated
            docsRphyRpdEntPhySensorValue object.

            This object SHOULD be set by the agent during entry
            creation, and the value SHOULD NOT change during operation."
    ::= { docsRphyRpdPhysEntSensorEntry 2 }

docsRphyRpdPhysEntSensorPrecision OBJECT-TYPE
    SYNTAX        EntitySensorPrecision
    MAX-ACCESS    read-only
    STATUS        current
    DESCRIPTION
            "The number of decimal places of precision in fixed-point
            sensor values returned by the associated docsRphyRpdEntPhySensorValue
            object.

            This object SHOULD be set to '0' when the associated
            docsRphyRpdEntPhySensorType value is not a fixed-point type: e.g.,
            'percentRH(9)', 'rpm(10)', 'cmm(11)', or 'truthvalue(12)'.

            This object SHOULD be set by the agent during entry
            creation, and the value SHOULD NOT change during operation."
    ::= { docsRphyRpdPhysEntSensorEntry 3 }

docsRphyRpdPhysEntSensorValue OBJECT-TYPE
    SYNTAX        EntitySensorValue
    MAX-ACCESS    read-only
    STATUS        current
    DESCRIPTION
            "The most recent measurement obtained by the agent for this
            sensor.

            To correctly interpret the value of this object, the
            associated docsRphyRpdEntPhySensorType, docsRphyRpdEntPhySensorScale, and
            docsRphyRpdEntPhySensorPrecision objects must also be examined."
    ::= { docsRphyRpdPhysEntSensorEntry 4 }

docsRphyRpdPhysEntSensorOperStatus OBJECT-TYPE
    SYNTAX        EntitySensorStatus
    MAX-ACCESS    read-only
    STATUS        current
    DESCRIPTION
            "The operational status of the sensor."
    ::= { docsRphyRpdPhysEntSensorEntry 5 }

docsRphyRpdPhysEntSensorUnitsDisplay OBJECT-TYPE
    SYNTAX      SnmpAdminString
    MAX-ACCESS  read-only
    STATUS      current
    DESCRIPTION
            "A textual description of the data units that should be used
            in the display of docsRphyRpdEntPhySensorValue."
    ::= { docsRphyRpdPhysEntSensorEntry 6 }

docsRphyRpdPhysEntSensorValueTimeStamp OBJECT-TYPE
    SYNTAX        TimeStamp
    MAX-ACCESS    read-only
    STATUS        current
    DESCRIPTION
            "The value of sysUpTime at the time the status and/or value
            of this sensor was last obtained by the agent."
    ::= { docsRphyRpdPhysEntSensorEntry 7 }

docsRphyRpdPhysEntSensorValueUpdateRate  OBJECT-TYPE
    SYNTAX        Unsigned32
    UNITS         "milliseconds"
    MAX-ACCESS    read-only
    STATUS        current
    DESCRIPTION
            "An indication of the frequency that the agent updates the
            associated docsRphyRpdEntPhySensorValue object, representing in
            milliseconds.

            The value zero indicates:

                - the sensor value is updated on demand (e.g.,
                  when polled by the agent for a get-request),
                - the sensor value is updated when the sensor
                  value changes (event-driven),
                - the agent does not know the update rate.
            "
    ::= { docsRphyRpdPhysEntSensorEntry 8 }
  
-- ---------------------------------------------------------------------
-- RPD Interface Group Objects Derived from IF-MIB RFC 2863
-- ---------------------------------------------------------------------  

-- ---------------------------------------------------------------------
-- RPD Ethernet Interface Table Objects
-- ---------------------------------------------------------------------
docsRphyRpdEnetIfTable OBJECT-TYPE
    SYNTAX      SEQUENCE OF DocsRphyRpdEnetIfEntry
    MAX-ACCESS  not-accessible
    STATUS      current
    DESCRIPTION
            "A list of interface entries.  The number of entries is
            given by the value of docsRphyRpdEnetIfNumber."
    ::= { docsRphyRpdIfMibObjects 1 }

docsRphyRpdEnetIfEntry OBJECT-TYPE
    SYNTAX      DocsRphyRpdEnetIfEntry
    MAX-ACCESS  not-accessible
    STATUS      current
    DESCRIPTION
            "An entry containing management information applicable to a
            particular interface.
            The Ethernet IfIndex is chosen by the RPD."
    INDEX   { docsRphyRpdInfoUniqueId,
              docsRphyRpdEnetIfIndex }
    ::= { docsRphyRpdEnetIfTable 1 }

DocsRphyRpdEnetIfEntry ::=
    SEQUENCE {
        docsRphyRpdEnetIfIndex                 InterfaceIndex,
        docsRphyRpdEnetIfDescr                 DisplayString,
        docsRphyRpdEnetIfName                  DisplayString,
        docsRphyRpdEnetIfAlias                 DisplayString,
        docsRphyRpdEnetIfType                  IANAifType,
        docsRphyRpdEnetIfMtu                   Integer32,
        docsRphyRpdEnetIfPhysAddress           PhysAddress,
        docsRphyRpdEnetIfAdminStatus           INTEGER,
        docsRphyRpdEnetIfOperStatus            INTEGER,
        docsRphyRpdEnetIfLastChange            TimeTicks,
        docsRphyRpdEnetIfLinkUpDownTrapEnable  INTEGER,
        docsRphyRpdEnetIfHighSpeed             Gauge32,
        docsRphyRpdEnetIfPromiscuousMode       TruthValue,
        docsRphyRpdEnetIfConnectorPresent      TruthValue       
    }

docsRphyRpdEnetIfIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { docsRphyRpdEnetIfEntry 1 }

docsRphyRpdEnetIfDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { docsRphyRpdEnetIfEntry 2 }
    
docsRphyRpdEnetIfName OBJECT-TYPE
    SYNTAX      DisplayString
    MAX-ACCESS  read-only
    STATUS      current
    DESCRIPTION
            "The textual name of the interface.  The value of this
            object should be the name of the interface as assigned by
            the local device and should be suitable for use in commands
            entered at the device's `console'.  This might be a text
            name, such as `le0' or a simple port number, such as `1',
            depending on the interface naming syntax of the device.  If
            several entries in the docsRphyRpdEnetIfTable together represent a single
            interface as named by the device, then each will have the
            same value of docsRphyRpdEnetIfName.  Note that for an agent which responds
            to SNMP queries concerning an interface on some other
            (proxied) device, then the value of docsRphyRpdEnetIfName for such an
            interface is the proxied device's local name for it.

            If there is no local name, or this object is otherwise not
            applicable, then this object contains a zero-length string."
    ::= { docsRphyRpdEnetIfEntry 3 }

docsRphyRpdEnetIfAlias   OBJECT-TYPE
    SYNTAX      DisplayString (SIZE(0..64))
    MAX-ACCESS  read-write
    STATUS      current
    DESCRIPTION
            "This object is an 'alias' name for the interface as
            specified by a network manager, and provides a non-volatile
            'handle' for the interface.

            On the first instantiation of an interface, the value of
            docsRphyRpdEnetIfAlias associated with that interface is the zero-length
            string.  As and when a value is written into an instance of
            docsRphyRpdEnetIfAlias through a network management set operation, then the
            agent must retain the supplied value in the docsRphyRpdEnetIfAlias instance
            associated with the same interface for as long as that
            interface remains instantiated, including across all re-
            initializations/reboots of the network management system,
            including those which result in a change of the interface's
            docsRphyRpdEnetIfIndex value.

            An example of the value which a network manager might store
            in this object for a WAN interface is the (Telco's) circuit
            number/identifier of the interface.

            Some agents may support write-access only for interfaces
            having particular values of docsRphyRpdEnetIfType.  An agent which supports
            write access to this object is required to keep the value in
            non-volatile storage, but it may limit the length of new
            values depending on how much storage is already occupied by
            the current values for other interfaces."
    ::= { docsRphyRpdEnetIfEntry 4 }

docsRphyRpdEnetIfType OBJECT-TYPE
    SYNTAX      IANAifType
    MAX-ACCESS  read-only
    STATUS      current
    DESCRIPTION
            "The type of interface.  Additional values for docsRphyRpdEnetIfType are
            assigned by the Internet Assigned Numbers Authority (IANA),
            through updating the syntax of the IANAifType textual
            convention."
    ::= { docsRphyRpdEnetIfEntry 5 }

docsRphyRpdEnetIfMtu OBJECT-TYPE
    SYNTAX      Integer32
    MAX-ACCESS  read-only
    STATUS      current
    DESCRIPTION
            "The size of the largest packet which can be sent/received
            on the interface, specified in octets.  For interfaces that
            are used for transmitting network datagrams, this is the
            size of the largest network datagram that can be sent on the
            interface."
    ::= { docsRphyRpdEnetIfEntry 6 }

docsRphyRpdEnetIfPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { docsRphyRpdEnetIfEntry 7 }

docsRphyRpdEnetIfAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            docsRphyRpdEnetIfAdminStatus in the down(2) state.  As a result of either
            explicit management action or per configuration information
            retained by the managed system, docsRphyRpdEnetIfAdminStatus is then
            changed to either the up(1) or testing(3) states (or remains
            in the down(2) state)."
    ::= { docsRphyRpdEnetIfEntry 8 }

docsRphyRpdEnetIfOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If docsRphyRpdEnetIfAdminStatus is down(2) then docsRphyRpdEnetIfOperStatus
            should be down(2).  If docsRphyRpdEnetIfAdminStatus is changed to up(1)
            then docsRphyRpdEnetIfOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { docsRphyRpdEnetIfEntry 9 }

docsRphyRpdEnetIfLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { docsRphyRpdEnetIfEntry 10 }

docsRphyRpdEnetIfLinkUpDownTrapEnable  OBJECT-TYPE
    SYNTAX      INTEGER { enabled(1), disabled(2) }
    MAX-ACCESS  read-write
    STATUS      current
    DESCRIPTION
            "Indicates whether linkUp/linkDown traps should be generated
            for this interface.

            By default, this object should have the value enabled(1) for
            interfaces which do not operate on 'top' of any other
            interface (as defined in the docsRphyRpdEnetIfStackTable), and disabled(2)
            otherwise."
    ::= { docsRphyRpdEnetIfEntry 11 }

docsRphyRpdEnetIfHighSpeed OBJECT-TYPE
    SYNTAX      Gauge32
    MAX-ACCESS  read-only
    STATUS      current
    DESCRIPTION
            "An estimate of the interface's current bandwidth in units
            of 1,000,000 bits per second.  If this object reports a
            value of `n' then the speed of the interface is somewhere in
            the range of `n-500,000' to `n+499,999'.  For interfaces
            which do not vary in bandwidth or for those where no
            accurate estimation can be made, this object should contain
            the nominal bandwidth.  For a sub-layer which has no concept
            of bandwidth, this object should be zero."
    ::= { docsRphyRpdEnetIfEntry 12 }

docsRphyRpdEnetIfPromiscuousMode  OBJECT-TYPE
    SYNTAX      TruthValue
    MAX-ACCESS  read-write
    STATUS      current
    DESCRIPTION
            "This object has a value of false(2) if this interface only
            accepts packets/frames that are addressed to this station.
            This object has a value of true(1) when the station accepts
            all packets/frames transmitted on the media.  The value
            true(1) is only legal on certain types of media.  If legal,
            setting this object to a value of true(1) may require the
            interface to be reset before becoming effective.

            The value of docsRphyRpdEnetIfPromiscuousMode does not affect the reception
            of broadcast and multicast packets/frames by the interface."
    ::= { docsRphyRpdEnetIfEntry 13 }

docsRphyRpdEnetIfConnectorPresent   OBJECT-TYPE
    SYNTAX      TruthValue
    MAX-ACCESS  read-only
    STATUS      current
    DESCRIPTION
            "This object has the value 'true(1)' if the interface
            sublayer has a physical connector and the value 'false(2)'
            otherwise."
    ::= { docsRphyRpdEnetIfEntry 14 }

    
-- ---------------------------------------------------------------------
-- RPD Ethernet Interface Stats Table Objects 
-- ---------------------------------------------------------------------
docsRphyRpdEnetIfStatsTable        OBJECT-TYPE
    SYNTAX      SEQUENCE OF DocsRphyRpdEnetIfStatsEntry
    MAX-ACCESS  not-accessible
    STATUS      current
    DESCRIPTION
            "A list of interface entries.  The number of entries is
            given by the value of ifNumber.  This table contains
            statistical objects for the interface table."
    ::= { docsRphyRpdIfMibObjects 2 }

docsRphyRpdEnetIfStatsEntry        OBJECT-TYPE
    SYNTAX      DocsRphyRpdEnetIfStatsEntry
    MAX-ACCESS  not-accessible
    STATUS      current
    DESCRIPTION
            "An entry containing statistical information
            applicable to a particular interface."
    AUGMENTS    { docsRphyRpdEnetIfEntry }
    ::= { docsRphyRpdEnetIfStatsTable 1 }

DocsRphyRpdEnetIfStatsEntry ::=
    SEQUENCE {
        docsRphyRpdEnetIfStatsInOctets            Counter64,
        docsRphyRpdEnetIfStatsOutOctets           Counter64,
        docsRphyRpdEnetIfStatsInFrames            Counter64,
        docsRphyRpdEnetIfStatsOutFrames           Counter64,
        docsRphyRpdEnetIfStatsInUnicastOctets     Counter64,
        docsRphyRpdEnetIfStatsOutUnicastOctets    Counter64,
        docsRphyRpdEnetIfStatsInUnicastFrames     Counter64,
        docsRphyRpdEnetIfStatsOutUnicastFrames    Counter64,
        docsRphyRpdEnetIfStatsInMulticastOctets   Counter64,
        docsRphyRpdEnetIfStatsOutMulticastOctets  Counter64,
        docsRphyRpdEnetIfStatsInMulticastFrames   Counter64,
        docsRphyRpdEnetIfStatsOutMulticastFrames  Counter64,
        docsRphyRpdEnetIfStatsInBroadcastOctets    Counter64,
        docsRphyRpdEnetIfStatsOutBroadcastOctets  Counter64,
        docsRphyRpdEnetIfStatsInBroadcastFrames   Counter64,
        docsRphyRpdEnetIfStatsOutBroadcastFrames  Counter64,
        docsRphyRpdEnetIfStatsInDiscards          Counter64,
        docsRphyRpdEnetIfStatsOutDiscards         Counter64,
        docsRphyRpdEnetIfStatsInErrors            Counter64,
        docsRphyRpdEnetIfStatsOutErrors           Counter64,
        docsRphyRpdEnetIfStatsInUnknownProtos     Counter64,
        docsRphyRpdEnetIfStatsCounterDiscontinuityTime TimeStamp
    }

docsRphyRpdEnetIfStatsInOctets OBJECT-TYPE
    SYNTAX      Counter64
    MAX-ACCESS  read-only
    STATUS      current
    DESCRIPTION
            "The total number of octets received on the interface,
            including framing characters.  

            Discontinuities in the value of this counter can occur at
            re-initialization of the management system, and at other
            times as indicated by the value of
            docsRphyRpdEnetIfCounterDiscontinuityTime."
    ::= { docsRphyRpdEnetIfStatsEntry 1 }
    
docsRphyRpdEnetIfStatsOutOctets OBJECT-TYPE
    SYNTAX      Counter64
    MAX-ACCESS  read-only
    STATUS      current
    DESCRIPTION
            "The total number of octets transmitted out of the
            interface, including framing characters.  

            Discontinuities in the value of this counter can occur at
            re-initialization of the management system, and at other
            times as indicated by the value of
            docsRphyRpdEnetIfCounterDiscontinuityTime."
    ::= { docsRphyRpdEnetIfStatsEntry 2 }
    
docsRphyRpdEnetIfStatsInFrames OBJECT-TYPE
    SYNTAX      Counter64
    MAX-ACCESS  read-only
    STATUS      current
    DESCRIPTION
            "The total number of frames received on the interface,
            including framing characters.  

            Discontinuities in the value of this counter can occur at
            re-initialization of the management system, and at other
            times as indicated by the value of
            docsRphyRpdEnetIfCounterDiscontinuityTime."
    ::= { docsRphyRpdEnetIfStatsEntry 3 }
    
docsRphyRpdEnetIfStatsOutFrames OBJECT-TYPE
    SYNTAX      Counter64
    MAX-ACCESS  read-only
    STATUS      current
    DESCRIPTION
            "The total number of frames transmitted out of the
            interface, including framing characters.  

            Discontinuities in the value of this counter can occur at
            re-initialization of the management system, and at other
            times as indicated by the value of
            docsRphyRpdEnetIfCounterDiscontinuityTime."
    ::= { docsRphyRpdEnetIfStatsEntry 4 }
    
docsRphyRpdEnetIfStatsInUnicastOctets OBJECT-TYPE
    SYNTAX      Counter64
    MAX-ACCESS  read-only
    STATUS      current
    DESCRIPTION
            "The number of octets, delivered by this sub-layer to a
            higher (sub-)layer, which were not addressed to a multicast
            or broadcast address at this sub-layer.  

            Discontinuities in the value of this counter can occur at
            re-initialization of the management system, and at other
            times as indicated by the value of
            docsRphyRpdEnetIfCounterDiscontinuityTime."
    ::= { docsRphyRpdEnetIfStatsEntry 5 }
   
docsRphyRpdEnetIfStatsOutUnicastOctets OBJECT-TYPE
    SYNTAX      Counter64
    MAX-ACCESS  read-only
    STATUS      current
    DESCRIPTION
            "The total number of octets that higher-level protocols
            requested be transmitted, and which were not addressed to a
            multicast or broadcast address at this sub-layer, including
            those that were discarded or not sent.  

            Discontinuities in the value of this counter can occur at
            re-initialization of the management system, and at other
            times as indicated by the value of
            docsRphyRpdEnetIfCounterDiscontinuityTime."
    ::= { docsRphyRpdEnetIfStatsEntry 6 }
     
docsRphyRpdEnetIfStatsInUnicastFrames OBJECT-TYPE
    SYNTAX      Counter64
    MAX-ACCESS  read-only
    STATUS      current
    DESCRIPTION
            "The number of frames, delivered by this sub-layer to a
            higher (sub-)layer, which were not addressed to a multicast
            or broadcast address at this sub-layer.  

            Discontinuities in the value of this counter can occur at
            re-initialization of the management system, and at other
            times as indicated by the value of
            docsRphyRpdEnetIfCounterDiscontinuityTime."
    ::= { docsRphyRpdEnetIfStatsEntry 7 }
    
docsRphyRpdEnetIfStatsOutUnicastFrames OBJECT-TYPE
    SYNTAX      Counter64
    MAX-ACCESS  read-only
    STATUS      current
    DESCRIPTION
            "The total number of frames that higher-level protocols
            requested be transmitted, and which were not addressed to a
            multicast or broadcast address at this sub-layer, including
            those that were discarded or not sent.  

            Discontinuities in the value of this counter can occur at
            re-initialization of the management system, and at other
            times as indicated by the value of
            docsRphyRpdEnetIfCounterDiscontinuityTime."
    ::= { docsRphyRpdEnetIfStatsEntry 8 }
    
docsRphyRpdEnetIfStatsInMulticastOctets OBJECT-TYPE
    SYNTAX      Counter64
    MAX-ACCESS  read-only
    STATUS      current
    DESCRIPTION
            "The number of octets, delivered by this sub-layer to a
            higher (sub-)layer, which were addressed to a multicast
            address at this sub-layer.  For a MAC layer protocol, this
            includes both Group and Functional addresses.

            Discontinuities in the value of this counter can occur at
            re-initialization of the management system, and at other
            times as indicated by the value of
            docsRphyRpdEnetIfCounterDiscontinuityTime."
    ::= { docsRphyRpdEnetIfStatsEntry 9 }
    
docsRphyRpdEnetIfStatsOutMulticastOctets OBJECT-TYPE
    SYNTAX      Counter64
    MAX-ACCESS  read-only
    STATUS      current
    DESCRIPTION
            "The total number of octets that higher-level protocols
            requested be transmitted, and which were addressed to a
            multicast address at this sub-layer, including those that
            were discarded or not sent.  For a MAC layer protocol, this
            includes both Group and Functional addresses.

            Discontinuities in the value of this counter can occur at
            re-initialization of the management system, and at other
            times as indicated by the value of
            docsRphyRpdEnetIfCounterDiscontinuityTime."
    ::= { docsRphyRpdEnetIfStatsEntry 10 }
    
docsRphyRpdEnetIfStatsInMulticastFrames OBJECT-TYPE
    SYNTAX      Counter64
    MAX-ACCESS  read-only
    STATUS      current
    DESCRIPTION
            "The number of frames, delivered by this sub-layer to a
            higher (sub-)layer, which were addressed to a multicast
            address at this sub-layer.  For a MAC layer protocol, this
            includes both Group and Functional addresses.

            Discontinuities in the value of this counter can occur at
            re-initialization of the management system, and at other
            times as indicated by the value of
            docsRphyRpdEnetIfCounterDiscontinuityTime."
    ::= { docsRphyRpdEnetIfStatsEntry 11 }

docsRphyRpdEnetIfStatsOutMulticastFrames OBJECT-TYPE
    SYNTAX      Counter64
    MAX-ACCESS  read-only
    STATUS      current
    DESCRIPTION
            "The total number of frames that higher-level protocols
            requested be transmitted, and which were addressed to a
            multicast address at this sub-layer, including those that
            were discarded or not sent.  For a MAC layer protocol, this
            includes both Group and Functional addresses.

            Discontinuities in the value of this counter can occur at
            re-initialization of the management system, and at other
            times as indicated by the value of
            docsRphyRpdEnetIfCounterDiscontinuityTime."
    ::= { docsRphyRpdEnetIfStatsEntry 12 }
    
docsRphyRpdEnetIfStatsInBroadcastOctets OBJECT-TYPE
    SYNTAX      Counter64
    MAX-ACCESS  read-only
    STATUS      current
    DESCRIPTION
            "The number of octets, delivered by this sub-layer to a
            higher (sub-)layer, which were addressed to a broadcast
            address at this sub-layer.

            Discontinuities in the value of this counter can occur at
            re-initialization of the management system, and at other
            times as indicated by the value of
            docsRphyRpdEnetIfCounterDiscontinuityTime."
    ::= { docsRphyRpdEnetIfStatsEntry 13 }

docsRphyRpdEnetIfStatsOutBroadcastOctets OBJECT-TYPE
    SYNTAX      Counter64
    MAX-ACCESS  read-only
    STATUS      current
    DESCRIPTION
            "The total number of octets that higher-level protocols
            requested be transmitted, and which were addressed to a
            broadcast address at this sub-layer, including those that
            were discarded or not sent.

            Discontinuities in the value of this counter can occur at
            re-initialization of the management system, and at other
            times as indicated by the value of
            docsRphyRpdEnetIfCounterDiscontinuityTime."
    ::= { docsRphyRpdEnetIfStatsEntry 14 }

docsRphyRpdEnetIfStatsInBroadcastFrames OBJECT-TYPE
    SYNTAX      Counter64
    MAX-ACCESS  read-only
    STATUS      current
    DESCRIPTION
            "The number of frames, delivered by this sub-layer to a
            higher (sub-)layer, which were addressed to a broadcast
            address at this sub-layer.

            Discontinuities in the value of this counter can occur at
            re-initialization of the management system, and at other
            times as indicated by the value of
            docsRphyRpdEnetIfCounterDiscontinuityTime."
    ::= { docsRphyRpdEnetIfStatsEntry 15 }

docsRphyRpdEnetIfStatsOutBroadcastFrames OBJECT-TYPE
    SYNTAX      Counter64
    MAX-ACCESS  read-only
    STATUS      current
    DESCRIPTION
            "The total number of frames that higher-level protocols
            requested be transmitted, and which were addressed to a
            broadcast address at this sub-layer, including those that
            were discarded or not sent.

            Discontinuities in the value of this counter can occur at
            re-initialization of the management system, and at other
            times as indicated by the value of
            docsRphyRpdEnetIfCounterDiscontinuityTime."
    ::= { docsRphyRpdEnetIfStatsEntry 16 }

docsRphyRpdEnetIfStatsInDiscards OBJECT-TYPE
    SYNTAX      Counter64
    MAX-ACCESS  read-only
    STATUS      current
    DESCRIPTION
            "The number of inbound packets which were chosen to be
            discarded even though no errors had been detected to prevent
            their being deliverable to a higher-layer protocol.  One
            possible reason for discarding such a packet could be to
            free up buffer space.

            Discontinuities in the value of this counter can occur at
            re-initialization of the management system, and at other
            times as indicated by the value of
            docsRphyRpdEnetIfCounterDiscontinuityTime."
    ::= { docsRphyRpdEnetIfStatsEntry 17 }

docsRphyRpdEnetIfStatsOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            docsRphyRpdEnetIfCounterDiscontinuityTime."
    ::= { docsRphyRpdEnetIfStatsEntry 18 }
    
docsRphyRpdEnetIfStatsInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            docsRphyRpdEnetIfCounterDiscontinuityTime."
    ::= { docsRphyRpdEnetIfStatsEntry 19 }

docsRphyRpdEnetIfStatsOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            docsRphyRpdEnetIfCounterDiscontinuityTime."
    ::= { docsRphyRpdEnetIfStatsEntry 20 }
    
docsRphyRpdEnetIfStatsInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            docsRphyRpdEnetIfCounterDiscontinuityTime."
    ::= { docsRphyRpdEnetIfStatsEntry 21 }

docsRphyRpdEnetIfStatsCounterDiscontinuityTime OBJECT-TYPE
    SYNTAX      TimeStamp
    MAX-ACCESS  read-only
    STATUS      current
    DESCRIPTION
            "The value of sysUpTime on the most recent occasion at which
            any one or more of this interface's counters suffered a
            discontinuity.  The relevant counters are the specific
            instances associated with this interface of any Counter32 or
            Counter64 object contained in the docsRphyRpdEnetIfStatsTable.  If
            no such discontinuities have occurred since the last re-
            initialization of the local management subsystem, then this
            object contains a zero value."
    ::= { docsRphyRpdEnetIfStatsEntry 22 }
    
-- ---------------------------------------------------------------------
-- RPD IP Group Objects Derived from IP-MIB RFC 4293
-- ---------------------------------------------------------------------

-- ---------------------------------------------------------------------
-- IPv4 Scalar Group Objects
-- ---------------------------------------------------------------------
docsRphyRpdIpv4GrpTable OBJECT-TYPE
    SYNTAX     SEQUENCE OF DocsRphyRpdIpv4GrpEntry
    MAX-ACCESS not-accessible
    STATUS     current
    DESCRIPTION
           "The table containing per-RPD IPv4-specific
            information."
    ::= { docsRphyRpdIpMibObjects 1 }

docsRphyRpdIpv4GrpEntry OBJECT-TYPE
    SYNTAX     DocsRphyRpdIpv4GrpEntry
    MAX-ACCESS not-accessible
    STATUS     current
    DESCRIPTION
           "An entry containing IPv4-specific information for a specific
            RPD."
    INDEX { docsRphyRpdInfoUniqueId }
    ::= { docsRphyRpdIpv4GrpTable 1 }

DocsRphyRpdIpv4GrpEntry ::= SEQUENCE {
        docsRphyRpdIpv4GrpIpForwarding               INTEGER,
        docsRphyRpdIpv4GrpDefaultTTL                 Integer32,
        docsRphyRpdIpv4GrpReasmTimeout               Integer32,
        docsRphyRpdIpv4GrpInterfaceTableLastChange   TimeStamp
    }
    
docsRphyRpdIpv4GrpIpForwarding OBJECT-TYPE
    SYNTAX     INTEGER {
                    forwarding(1),    -- acting as a router
                    notForwarding(2)  -- NOT acting as a router
               }
    MAX-ACCESS read-write
    STATUS     current
    DESCRIPTION
           "The indication of whether this entity is acting as an IPv4
            router in respect to the forwarding of datagrams received
            by, but not addressed to, this entity.  IPv4 routers forward
            datagrams.  IPv4 hosts do not (except those source-routed
            via the host).

            When this object is written, the entity should save the
            change to non-volatile storage and restore the object from
            non-volatile storage upon re-initialization of the system.
            Note: a stronger requirement is not used because this object
            was previously defined."
    ::= { docsRphyRpdIpv4GrpEntry 1 }

docsRphyRpdIpv4GrpDefaultTTL OBJECT-TYPE
    SYNTAX     Integer32 (1..255)
    MAX-ACCESS read-write
    STATUS     current
    DESCRIPTION
           "The default value inserted into the Time-To-Live field of
            the IPv4 header of datagrams originated at this entity,
            whenever a TTL value is not supplied by the transport layer
            protocol.

            When this object is written, the entity should save the
            change to non-volatile storage and restore the object from
            non-volatile storage upon re-initialization of the system.
            Note: a stronger requirement is not used because this object
            was previously defined."
    ::= { docsRphyRpdIpv4GrpEntry 2 }

docsRphyRpdIpv4GrpReasmTimeout OBJECT-TYPE
    SYNTAX     Integer32
    UNITS      "seconds"
    MAX-ACCESS read-only
    STATUS     current
    DESCRIPTION
           "The maximum number of seconds that received fragments are
            held while they are awaiting reassembly at this entity."
    ::= { docsRphyRpdIpv4GrpEntry 3 }
    
docsRphyRpdIpv4GrpInterfaceTableLastChange OBJECT-TYPE
    SYNTAX     TimeStamp
    MAX-ACCESS read-only
    STATUS     current
    DESCRIPTION
           "The value of sysUpTime on the most recent occasion at which
            a row in the docsRphyRpdIpv4InterfaceTable was added or deleted, or
            when an docsRphyRpdIpv4InterfaceReasmMaxSize or an
            docsRphyRpdIpv4InterfaceEnableStatus object was modified.

            If new objects are added to the docsRphyRpdIpv4InterfaceTable that
            require the docsRphyRpdIpv4InterfaceTableLastChange to be updated when
            they are modified, they must specify that requirement in
            their description clause."
    ::= { docsRphyRpdIpv4GrpEntry 4 }

-- ---------------------------------------------------------------------
-- IPv6 Scalar Group Objects
-- ---------------------------------------------------------------------
docsRphyRpdIpv6GrpTable OBJECT-TYPE
    SYNTAX     SEQUENCE OF DocsRphyRpdIpv6GrpEntry
    MAX-ACCESS not-accessible
    STATUS     current
    DESCRIPTION
           "The table containing per-RPD IPv6-specific
            information."
    ::= { docsRphyRpdIpMibObjects 2 }

docsRphyRpdIpv6GrpEntry OBJECT-TYPE
    SYNTAX     DocsRphyRpdIpv6GrpEntry
    MAX-ACCESS not-accessible
    STATUS     current
    DESCRIPTION
           "An entry containing IPv6-specific information for a specific
            RPD."
    INDEX { docsRphyRpdInfoUniqueId }
    ::= { docsRphyRpdIpv6GrpTable 1 }

DocsRphyRpdIpv6GrpEntry ::= SEQUENCE {
        docsRphyRpdIpv6GrpIpForwarding             INTEGER,
        docsRphyRpdIpv6GrpIpDefaultHopLimit        Integer32, 
        docsRphyRpdIpv6GrpInterfaceTableLastChange TimeStamp,
        docsRphyRpdIpv6GrpIfStatsTableLastChange   TimeStamp
    }
    
docsRphyRpdIpv6GrpIpForwarding OBJECT-TYPE
    SYNTAX     INTEGER {
                    forwarding(1),    -- acting as a router
                    notForwarding(2)  -- NOT acting as a router
               }
    MAX-ACCESS read-write
    STATUS     current
    DESCRIPTION
           "The indication of whether this entity is acting as an IPv6
            router on any interface in respect to the forwarding of
            datagrams received by, but not addressed to, this entity.
            IPv6 routers forward datagrams.  IPv6 hosts do not (except
            those source-routed via the host).

            When this object is written, the entity SHOULD save the
            change to non-volatile storage and restore the object from
            non-volatile storage upon re-initialization of the system."
    ::= { docsRphyRpdIpv6GrpEntry 1 }

docsRphyRpdIpv6GrpIpDefaultHopLimit OBJECT-TYPE
    SYNTAX     Integer32 (0..255)
    MAX-ACCESS read-write
    STATUS     current
    DESCRIPTION
           "The default value inserted into the Hop Limit field of the
            IPv6 header of datagrams originated at this entity whenever
            a Hop Limit value is not supplied by the transport layer
            protocol.

            When this object is written, the entity SHOULD save the
            change to non-volatile storage and restore the object from
            non-volatile storage upon re-initialization of the system."
    REFERENCE "RFC 2461 Section 6.3.2"
    ::= { docsRphyRpdIpv6GrpEntry 2 }
    
docsRphyRpdIpv6GrpInterfaceTableLastChange OBJECT-TYPE
    SYNTAX     TimeStamp
    MAX-ACCESS read-only
    STATUS     current
    DESCRIPTION
           "The value of sysUpTime on the most recent occasion at which
            a row in the docsRphyRpdIpv6InterfaceTable was added or deleted or when
            an docsRphyRpdIpv6InterfaceReasmMaxSize, docsRphyRpdIpv6InterfaceIdentifier,
            docsRphyRpdIpv6InterfaceEnableStatus, docsRphyRpdIpv6InterfaceReachableTime,
            docsRphyRpdIpv6InterfaceRetransmitTime, or docsRphyRpdIpv6InterfaceForwarding
            object was modified.

            If new objects are added to the docsRphyRpdIpv6InterfaceTable that
            require the docsRphyRpdIpv6InterfaceTableLastChange to be updated when
            they are modified, they must specify that requirement in
            their description clause."
    ::= { docsRphyRpdIpv6GrpEntry 3 }
    
docsRphyRpdIpv6GrpIfStatsTableLastChange OBJECT-TYPE
    SYNTAX     TimeStamp
    MAX-ACCESS read-only
    STATUS     current
    DESCRIPTION
           "The value of sysUpTime on the most recent occasion at which
            a row in the docsRphyRpdIpIfStatsTable was added or deleted.

            If new objects are added to the docsRphyRpdIpIfStatsTable that require
            the docsRphyRpdIpIfStatsTableLastChange to be updated when they are
            modified, they must specify that requirement in their
            description clause."
    ::= { docsRphyRpdIpv6GrpEntry 4 }
    
-- ---------------------------------------------------------------------
-- IPv4 Interface Table
-- ---------------------------------------------------------------------

docsRphyRpdIpv4InterfaceTable OBJECT-TYPE
    SYNTAX     SEQUENCE OF DocsRphyRpdIpv4InterfaceEntry
    MAX-ACCESS not-accessible
    STATUS     current
    DESCRIPTION
           "The table containing per-interface IPv4-specific
            information."
    ::= { docsRphyRpdIpMibObjects 3 }

docsRphyRpdIpv4InterfaceEntry OBJECT-TYPE
    SYNTAX     DocsRphyRpdIpv4InterfaceEntry
    MAX-ACCESS not-accessible
    STATUS     current
    DESCRIPTION
           "An entry containing IPv4-specific information for a specific
            interface."
    INDEX { docsRphyRpdInfoUniqueId,
            docsRphyRpdIpv4InterfaceIfIndex }
    ::= { docsRphyRpdIpv4InterfaceTable 1 }

DocsRphyRpdIpv4InterfaceEntry ::= SEQUENCE {
        docsRphyRpdIpv4InterfaceIfIndex         InterfaceIndex,
        docsRphyRpdIpv4InterfaceReasmMaxSize    Integer32,
        docsRphyRpdIpv4InterfaceEnableStatus    INTEGER,
        docsRphyRpdIpv4InterfaceRetransmitTime  Unsigned32
    }

docsRphyRpdIpv4InterfaceIfIndex OBJECT-TYPE
    SYNTAX     InterfaceIndex
    MAX-ACCESS not-accessible
    STATUS     current
    DESCRIPTION
           "The index value that uniquely identifies the interface to
            which this entry is applicable.  The interface identified by
            a particular value of this index is the same interface as
            identified by the same value of the IF-MIB's ifIndex."
    ::= { docsRphyRpdIpv4InterfaceEntry 1 }

docsRphyRpdIpv4InterfaceReasmMaxSize OBJECT-TYPE
    SYNTAX     Integer32 (0..65535)
    MAX-ACCESS read-only
    STATUS     current
    DESCRIPTION
           "The size of the largest IPv4 datagram that this entity can
            re-assemble from incoming IPv4 fragmented datagrams received
            on this interface."
    ::= { docsRphyRpdIpv4InterfaceEntry 2 }

docsRphyRpdIpv4InterfaceEnableStatus OBJECT-TYPE
    SYNTAX     INTEGER {
                 up(1),
                 down(2)
    }
    MAX-ACCESS read-write
    STATUS     current
    DESCRIPTION
           "The indication of whether IPv4 is enabled (up) or disabled
            (down) on this interface.  This object does not affect the
            state of the interface itself, only its connection to an
            IPv4 stack.  The IF-MIB should be used to control the state
            of the interface."
    ::= { docsRphyRpdIpv4InterfaceEntry 3 }

docsRphyRpdIpv4InterfaceRetransmitTime OBJECT-TYPE
    SYNTAX     Unsigned32
    UNITS      "milliseconds"
    MAX-ACCESS read-only
    STATUS     current
    DESCRIPTION
           "The time between retransmissions of ARP requests to a
            neighbor when resolving the address or when probing the
            reachability of a neighbor."
    REFERENCE "RFC 1122"
    DEFVAL { 1000 }
    ::= { docsRphyRpdIpv4InterfaceEntry 4 }

-- ---------------------------------------------------------------------
-- IPv6 Interface Table
-- ---------------------------------------------------------------------

docsRphyRpdIpv6InterfaceTable OBJECT-TYPE
    SYNTAX     SEQUENCE OF DocsRphyRpdIpv6InterfaceEntry
    MAX-ACCESS not-accessible
    STATUS     current
    DESCRIPTION
           "The table containing per-interface IPv6-specific
            information."
    ::= { docsRphyRpdIpMibObjects 4 }

docsRphyRpdIpv6InterfaceEntry OBJECT-TYPE
    SYNTAX     DocsRphyRpdIpv6InterfaceEntry
    MAX-ACCESS not-accessible
    STATUS     current
    DESCRIPTION
           "An entry containing IPv6-specific information for a given
            interface."
    INDEX { docsRphyRpdInfoUniqueId,
            docsRphyRpdIpv6InterfaceIfIndex }
    ::= { docsRphyRpdIpv6InterfaceTable 1 }

DocsRphyRpdIpv6InterfaceEntry ::= SEQUENCE {
        docsRphyRpdIpv6InterfaceIfIndex         InterfaceIndex,
        docsRphyRpdIpv6InterfaceReasmMaxSize    Unsigned32,
        docsRphyRpdIpv6InterfaceIdentifier      Ipv6AddressIfIdentifierTC,
        docsRphyRpdIpv6InterfaceEnableStatus    INTEGER,
        docsRphyRpdIpv6InterfaceReachableTime   Unsigned32,
        docsRphyRpdIpv6InterfaceRetransmitTime  Unsigned32,
        docsRphyRpdIpv6InterfaceForwarding      INTEGER
    }

docsRphyRpdIpv6InterfaceIfIndex OBJECT-TYPE
    SYNTAX     InterfaceIndex
    MAX-ACCESS not-accessible
    STATUS     current
    DESCRIPTION
           "The index value that uniquely identifies the interface to
            which this entry is applicable.  The interface identified by
            a particular value of this index is the same interface as
            identified by the same value of the IF-MIB's ifIndex."
    ::= { docsRphyRpdIpv6InterfaceEntry 1 }

docsRphyRpdIpv6InterfaceReasmMaxSize OBJECT-TYPE
    SYNTAX     Unsigned32 (1500..65535)
    UNITS      "octets"
    MAX-ACCESS read-only
    STATUS     current
    DESCRIPTION
           "The size of the largest IPv6 datagram that this entity can
            re-assemble from incoming IPv6 fragmented datagrams received
            on this interface."
    ::= { docsRphyRpdIpv6InterfaceEntry 2 }

docsRphyRpdIpv6InterfaceIdentifier OBJECT-TYPE
    SYNTAX     Ipv6AddressIfIdentifierTC
    MAX-ACCESS read-only
    STATUS     current
    DESCRIPTION
           "The Interface Identifier for this interface.  The Interface
            Identifier is combined with an address prefix to form an
            interface address.

            By default, the Interface Identifier is auto-configured
            according to the rules of the link type to which this
            interface is attached.

            A zero length identifier may be used where appropriate.  One
            possible example is a loopback interface."
    ::= { docsRphyRpdIpv6InterfaceEntry 3 }

docsRphyRpdIpv6InterfaceEnableStatus OBJECT-TYPE
    SYNTAX     INTEGER {
                 up(1),
                 down(2)
    }
    MAX-ACCESS read-write
    STATUS     current
    DESCRIPTION
           "The indication of whether IPv6 is enabled (up) or disabled
            (down) on this interface.  This object does not affect the
            state of the interface itself, only its connection to an
            IPv6 stack.  The IF-MIB should be used to control the state
            of the interface.

            When this object is written, the entity SHOULD save the
            change to non-volatile storage and restore the object from
            non-volatile storage upon re-initialization of the system."
    ::= { docsRphyRpdIpv6InterfaceEntry 5 }

docsRphyRpdIpv6InterfaceReachableTime OBJECT-TYPE
    SYNTAX     Unsigned32
    UNITS      "milliseconds"
    MAX-ACCESS read-only
    STATUS     current
    DESCRIPTION
           "The time a neighbor is considered reachable after receiving
            a reachability confirmation."
    REFERENCE "RFC 2461, Section 6.3.2"
    ::= { docsRphyRpdIpv6InterfaceEntry 6 }

docsRphyRpdIpv6InterfaceRetransmitTime OBJECT-TYPE
    SYNTAX     Unsigned32
    UNITS      "milliseconds"
    MAX-ACCESS read-only
    STATUS     current
    DESCRIPTION
           "The time between retransmissions of Neighbor Solicitation
            messages to a neighbor when resolving the address or when
            probing the reachability of a neighbor."
    REFERENCE "RFC 2461, Section 6.3.2"
    ::= { docsRphyRpdIpv6InterfaceEntry 7 }

docsRphyRpdIpv6InterfaceForwarding OBJECT-TYPE
    SYNTAX     INTEGER {
                    forwarding(1),    -- acting as a router
                    notForwarding(2)  -- NOT acting as a router
               }
    MAX-ACCESS read-write
    STATUS     current
    DESCRIPTION
           "The indication of whether this entity is acting as an IPv6
            router on this interface with respect to the forwarding of
            datagrams received by, but not addressed to, this entity.
            IPv6 routers forward datagrams.  IPv6 hosts do not (except
            those source-routed via the host).

            This object is constrained by docsRphyRpdIpv6IpForwarding and is
            ignored if docsRphyRpdIpv6IpForwarding is set to notForwarding.  Those
            systems that do not provide per-interface control of the
            forwarding function should set this object to forwarding for
            all interfaces and allow the docsRphyRpdIpv6IpForwarding object to
            control the forwarding capability.

            When this object is written, the entity SHOULD save the
            change to non-volatile storage and restore the object from
            non-volatile storage upon re-initialization of the system."
    ::= { docsRphyRpdIpv6InterfaceEntry 8 }


-- ---------------------------------------------------------------------
-- Per-Interface IP Statistics Table
-- ---------------------------------------------------------------------

docsRphyRpdIpIfStatsTable OBJECT-TYPE
    SYNTAX     SEQUENCE OF DocsRphyRpdIpIfStatsEntry
    MAX-ACCESS not-accessible
    STATUS     current
    DESCRIPTION
           "The table containing per-interface traffic statistics.  This
            table and the docsRphyRpdIpSystemStatsTable contain similar objects
            whose difference is in their granularity.  Where this table
            contains per-interface statistics, the docsRphyRpdIpSystemStatsTable
            contains the same statistics, but counted on a system wide
            basis."
    ::= { docsRphyRpdIpMibObjects 5 }

docsRphyRpdIpIfStatsEntry OBJECT-TYPE
    SYNTAX     DocsRphyRpdIpIfStatsEntry
    MAX-ACCESS not-accessible
    STATUS     current
    DESCRIPTION
           "An interface statistics entry containing objects for a
            particular interface and version of IP."
    INDEX { docsRphyRpdInfoUniqueId,
            docsRphyRpdIpIfStatsIPVersion, 
            docsRphyRpdIpIfStatsIfIndex }
    ::= { docsRphyRpdIpIfStatsTable 1 }

DocsRphyRpdIpIfStatsEntry ::= SEQUENCE {
        docsRphyRpdIpIfStatsIPVersion           InetVersion,
        docsRphyRpdIpIfStatsIfIndex             InterfaceIndex,
        docsRphyRpdIpIfStatsInReceives          Counter32,
        docsRphyRpdIpIfStatsHCInReceives        Counter64,
        docsRphyRpdIpIfStatsInOctets            Counter32,
        docsRphyRpdIpIfStatsHCInOctets          Counter64,
        docsRphyRpdIpIfStatsInHdrErrors         Counter32,
        docsRphyRpdIpIfStatsInNoRoutes          Counter32,
        docsRphyRpdIpIfStatsInAddrErrors        Counter32,
        docsRphyRpdIpIfStatsInUnknownProtos     Counter32,
        docsRphyRpdIpIfStatsInTruncatedPkts     Counter32,
        docsRphyRpdIpIfStatsInForwDatagrams     Counter32,
        docsRphyRpdIpIfStatsHCInForwDatagrams   Counter64,
        docsRphyRpdIpIfStatsReasmReqds          Counter32,
        docsRphyRpdIpIfStatsReasmOKs            Counter32,
        docsRphyRpdIpIfStatsReasmFails          Counter32,
        docsRphyRpdIpIfStatsInDiscards          Counter32,
        docsRphyRpdIpIfStatsInDelivers          Counter32,
        docsRphyRpdIpIfStatsHCInDelivers        Counter64,
        docsRphyRpdIpIfStatsOutRequests         Counter32,
        docsRphyRpdIpIfStatsHCOutRequests       Counter64,
        docsRphyRpdIpIfStatsOutForwDatagrams    Counter32,
        docsRphyRpdIpIfStatsHCOutForwDatagrams  Counter64,
        docsRphyRpdIpIfStatsOutDiscards         Counter32,
        docsRphyRpdIpIfStatsOutFragReqds        Counter32,
        docsRphyRpdIpIfStatsOutFragOKs          Counter32,
        docsRphyRpdIpIfStatsOutFragFails        Counter32,
        docsRphyRpdIpIfStatsOutFragCreates      Counter32,
        docsRphyRpdIpIfStatsOutTransmits        Counter32,
        docsRphyRpdIpIfStatsHCOutTransmits      Counter64,
        docsRphyRpdIpIfStatsOutOctets           Counter32,
        docsRphyRpdIpIfStatsHCOutOctets         Counter64,
        docsRphyRpdIpIfStatsInMcastPkts         Counter32,
        docsRphyRpdIpIfStatsHCInMcastPkts       Counter64,
        docsRphyRpdIpIfStatsInMcastOctets       Counter32,
        docsRphyRpdIpIfStatsHCInMcastOctets     Counter64,
        docsRphyRpdIpIfStatsOutMcastPkts        Counter32,
        docsRphyRpdIpIfStatsHCOutMcastPkts      Counter64,
        docsRphyRpdIpIfStatsOutMcastOctets      Counter32,
        docsRphyRpdIpIfStatsHCOutMcastOctets    Counter64,
        docsRphyRpdIpIfStatsInBcastPkts         Counter32,
        docsRphyRpdIpIfStatsHCInBcastPkts       Counter64,
        docsRphyRpdIpIfStatsOutBcastPkts        Counter32,
        docsRphyRpdIpIfStatsHCOutBcastPkts      Counter64,
        docsRphyRpdIpIfStatsDiscontinuityTime   TimeStamp,
        docsRphyRpdIpIfStatsRefreshRate         Unsigned32
    }

docsRphyRpdIpIfStatsIPVersion OBJECT-TYPE
    SYNTAX     InetVersion
    MAX-ACCESS not-accessible
    STATUS     current
    DESCRIPTION
           "The IP version of this row."
    ::= { docsRphyRpdIpIfStatsEntry 1 }

docsRphyRpdIpIfStatsIfIndex OBJECT-TYPE
    SYNTAX     InterfaceIndex
    MAX-ACCESS not-accessible
    STATUS     current
    DESCRIPTION
           "The index value that uniquely identifies the interface to
            which this entry is applicable.  The interface identified by
            a particular value of this index is the same interface as
            identified by the same value of the IF-MIB's ifIndex."
    ::= { docsRphyRpdIpIfStatsEntry 2 }

docsRphyRpdIpIfStatsInReceives OBJECT-TYPE
    SYNTAX     Counter32
    MAX-ACCESS read-only
    STATUS     current
    DESCRIPTION
           "The total number of input IP datagrams received, including
            those received in error.

            Discontinuities in the value of this counter can occur at
            re-initialization of the management system, and at other
            times as indicated by the value of
            docsRphyRpdIpIfStatsDiscontinuityTime."
    ::= { docsRphyRpdIpIfStatsEntry 3 }

docsRphyRpdIpIfStatsHCInReceives OBJECT-TYPE
    SYNTAX     Counter64
    MAX-ACCESS read-only
    STATUS     current
    DESCRIPTION
           "The total number of input IP datagrams received, including
            those received in error.  This object counts the same
            datagrams as docsRphyRpdIpIfStatsInReceives, but allows for larger
            values.

            Discontinuities in the value of this counter can occur at
            re-initialization of the management system, and at other
            times as indicated by the value of
            docsRphyRpdIpIfStatsDiscontinuityTime."
    ::= { docsRphyRpdIpIfStatsEntry 4 }

docsRphyRpdIpIfStatsInOctets OBJECT-TYPE
    SYNTAX     Counter32
    MAX-ACCESS read-only
    STATUS     current
    DESCRIPTION
           "The total number of octets received in input IP datagrams,
            including those received in error.  Octets from datagrams
            counted in docsRphyRpdIpIfStatsInReceives MUST be counted here.

            Discontinuities in the value of this counter can occur at
            re-initialization of the management system, and at other
            times as indicated by the value of
            docsRphyRpdIpIfStatsDiscontinuityTime."
    ::= { docsRphyRpdIpIfStatsEntry 5 }

docsRphyRpdIpIfStatsHCInOctets OBJECT-TYPE
    SYNTAX     Counter64
    MAX-ACCESS read-only
    STATUS     current
    DESCRIPTION
           "The total number of octets received in input IP datagrams,
            including those received in error.  This object counts the
            same octets as docsRphyRpdIpIfStatsInOctets, but allows for larger
            values.

            Discontinuities in the value of this counter can occur at
            re-initialization of the management system, and at other
            times as indicated by the value of
            docsRphyRpdIpIfStatsDiscontinuityTime."
    ::= { docsRphyRpdIpIfStatsEntry 6 }

docsRphyRpdIpIfStatsInHdrErrors OBJECT-TYPE
    SYNTAX     Counter32
    MAX-ACCESS read-only
    STATUS     current
    DESCRIPTION
           "The number of input IP datagrams discarded due to errors in
            their IP headers, including version number mismatch, other
            format errors, hop count exceeded, errors discovered in
            processing their IP options, etc.

            Discontinuities in the value of this counter can occur at
            re-initialization of the management system, and at other
            times as indicated by the value of
            docsRphyRpdIpIfStatsDiscontinuityTime."
    ::= { docsRphyRpdIpIfStatsEntry 7 }

docsRphyRpdIpIfStatsInNoRoutes OBJECT-TYPE
    SYNTAX     Counter32
    MAX-ACCESS read-only
    STATUS     current
    DESCRIPTION
           "The number of input IP datagrams discarded because no route
            could be found to transmit them to their destination.

            Discontinuities in the value of this counter can occur at
            re-initialization of the management system, and at other
            times as indicated by the value of
            docsRphyRpdIpIfStatsDiscontinuityTime."
    ::= { docsRphyRpdIpIfStatsEntry 8 }

docsRphyRpdIpIfStatsInAddrErrors OBJECT-TYPE
    SYNTAX     Counter32
    MAX-ACCESS read-only
    STATUS     current
    DESCRIPTION
           "The number of input IP datagrams discarded because the IP
            address in their IP header's destination field was not a
            valid address to be received at this entity.  This count
            includes invalid addresses (e.g., ::0).  For entities that
            are not IP routers and therefore do not forward datagrams,
            this counter includes datagrams discarded because the
            destination address was not a local address.

            Discontinuities in the value of this counter can occur at
            re-initialization of the management system, and at other
            times as indicated by the value of
            docsRphyRpdIpIfStatsDiscontinuityTime."
    ::= { docsRphyRpdIpIfStatsEntry 9 }

docsRphyRpdIpIfStatsInUnknownProtos OBJECT-TYPE
    SYNTAX     Counter32
    MAX-ACCESS read-only
    STATUS     current
    DESCRIPTION
           "The number of locally-addressed IP datagrams received
            successfully but discarded because of an unknown or
            unsupported protocol.

            When tracking interface statistics, the counter of the
            interface to which these datagrams were addressed is
            incremented.  This interface might not be the same as the
            input interface for some of the datagrams.

            Discontinuities in the value of this counter can occur at
            re-initialization of the management system, and at other
            times as indicated by the value of
            docsRphyRpdIpIfStatsDiscontinuityTime."
    ::= { docsRphyRpdIpIfStatsEntry 10 }

docsRphyRpdIpIfStatsInTruncatedPkts OBJECT-TYPE
    SYNTAX     Counter32
    MAX-ACCESS read-only
    STATUS     current
    DESCRIPTION
           "The number of input IP datagrams discarded because the
            datagram frame didn't carry enough data.

            Discontinuities in the value of this counter can occur at
            re-initialization of the management system, and at other
            times as indicated by the value of
            docsRphyRpdIpIfStatsDiscontinuityTime."
    ::= { docsRphyRpdIpIfStatsEntry 11 }

docsRphyRpdIpIfStatsInForwDatagrams OBJECT-TYPE
    SYNTAX     Counter32
    MAX-ACCESS read-only
    STATUS     current
    DESCRIPTION
           "The number of input datagrams for which this entity was not
            their final IP destination and for which this entity
            attempted to find a route to forward them to that final
            destination.  In entities that do not act as IP routers,
            this counter will include only those datagrams that were
            Source-Routed via this entity, and the Source-Route
            processing was successful.

            When tracking interface statistics, the counter of the
            incoming interface is incremented for each datagram.

            Discontinuities in the value of this counter can occur at
            re-initialization of the management system, and at other
            times as indicated by the value of
            docsRphyRpdIpIfStatsDiscontinuityTime."
    ::= { docsRphyRpdIpIfStatsEntry 12 }

docsRphyRpdIpIfStatsHCInForwDatagrams OBJECT-TYPE
    SYNTAX     Counter64
    MAX-ACCESS read-only
    STATUS     current
    DESCRIPTION
           "The number of input datagrams for which this entity was not
            their final IP destination and for which this entity
            attempted to find a route to forward them to that final
            destination.  This object counts the same packets as
            docsRphyRpdIpIfStatsInForwDatagrams, but allows for larger values.

            Discontinuities in the value of this counter can occur at
            re-initialization of the management system, and at other
            times as indicated by the value of
            docsRphyRpdIpIfStatsDiscontinuityTime."
    ::= { docsRphyRpdIpIfStatsEntry 13 }

docsRphyRpdIpIfStatsReasmReqds OBJECT-TYPE
    SYNTAX     Counter32
    MAX-ACCESS read-only
    STATUS     current
    DESCRIPTION
           "The number of IP fragments received that needed to be
            reassembled at this interface.

            When tracking interface statistics, the counter of the
            interface to which these fragments were addressed is
            incremented.  This interface might not be the same as the
            input interface for some of the fragments.

            Discontinuities in the value of this counter can occur at
            re-initialization of the management system, and at other
            times as indicated by the value of
            docsRphyRpdIpIfStatsDiscontinuityTime."
    ::= { docsRphyRpdIpIfStatsEntry 14 }

docsRphyRpdIpIfStatsReasmOKs OBJECT-TYPE
    SYNTAX     Counter32
    MAX-ACCESS read-only
    STATUS     current
    DESCRIPTION
           "The number of IP datagrams successfully reassembled.

            When tracking interface statistics, the counter of the
            interface to which these datagrams were addressed is
            incremented.  This interface might not be the same as the
            input interface for some of the datagrams.

            Discontinuities in the value of this counter can occur at
            re-initialization of the management system, and at other
            times as indicated by the value of
            docsRphyRpdIpIfStatsDiscontinuityTime."
    ::= { docsRphyRpdIpIfStatsEntry 15 }

docsRphyRpdIpIfStatsReasmFails OBJECT-TYPE
    SYNTAX     Counter32
    MAX-ACCESS read-only
    STATUS     current
    DESCRIPTION
           "The number of failures detected by the IP re-assembly
            algorithm (for whatever reason: timed out, errors, etc.).
            Note that this is not necessarily a count of discarded IP
            fragments since some algorithms (notably the algorithm in
            RFC 815) can lose track of the number of fragments by
            combining them as they are received.

            When tracking interface statistics, the counter of the
            interface to which these fragments were addressed is
            incremented.  This interface might not be the same as the
            input interface for some of the fragments.

            Discontinuities in the value of this counter can occur at
            re-initialization of the management system, and at other
            times as indicated by the value of
            docsRphyRpdIpIfStatsDiscontinuityTime."
    ::= { docsRphyRpdIpIfStatsEntry 16 }

docsRphyRpdIpIfStatsInDiscards OBJECT-TYPE
    SYNTAX     Counter32
    MAX-ACCESS read-only
    STATUS     current
    DESCRIPTION
           "The number of input IP datagrams for which no problems were
            encountered to prevent their continued processing, but
            were discarded (e.g., for lack of buffer space).  Note that
            this counter does not include any datagrams discarded while
            awaiting re-assembly.

            Discontinuities in the value of this counter can occur at
            re-initialization of the management system, and at other
            times as indicated by the value of
            docsRphyRpdIpIfStatsDiscontinuityTime."
    ::= { docsRphyRpdIpIfStatsEntry 17 }

docsRphyRpdIpIfStatsInDelivers OBJECT-TYPE
    SYNTAX     Counter32
    MAX-ACCESS read-only
    STATUS     current
    DESCRIPTION
           "The total number of datagrams successfully delivered to IP
            user-protocols (including ICMP).

            When tracking interface statistics, the counter of the
            interface to which these datagrams were addressed is
            incremented.  This interface might not be the same as the
            input interface for some of the datagrams.

            Discontinuities in the value of this counter can occur at
            re-initialization of the management system, and at other
            times as indicated by the value of
            docsRphyRpdIpIfStatsDiscontinuityTime."
    ::= { docsRphyRpdIpIfStatsEntry 18 }

docsRphyRpdIpIfStatsHCInDelivers OBJECT-TYPE
    SYNTAX     Counter64
    MAX-ACCESS read-only
    STATUS     current
    DESCRIPTION
           "The total number of datagrams successfully delivered to IP
            user-protocols (including ICMP).  This object counts the
            same packets as docsRphyRpdIpIfStatsInDelivers, but allows for larger
            values.

            Discontinuities in the value of this counter can occur at
            re-initialization of the management system, and at other
            times as indicated by the value of
            docsRphyRpdIpIfStatsDiscontinuityTime."
    ::= { docsRphyRpdIpIfStatsEntry 19 }

docsRphyRpdIpIfStatsOutRequests OBJECT-TYPE
    SYNTAX     Counter32
    MAX-ACCESS read-only
    STATUS     current
    DESCRIPTION
           "The total number of IP datagrams that local IP user-
            protocols (including ICMP) supplied to IP in requests for
            transmission.  Note that this counter does not include any
            datagrams counted in docsRphyRpdIpIfStatsOutForwDatagrams.

            Discontinuities in the value of this counter can occur at
            re-initialization of the management system, and at other
            times as indicated by the value of
            docsRphyRpdIpIfStatsDiscontinuityTime."
    ::= { docsRphyRpdIpIfStatsEntry 20 }

docsRphyRpdIpIfStatsHCOutRequests OBJECT-TYPE
    SYNTAX     Counter64
    MAX-ACCESS read-only
    STATUS     current
    DESCRIPTION
           "The total number of IP datagrams that local IP user-
            protocols (including ICMP) supplied to IP in requests for
            transmission.  This object counts the same packets as
            docsRphyRpdIpIfStatsOutRequests, but allows for larger values.

            Discontinuities in the value of this counter can occur at
            re-initialization of the management system, and at other
            times as indicated by the value of
            docsRphyRpdIpIfStatsDiscontinuityTime."
    ::= { docsRphyRpdIpIfStatsEntry 21 }

docsRphyRpdIpIfStatsOutForwDatagrams OBJECT-TYPE
    SYNTAX     Counter32
    MAX-ACCESS read-only
    STATUS     current
    DESCRIPTION
           "The number of datagrams for which this entity was not their
            final IP destination and for which it was successful in
            finding a path to their final destination.  In entities
            that do not act as IP routers, this counter will include
            only those datagrams that were Source-Routed via this
            entity, and the Source-Route processing was successful.

            When tracking interface statistics, the counter of the
            outgoing interface is incremented for a successfully
            forwarded datagram.

            Discontinuities in the value of this counter can occur at
            re-initialization of the management system, and at other
            times as indicated by the value of
            docsRphyRpdIpIfStatsDiscontinuityTime."
    ::= { docsRphyRpdIpIfStatsEntry 23 }

docsRphyRpdIpIfStatsHCOutForwDatagrams OBJECT-TYPE
    SYNTAX     Counter64
    MAX-ACCESS read-only
    STATUS     current
    DESCRIPTION
           "The number of datagrams for which this entity was not their
            final IP destination and for which it was successful in
            finding a path to their final destination.  This object
            counts the same packets as docsRphyRpdIpIfStatsOutForwDatagrams, but
            allows for larger values.

            Discontinuities in the value of this counter can occur at
            re-initialization of the management system, and at other
            times as indicated by the value of
            docsRphyRpdIpIfStatsDiscontinuityTime."
    ::= { docsRphyRpdIpIfStatsEntry 24 }

docsRphyRpdIpIfStatsOutDiscards OBJECT-TYPE
    SYNTAX     Counter32
    MAX-ACCESS read-only
    STATUS     current
    DESCRIPTION
           "The number of output IP datagrams for which no problem was
            encountered to prevent their transmission to their
            destination, but were discarded (e.g., for lack of
            buffer space).  Note that this counter would include
            datagrams counted in docsRphyRpdIpIfStatsOutForwDatagrams if any such
            datagrams met this (discretionary) discard criterion.

            Discontinuities in the value of this counter can occur at
            re-initialization of the management system, and at other
            times as indicated by the value of
            docsRphyRpdIpIfStatsDiscontinuityTime."
    ::= { docsRphyRpdIpIfStatsEntry 25 }

docsRphyRpdIpIfStatsOutFragReqds OBJECT-TYPE
    SYNTAX     Counter32
    MAX-ACCESS read-only
    STATUS     current
    DESCRIPTION
           "The number of IP datagrams that would require fragmentation
            in order to be transmitted.

            When tracking interface statistics, the counter of the
            outgoing interface is incremented for a successfully
            fragmented datagram.

            Discontinuities in the value of this counter can occur at
            re-initialization of the management system, and at other
            times as indicated by the value of
            docsRphyRpdIpIfStatsDiscontinuityTime."
    ::= { docsRphyRpdIpIfStatsEntry 26 }

docsRphyRpdIpIfStatsOutFragOKs OBJECT-TYPE
    SYNTAX     Counter32
    MAX-ACCESS read-only
    STATUS     current
    DESCRIPTION
           "The number of IP datagrams that have been successfully
            fragmented.

            When tracking interface statistics, the counter of the
            outgoing interface is incremented for a successfully
            fragmented datagram.

            Discontinuities in the value of this counter can occur at
            re-initialization of the management system, and at other
            times as indicated by the value of
            docsRphyRpdIpIfStatsDiscontinuityTime."
    ::= { docsRphyRpdIpIfStatsEntry 27 }

docsRphyRpdIpIfStatsOutFragFails OBJECT-TYPE
    SYNTAX     Counter32
    MAX-ACCESS read-only
    STATUS     current
    DESCRIPTION
           "The number of IP datagrams that have been discarded because
            they needed to be fragmented but could not be.  This
            includes IPv4 packets that have the DF bit set and IPv6
            packets that are being forwarded and exceed the outgoing
            link MTU.

            When tracking interface statistics, the counter of the
            outgoing interface is incremented for an unsuccessfully
            fragmented datagram.

            Discontinuities in the value of this counter can occur at
            re-initialization of the management system, and at other
            times as indicated by the value of
            docsRphyRpdIpIfStatsDiscontinuityTime."
    ::= { docsRphyRpdIpIfStatsEntry 28 }

docsRphyRpdIpIfStatsOutFragCreates OBJECT-TYPE
    SYNTAX     Counter32
    MAX-ACCESS read-only
    STATUS     current
    DESCRIPTION
           "The number of output datagram fragments that have been
            generated as a result of IP fragmentation.

            When tracking interface statistics, the counter of the
            outgoing interface is incremented for a successfully
            fragmented datagram.

            Discontinuities in the value of this counter can occur at
            re-initialization of the management system, and at other
            times as indicated by the value of
            docsRphyRpdIpIfStatsDiscontinuityTime."
    ::= { docsRphyRpdIpIfStatsEntry 29 }

docsRphyRpdIpIfStatsOutTransmits OBJECT-TYPE
    SYNTAX     Counter32
    MAX-ACCESS read-only
    STATUS     current
    DESCRIPTION
           "The total number of IP datagrams that this entity supplied
            to the lower layers for transmission.  This includes
            datagrams generated locally and those forwarded by this
            entity.

            Discontinuities in the value of this counter can occur at
            re-initialization of the management system, and at other
            times as indicated by the value of
            docsRphyRpdIpIfStatsDiscontinuityTime."
    ::= { docsRphyRpdIpIfStatsEntry 30 }

docsRphyRpdIpIfStatsHCOutTransmits OBJECT-TYPE
    SYNTAX     Counter64
    MAX-ACCESS read-only
    STATUS     current
    DESCRIPTION
           "The total number of IP datagrams that this entity supplied
            to the lower layers for transmission.  This object counts
            the same datagrams as docsRphyRpdIpIfStatsOutTransmits, but allows for
            larger values.

            Discontinuities in the value of this counter can occur at
            re-initialization of the management system, and at other
            times as indicated by the value of
            docsRphyRpdIpIfStatsDiscontinuityTime."
    ::= { docsRphyRpdIpIfStatsEntry 31 }

docsRphyRpdIpIfStatsOutOctets OBJECT-TYPE
    SYNTAX     Counter32
    MAX-ACCESS read-only
    STATUS     current
    DESCRIPTION
           "The total number of octets in IP datagrams delivered to the
            lower layers for transmission.  Octets from datagrams
            counted in docsRphyRpdIpIfStatsOutTransmits MUST be counted here.

            Discontinuities in the value of this counter can occur at
            re-initialization of the management system, and at other
            times as indicated by the value of
            docsRphyRpdIpIfStatsDiscontinuityTime."
    ::= { docsRphyRpdIpIfStatsEntry 32 }

docsRphyRpdIpIfStatsHCOutOctets OBJECT-TYPE
    SYNTAX     Counter64
    MAX-ACCESS read-only
    STATUS     current
    DESCRIPTION
           "The total number of octets in IP datagrams delivered to the
            lower layers for transmission.  This objects counts the same
            octets as docsRphyRpdIpIfStatsOutOctets, but allows for larger values.

            Discontinuities in the value of this counter can occur at
            re-initialization of the management system, and at other
            times as indicated by the value of
            docsRphyRpdIpIfStatsDiscontinuityTime."
    ::= { docsRphyRpdIpIfStatsEntry 33 }

docsRphyRpdIpIfStatsInMcastPkts OBJECT-TYPE
    SYNTAX     Counter32
    MAX-ACCESS read-only
    STATUS     current
    DESCRIPTION
           "The number of IP multicast datagrams received.

            Discontinuities in the value of this counter can occur at
            re-initialization of the management system, and at other
            times as indicated by the value of
            docsRphyRpdIpIfStatsDiscontinuityTime."
    ::= { docsRphyRpdIpIfStatsEntry 34 }

docsRphyRpdIpIfStatsHCInMcastPkts OBJECT-TYPE
    SYNTAX     Counter64
    MAX-ACCESS read-only
    STATUS     current
    DESCRIPTION
           "The number of IP multicast datagrams received.  This object
            counts the same datagrams as docsRphyRpdIpIfStatsInMcastPkts, but
            allows for larger values.

            Discontinuities in the value of this counter can occur at
            re-initialization of the management system, and at other
            times as indicated by the value of
            docsRphyRpdIpIfStatsDiscontinuityTime."
    ::= { docsRphyRpdIpIfStatsEntry 35 }

docsRphyRpdIpIfStatsInMcastOctets OBJECT-TYPE
    SYNTAX     Counter32
    MAX-ACCESS read-only
    STATUS     current
    DESCRIPTION
           "The total number of octets received in IP multicast
            datagrams.  Octets from datagrams counted in
            docsRphyRpdIpIfStatsInMcastPkts MUST be counted here.

            Discontinuities in the value of this counter can occur at
            re-initialization of the management system, and at other
            times as indicated by the value of
            docsRphyRpdIpIfStatsDiscontinuityTime."
    ::= { docsRphyRpdIpIfStatsEntry 36 }

docsRphyRpdIpIfStatsHCInMcastOctets OBJECT-TYPE
    SYNTAX     Counter64
    MAX-ACCESS read-only
    STATUS     current
    DESCRIPTION
           "The total number of octets received in IP multicast
            datagrams.  This object counts the same octets as
            docsRphyRpdIpIfStatsInMcastOctets, but allows for larger values.

            Discontinuities in the value of this counter can occur at
            re-initialization of the management system, and at other
            times as indicated by the value of
            docsRphyRpdIpIfStatsDiscontinuityTime."
    ::= { docsRphyRpdIpIfStatsEntry 37 }

docsRphyRpdIpIfStatsOutMcastPkts OBJECT-TYPE
    SYNTAX     Counter32
    MAX-ACCESS read-only
    STATUS     current
    DESCRIPTION
           "The number of IP multicast datagrams transmitted.

            Discontinuities in the value of this counter can occur at
            re-initialization of the management system, and at other
            times as indicated by the value of
            docsRphyRpdIpIfStatsDiscontinuityTime."
    ::= { docsRphyRpdIpIfStatsEntry 38 }

docsRphyRpdIpIfStatsHCOutMcastPkts OBJECT-TYPE
    SYNTAX     Counter64
    MAX-ACCESS read-only
    STATUS     current
    DESCRIPTION
           "The number of IP multicast datagrams transmitted.  This
            object counts the same datagrams as docsRphyRpdIpIfStatsOutMcastPkts,
            but allows for larger values.

            Discontinuities in the value of this counter can occur at
            re-initialization of the management system, and at other
            times as indicated by the value of
            docsRphyRpdIpIfStatsDiscontinuityTime."
    ::= { docsRphyRpdIpIfStatsEntry 39 }

docsRphyRpdIpIfStatsOutMcastOctets OBJECT-TYPE
    SYNTAX     Counter32
    MAX-ACCESS read-only
    STATUS     current
    DESCRIPTION
           "The total number of octets transmitted in IP multicast
            datagrams.  Octets from datagrams counted in
            docsRphyRpdIpIfStatsOutMcastPkts MUST be counted here.

            Discontinuities in the value of this counter can occur at
            re-initialization of the management system, and at other
            times as indicated by the value of
            docsRphyRpdIpIfStatsDiscontinuityTime."
    ::= { docsRphyRpdIpIfStatsEntry 40 }

docsRphyRpdIpIfStatsHCOutMcastOctets OBJECT-TYPE
    SYNTAX     Counter64
    MAX-ACCESS read-only
    STATUS     current
    DESCRIPTION
           "The total number of octets transmitted in IP multicast
            datagrams.  This object counts the same octets as
            docsRphyRpdIpIfStatsOutMcastOctets, but allows for larger values.

            Discontinuities in the value of this counter can occur at
            re-initialization of the management system, and at other
            times as indicated by the value of
            docsRphyRpdIpIfStatsDiscontinuityTime."
    ::= { docsRphyRpdIpIfStatsEntry 41 }

docsRphyRpdIpIfStatsInBcastPkts OBJECT-TYPE
    SYNTAX     Counter32
    MAX-ACCESS read-only
    STATUS     current
    DESCRIPTION
           "The number of IP broadcast datagrams received.

            Discontinuities in the value of this counter can occur at
            re-initialization of the management system, and at other
            times as indicated by the value of
            docsRphyRpdIpIfStatsDiscontinuityTime."
    ::= { docsRphyRpdIpIfStatsEntry 42 }

docsRphyRpdIpIfStatsHCInBcastPkts OBJECT-TYPE
    SYNTAX     Counter64
    MAX-ACCESS read-only
    STATUS     current
    DESCRIPTION
           "The number of IP broadcast datagrams received.  This object
            counts the same datagrams as docsRphyRpdIpIfStatsInBcastPkts, but
            allows for larger values.

            Discontinuities in the value of this counter can occur at
            re-initialization of the management system, and at other
            times as indicated by the value of
            docsRphyRpdIpIfStatsDiscontinuityTime."
    ::= { docsRphyRpdIpIfStatsEntry 43 }

docsRphyRpdIpIfStatsOutBcastPkts OBJECT-TYPE
    SYNTAX     Counter32
    MAX-ACCESS read-only
    STATUS     current
    DESCRIPTION
           "The number of IP broadcast datagrams transmitted.

            Discontinuities in the value of this counter can occur at
            re-initialization of the management system, and at other
            times as indicated by the value of
            docsRphyRpdIpIfStatsDiscontinuityTime."
    ::= { docsRphyRpdIpIfStatsEntry 44 }

docsRphyRpdIpIfStatsHCOutBcastPkts OBJECT-TYPE
    SYNTAX     Counter64
    MAX-ACCESS read-only
    STATUS     current
    DESCRIPTION
           "The number of IP broadcast datagrams transmitted.  This
            object counts the same datagrams as docsRphyRpdIpIfStatsOutBcastPkts,
            but allows for larger values.

            Discontinuities in the value of this counter can occur at
            re-initialization of the management system, and at other
            times as indicated by the value of
            docsRphyRpdIpIfStatsDiscontinuityTime."
    ::= { docsRphyRpdIpIfStatsEntry 45 }

docsRphyRpdIpIfStatsDiscontinuityTime OBJECT-TYPE
    SYNTAX     TimeStamp
    MAX-ACCESS read-only
    STATUS     current
    DESCRIPTION
           "The value of sysUpTime on the most recent occasion at which
            any one or more of this entry's counters suffered a
            discontinuity.

            If no such discontinuities have occurred since the last re-
            initialization of the local management subsystem, then this
            object contains a zero value."
    ::= { docsRphyRpdIpIfStatsEntry 46 }

docsRphyRpdIpIfStatsRefreshRate OBJECT-TYPE
    SYNTAX     Unsigned32
    UNITS "milli-seconds"
    MAX-ACCESS read-only
    STATUS     current
    DESCRIPTION
           "The minimum reasonable polling interval for this entry.
            This object provides an indication of the minimum amount of
            time required to update the counters in this entry."
    ::= { docsRphyRpdIpIfStatsEntry 47 }


-- ---------------------------------------------------------------------
-- Internet Address Table
-- ---------------------------------------------------------------------

docsRphyRpdIpAddressTable OBJECT-TYPE
    SYNTAX     SEQUENCE OF DocsRphyRpdIpAddressEntry
    MAX-ACCESS not-accessible
    STATUS     current
    DESCRIPTION
           "This table contains addressing information relevant to the
            entity's interfaces.

            This table does not contain multicast address information.
            Tables for such information should be contained in multicast
            specific MIBs, such as RFC 3019.

            While this table is writable, the user will note that
            several objects, such as docsRphyRpdIpAddressOrigin, are not.  The
            intention in allowing a user to write to this table is to
            allow them to add or remove any entry that isn't
            permanent.  The user should be allowed to modify objects
            and entries when that would not cause inconsistencies
            within the table.  Allowing write access to objects, such
            as docsRphyRpdIpAddressOrigin, could allow a user to insert an entry
            and then label it incorrectly.

            Note well: When including IPv6 link-local addresses in this
            table, the entry must use an InetAddressType of 'docsRphyRpdIpv6z' in
            order to differentiate between the possible interfaces."
    ::= { docsRphyRpdIpMibObjects 6 }

docsRphyRpdIpAddressEntry OBJECT-TYPE
    SYNTAX     DocsRphyRpdIpAddressEntry
    MAX-ACCESS not-accessible
    STATUS     current
    DESCRIPTION
           "An address mapping for a particular interface."
    INDEX { docsRphyRpdInfoUniqueId,
            docsRphyRpdIpAddressAddrType, 
            docsRphyRpdIpAddressAddr }
    ::= { docsRphyRpdIpAddressTable 1 }

DocsRphyRpdIpAddressEntry ::= SEQUENCE {
        docsRphyRpdIpAddressAddrType     InetAddressType,
        docsRphyRpdIpAddressAddr         InetAddress,
        docsRphyRpdIpAddressIfIndex      InterfaceIndex,
        docsRphyRpdIpAddressType         INTEGER,
        docsRphyRpdIpAddressPrefixLen    Unsigned32,
        docsRphyRpdIpAddressOrigin       IpAddressOriginTC,
        docsRphyRpdIpAddressStatus       IpAddressStatusTC,
        docsRphyRpdIpAddressCreated      TimeStamp,
        docsRphyRpdIpAddressLastChanged  TimeStamp
    }

docsRphyRpdIpAddressAddrType OBJECT-TYPE
    SYNTAX     InetAddressType
    MAX-ACCESS not-accessible
    STATUS     current
    DESCRIPTION
           "The address type of docsRphyRpdIpAddressAddr."
    ::= { docsRphyRpdIpAddressEntry 1 }

docsRphyRpdIpAddressAddr OBJECT-TYPE
    SYNTAX     InetAddress
    MAX-ACCESS not-accessible
    STATUS     current
    DESCRIPTION
           "The IP address to which this entry's addressing information
            pertains.  The address type of this object is specified in
            docsRphyRpdIpAddressAddrType.

            Implementors need to be aware that if the size of
            docsRphyRpdIpAddressAddr exceeds 116 octets, then OIDS of instances of
            columns in this row will have more than 128 sub-identifiers
            and cannot be accessed using SNMPv1, SNMPv2c, or SNMPv3."
    ::= { docsRphyRpdIpAddressEntry 2 }

docsRphyRpdIpAddressIfIndex OBJECT-TYPE
    SYNTAX     InterfaceIndex
    MAX-ACCESS read-create
    STATUS     current
    DESCRIPTION
           "The index value that uniquely identifies the interface to
            which this entry is applicable.  The interface identified by
            a particular value of this index is the same interface as
            identified by the same value of the IF-MIB's ifIndex."
    ::= { docsRphyRpdIpAddressEntry 3 }

docsRphyRpdIpAddressType OBJECT-TYPE
    SYNTAX     INTEGER {
                 unicast(1),
                 anycast(2),
                 broadcast(3)
    }
    MAX-ACCESS read-create
    STATUS     current
    DESCRIPTION
           "The type of address.  broadcast(3) is not a valid value for
            IPv6 addresses (RFC 3513)."
    DEFVAL { unicast }
    ::= { docsRphyRpdIpAddressEntry 4 }

docsRphyRpdIpAddressPrefixLen OBJECT-TYPE
    SYNTAX     Unsigned32
    MAX-ACCESS read-only
    STATUS     current
    DESCRIPTION
           "The prefix length."
    DEFVAL { 0 }
    ::= { docsRphyRpdIpAddressEntry 5 }

docsRphyRpdIpAddressOrigin OBJECT-TYPE
    SYNTAX     IpAddressOriginTC
    MAX-ACCESS read-only
    STATUS     current
    DESCRIPTION
           "The origin of the address."
    ::= { docsRphyRpdIpAddressEntry 6 }

docsRphyRpdIpAddressStatus OBJECT-TYPE
    SYNTAX     IpAddressStatusTC
    MAX-ACCESS read-create
    STATUS     current
    DESCRIPTION
           "The status of the address, describing if the address can be
            used for communication.

            In the absence of other information, an IPv4 address is
            always preferred(1)."
    DEFVAL { preferred }
    ::= { docsRphyRpdIpAddressEntry 7 }

docsRphyRpdIpAddressCreated OBJECT-TYPE
    SYNTAX     TimeStamp
    MAX-ACCESS read-only
    STATUS     current
    DESCRIPTION
           "The value of sysUpTime at the time this entry was created.
            If this entry was created prior to the last re-
            initialization of the local network management subsystem,
            then this object contains a zero value."
    ::= { docsRphyRpdIpAddressEntry 8 }

docsRphyRpdIpAddressLastChanged OBJECT-TYPE
    SYNTAX     TimeStamp
    MAX-ACCESS read-only
    STATUS     current
    DESCRIPTION
           "The value of sysUpTime at the time this entry was last
            updated.  If this entry was updated prior to the last re-
            initialization of the local network management subsystem,
            then this object contains a zero value."
    ::= { docsRphyRpdIpAddressEntry 9 }
    

-- ---------------------------------------------------------------------
-- Internet Address Translation Table
-- ---------------------------------------------------------------------

docsRphyRpdIpNetToPhysicalTable OBJECT-TYPE
    SYNTAX     SEQUENCE OF DocsRphyRpdIpNetToPhysicalEntry
    MAX-ACCESS not-accessible
    STATUS     current
    DESCRIPTION
           "The IP Address Translation table used for mapping from IP
            addresses to physical addresses.

            The Address Translation tables contain the IP address to
            'physical' address equivalences.  Some interfaces do not use
            translation tables for determining address equivalences
            (e.g., DDN-X.25 has an algorithmic method); if all
            interfaces are of this type, then the Address Translation
            table is empty, i.e., has zero entries.

            While many protocols may be used to populate this table, ARP
            and Neighbor Discovery are the most likely
            options."
    REFERENCE "RFC 826 and RFC 2461"
    ::= { docsRphyRpdIpMibObjects 7 }

docsRphyRpdIpNetToPhysicalEntry OBJECT-TYPE
    SYNTAX     DocsRphyRpdIpNetToPhysicalEntry
    MAX-ACCESS not-accessible
    STATUS     current
    DESCRIPTION
           "Each entry contains one IP address to `physical' address
            equivalence."
    INDEX       { docsRphyRpdInfoUniqueId,
                  docsRphyRpdIpNetToPhysicalIfIndex,
                  docsRphyRpdIpNetToPhysicalNetAddressType,
                  docsRphyRpdIpNetToPhysicalNetAddress }
    ::= { docsRphyRpdIpNetToPhysicalTable 1 }

DocsRphyRpdIpNetToPhysicalEntry ::= SEQUENCE {
        docsRphyRpdIpNetToPhysicalIfIndex         InterfaceIndex,
        docsRphyRpdIpNetToPhysicalNetAddressType  InetAddressType,
        docsRphyRpdIpNetToPhysicalNetAddress      InetAddress,
        docsRphyRpdIpNetToPhysicalPhysAddress     PhysAddress,
        docsRphyRpdIpNetToPhysicalLastUpdated     TimeStamp,
        docsRphyRpdIpNetToPhysicalType            INTEGER,
        docsRphyRpdIpNetToPhysicalState           INTEGER
    }

docsRphyRpdIpNetToPhysicalIfIndex OBJECT-TYPE
    SYNTAX     InterfaceIndex
    MAX-ACCESS not-accessible
    STATUS     current
    DESCRIPTION
           "The index value that uniquely identifies the interface to
            which this entry is applicable.  The interface identified by
            a particular value of this index is the same interface as
            identified by the same value of the IF-MIB's ifIndex."
    ::= { docsRphyRpdIpNetToPhysicalEntry 1 }

docsRphyRpdIpNetToPhysicalNetAddressType OBJECT-TYPE
    SYNTAX     InetAddressType
    MAX-ACCESS not-accessible
    STATUS     current
    DESCRIPTION
           "The type of docsRphyRpdIpNetToPhysicalNetAddress."
    ::= { docsRphyRpdIpNetToPhysicalEntry 2 }

docsRphyRpdIpNetToPhysicalNetAddress OBJECT-TYPE
    SYNTAX     InetAddress
    MAX-ACCESS not-accessible
    STATUS     current
    DESCRIPTION
           "The IP Address corresponding to the media-dependent
            `physical' address.  The address type of this object is
            specified in docsRphyRpdIpNetToPhysicalAddressType.

            Implementors need to be aware that if the size of
            docsRphyRpdIpNetToPhysicalNetAddress exceeds 115 octets, then OIDS of
            instances of columns in this row will have more than 128
            sub-identifiers and cannot be accessed using SNMPv1,
            SNMPv2c, or SNMPv3."
    ::= { docsRphyRpdIpNetToPhysicalEntry 3 }

docsRphyRpdIpNetToPhysicalPhysAddress OBJECT-TYPE
    SYNTAX     PhysAddress (SIZE(0..65535))
    MAX-ACCESS read-create
    STATUS     current
    DESCRIPTION
           "The media-dependent `physical' address.

            As the entries in this table are typically not persistent
            when this object is written the entity SHOULD NOT save the
            change to non-volatile storage."
    ::= { docsRphyRpdIpNetToPhysicalEntry 4 }

docsRphyRpdIpNetToPhysicalLastUpdated OBJECT-TYPE
    SYNTAX     TimeStamp
    MAX-ACCESS read-only
    STATUS     current
    DESCRIPTION
           "The value of sysUpTime at the time this entry was last
            updated.  If this entry was updated prior to the last re-
            initialization of the local network management subsystem,
            then this object contains a zero value."
    ::= { docsRphyRpdIpNetToPhysicalEntry 5 }

docsRphyRpdIpNetToPhysicalType OBJECT-TYPE
    SYNTAX     INTEGER {
                other(1),        -- none of the following
                invalid(2),      -- an invalidated mapping
                dynamic(3),
                static(4),
                local(5)         -- local interface
            }
    MAX-ACCESS read-create
    STATUS     current
    DESCRIPTION
           "The type of mapping.

            Setting this object to the value invalid(2) has the effect
            of invalidating the corresponding entry in the
            docsRphyRpdIpNetToPhysicalTable.  That is, it effectively dis-
            associates the interface identified with said entry from the
            mapping identified with said entry.  It is an
            implementation-specific matter as to whether the agent
            removes an invalidated entry from the table.  Accordingly,
            management stations must be prepared to receive tabular
            information from agents that corresponds to entries not
            currently in use.  Proper interpretation of such entries
            requires examination of the relevant docsRphyRpdIpNetToPhysicalType
            object.

            The 'dynamic(3)' type indicates that the IP address to
            physical addresses mapping has been dynamically resolved
            using e.g., IPv4 ARP or the IPv6 Neighbor Discovery
            protocol.

            The 'static(4)' type indicates that the mapping has been
            statically configured.  Both of these refer to entries that
            provide mappings for other entities addresses.

            The 'local(5)' type indicates that the mapping is provided
            for an entity's own interface address.

            As the entries in this table are typically not persistent
            when this object is written the entity SHOULD NOT save the
            change to non-volatile storage."
    DEFVAL { static }
    ::= { docsRphyRpdIpNetToPhysicalEntry 6 }

docsRphyRpdIpNetToPhysicalState OBJECT-TYPE
    SYNTAX     INTEGER {
                     reachable(1), -- confirmed reachability

                     stale(2),     -- unconfirmed reachability

                     delay(3),     -- waiting for reachability
                                   -- confirmation before entering
                                   -- the probe state

                     probe(4),     -- actively probing

                     invalid(5),   -- an invalidated mapping

                     unknown(6),   -- state can not be determined
                                   -- for some reason.

                     incomplete(7) -- address resolution is being
                                   -- performed.
                    }
    MAX-ACCESS read-only
    STATUS     current
    DESCRIPTION
           "The Neighbor Unreachability Detection state for the
            interface when the address mapping in this entry is used.
            If Neighbor Unreachability Detection is not in use (e.g. for
            IPv4), this object is always unknown(6)."
    REFERENCE "RFC 2461"
    ::= { docsRphyRpdIpNetToPhysicalEntry 7 }

-- ---------------------------------------------------------------------
-- Default Router Table
-- ---------------------------------------------------------------------

docsRphyRpdIpDefaultRouterTable OBJECT-TYPE
    SYNTAX     SEQUENCE OF DocsRphyRpdIpDefaultRouterEntry
    MAX-ACCESS not-accessible
    STATUS     current
    DESCRIPTION
           "The table used to describe the default routers known to this
            entity."
    ::= { docsRphyRpdIpMibObjects 8 }

docsRphyRpdIpDefaultRouterEntry OBJECT-TYPE
    SYNTAX     DocsRphyRpdIpDefaultRouterEntry
    MAX-ACCESS not-accessible
    STATUS     current
    DESCRIPTION
           "Each entry contains information about a default router known
            to this entity."
    INDEX { docsRphyRpdInfoUniqueId,
            docsRphyRpdIpDefaultRouterAddressType, 
            docsRphyRpdIpDefaultRouterAddress,
            docsRphyRpdIpDefaultRouterIfIndex }
    ::= { docsRphyRpdIpDefaultRouterTable 1 }

DocsRphyRpdIpDefaultRouterEntry ::= SEQUENCE {
        docsRphyRpdIpDefaultRouterAddressType  InetAddressType,
        docsRphyRpdIpDefaultRouterAddress      InetAddress,
        docsRphyRpdIpDefaultRouterIfIndex      InterfaceIndex,
        docsRphyRpdIpDefaultRouterLifetime     Unsigned32,
        docsRphyRpdIpDefaultRouterPreference   INTEGER
    }

docsRphyRpdIpDefaultRouterAddressType OBJECT-TYPE
    SYNTAX     InetAddressType
    MAX-ACCESS not-accessible
    STATUS     current
    DESCRIPTION
           "The address type for this row."
    ::= { docsRphyRpdIpDefaultRouterEntry 1 }

docsRphyRpdIpDefaultRouterAddress OBJECT-TYPE
    SYNTAX     InetAddress
    MAX-ACCESS not-accessible
    STATUS     current
    DESCRIPTION
           "The IP address of the default router represented by this
            row.  The address type of this object is specified in
            docsRphyRpdIpDefaultRouterAddressType.

            Implementers need to be aware that if the size of
            docsRphyRpdIpDefaultRouterAddress exceeds 115 octets, then OIDS of
            instances of columns in this row will have more than 128
            sub-identifiers and cannot be accessed using SNMPv1,
            SNMPv2c, or SNMPv3."
    ::= { docsRphyRpdIpDefaultRouterEntry 2 }

docsRphyRpdIpDefaultRouterIfIndex OBJECT-TYPE
    SYNTAX     InterfaceIndex
    MAX-ACCESS not-accessible
    STATUS     current
    DESCRIPTION
           "The index value that uniquely identifies the interface by
            which the router can be reached.  The interface identified
            by a particular value of this index is the same interface as
            identified by the same value of the IF-MIB's ifIndex."
    ::= { docsRphyRpdIpDefaultRouterEntry 3 }

docsRphyRpdIpDefaultRouterLifetime OBJECT-TYPE
    SYNTAX     Unsigned32 (0..65535)
    UNITS      "seconds"
    MAX-ACCESS read-only
    STATUS     current
    DESCRIPTION
           "The remaining length of time, in seconds, that this router
            will continue to be useful as a default router.  A value of
            zero indicates that it is no longer useful as a default
            router.  It is left to the implementer of the MIB as to
            whether a router with a lifetime of zero is removed from the
            list.

            For IPv6, this value should be extracted from the router
            advertisement messages."
    REFERENCE "For IPv6 RFC 2462 sections 4.2 and 6.3.4"
    ::= { docsRphyRpdIpDefaultRouterEntry 4 }

docsRphyRpdIpDefaultRouterPreference OBJECT-TYPE
    SYNTAX     INTEGER {
                     reserved (-2),
                     low (-1),
                     medium (0),
                     high (1)
                    }
    MAX-ACCESS read-only
    STATUS     current
    DESCRIPTION
           "An indication of preference given to this router as a
            default router as described in he Default Router
            Preferences document.  Treating the value as a
            2 bit signed integer allows for simple arithmetic
            comparisons.

            For IPv4 routers or IPv6 routers that are not using the
            updated router advertisement format, this object is set to
            medium (0)."
    REFERENCE "RFC 4291, section 2.1"
    ::= { docsRphyRpdIpDefaultRouterEntry 5 }


-- ---------------------------------------------------------------------
-- ICMP non-message-specific counters Table
-- ---------------------------------------------------------------------

docsRphyRpdIpIcmpStatsTable OBJECT-TYPE
    SYNTAX     SEQUENCE OF DocsRphyRpdIpIcmpStatsEntry
    MAX-ACCESS not-accessible
    STATUS     current
    DESCRIPTION
           "The table of generic system-wide ICMP counters."
    ::= { docsRphyRpdIpIcmpMibObjects 1 }

docsRphyRpdIpIcmpStatsEntry OBJECT-TYPE
    SYNTAX     DocsRphyRpdIpIcmpStatsEntry
    MAX-ACCESS not-accessible
    STATUS     current
    DESCRIPTION
           "A conceptual row in the docsRphyRpdIpIcmpStatsTable."
    INDEX    { docsRphyRpdInfoUniqueId,
               docsRphyRpdIpIcmpStatsIPVersion }
    ::= { docsRphyRpdIpIcmpStatsTable 1 }

DocsRphyRpdIpIcmpStatsEntry ::= SEQUENCE {
        docsRphyRpdIpIcmpStatsIPVersion  InetVersion,
        docsRphyRpdIpIcmpStatsInMsgs     Counter32,
        docsRphyRpdIpIcmpStatsInErrors   Counter32,
        docsRphyRpdIpIcmpStatsOutMsgs    Counter32,
        docsRphyRpdIpIcmpStatsOutErrors  Counter32
    }

docsRphyRpdIpIcmpStatsIPVersion OBJECT-TYPE
    SYNTAX     InetVersion
    MAX-ACCESS not-accessible
    STATUS     current
    DESCRIPTION
           "The IP version of the statistics."
    ::= { docsRphyRpdIpIcmpStatsEntry 1 }

docsRphyRpdIpIcmpStatsInMsgs OBJECT-TYPE
    SYNTAX     Counter32
    MAX-ACCESS read-only
    STATUS     current
    DESCRIPTION
           "The total number of ICMP messages that the entity received.
            Note that this counter includes all those counted by
            docsRphyRpdIpIcmpStatsInErrors."
    ::= { docsRphyRpdIpIcmpStatsEntry 2 }

docsRphyRpdIpIcmpStatsInErrors OBJECT-TYPE
    SYNTAX     Counter32
    MAX-ACCESS read-only
    STATUS     current
    DESCRIPTION
           "The number of ICMP messages that the entity received but
            determined as having ICMP-specific errors (bad ICMP
            checksums, bad length, etc.)."
    ::= { docsRphyRpdIpIcmpStatsEntry 3 }

docsRphyRpdIpIcmpStatsOutMsgs OBJECT-TYPE
    SYNTAX     Counter32
    MAX-ACCESS read-only
    STATUS     current
    DESCRIPTION
           "The total number of ICMP messages that the entity attempted
            to send.  Note that this counter includes all those counted
            by docsRphyRpdIpIcmpStatsOutErrors."
    ::= { docsRphyRpdIpIcmpStatsEntry 4 }

docsRphyRpdIpIcmpStatsOutErrors OBJECT-TYPE
    SYNTAX     Counter32
    MAX-ACCESS read-only
    STATUS     current
    DESCRIPTION
           "The number of ICMP messages that this entity did not send
            due to problems discovered within ICMP, such as a lack of
            buffers.  This value should not include errors discovered
            outside the ICMP layer, such as the inability of IP to route
            the resultant datagram.  In some implementations, there may
            be no types of error that contribute to this counter's
            value."
    ::= { docsRphyRpdIpIcmpStatsEntry 5 }


-- ---------------------------------------------------------------------
-- ICMP per-version, per-message type ICMP counters Table
-- ---------------------------------------------------------------------

docsRphyRpdIpIcmpMsgStatsTable OBJECT-TYPE
    SYNTAX     SEQUENCE OF DocsRphyRpdIpIcmpMsgStatsEntry
    MAX-ACCESS not-accessible
    STATUS     current
    DESCRIPTION
           "The table of system-wide per-version, per-message type ICMP
            counters."
    ::= { docsRphyRpdIpIcmpMibObjects 2 }

docsRphyRpdIpIcmpMsgStatsEntry OBJECT-TYPE
    SYNTAX     DocsRphyRpdIpIcmpMsgStatsEntry
    MAX-ACCESS not-accessible
    STATUS     current
    DESCRIPTION
           "A conceptual row in the docsRphyRpdIpIcmpMsgStatsTable.

            The system should track each ICMP type value, even if that
            ICMP type is not supported by the system.  However, a
            given row need not be instantiated unless a message of that
            type has been processed, i.e., the row for
            docsRphyRpdIpIcmpMsgStatsType=X MAY be instantiated before but MUST be
            instantiated after the first message with Type=X is
            received or transmitted.  After receiving or transmitting
            any succeeding messages with Type=X, the relevant counter
            must be incremented."
    INDEX { docsRphyRpdInfoUniqueId,
            docsRphyRpdIpIcmpMsgStatsIPVersion, 
            docsRphyRpdIpIcmpMsgStatsType }
    ::= { docsRphyRpdIpIcmpMsgStatsTable 1 }

DocsRphyRpdIpIcmpMsgStatsEntry ::= SEQUENCE {
        docsRphyRpdIpIcmpMsgStatsIPVersion  InetVersion,
        docsRphyRpdIpIcmpMsgStatsType       Integer32,
        docsRphyRpdIpIcmpMsgStatsInPkts     Counter32,
        docsRphyRpdIpIcmpMsgStatsOutPkts    Counter32
    }

docsRphyRpdIpIcmpMsgStatsIPVersion OBJECT-TYPE
    SYNTAX     InetVersion
    MAX-ACCESS not-accessible
    STATUS     current
    DESCRIPTION
           "The IP version of the statistics."
    ::= { docsRphyRpdIpIcmpMsgStatsEntry 1 }

docsRphyRpdIpIcmpMsgStatsType OBJECT-TYPE
    SYNTAX     Integer32 (0..255)
    MAX-ACCESS not-accessible
    STATUS     current
    DESCRIPTION
           "The ICMP type field of the message type being counted by
            this row.

            Note that ICMP message types are scoped by the address type
            in use."
    REFERENCE "http://www.iana.org/assignments/icmp-parameters and
               http://www.iana.org/assignments/icmpv6-parameters"
    ::= { docsRphyRpdIpIcmpMsgStatsEntry 2 }

docsRphyRpdIpIcmpMsgStatsInPkts OBJECT-TYPE
    SYNTAX     Counter32
    MAX-ACCESS read-only
    STATUS     current
    DESCRIPTION
           "The number of input packets for this AF and type."
    ::= { docsRphyRpdIpIcmpMsgStatsEntry 3 }

docsRphyRpdIpIcmpMsgStatsOutPkts OBJECT-TYPE
    SYNTAX     Counter32
    MAX-ACCESS read-only
    STATUS     current
    DESCRIPTION
           "The number of output packets for this AF and type."
    ::= { docsRphyRpdIpIcmpMsgStatsEntry 4 }

-- ---------------------------------------------------------------------
-- CCAP Core Group Objects
-- ---------------------------------------------------------------------
                 
-- ---------------------------------------------------------
-- Core L2TP Session Info Table 
-- ---------------------------------------------------------
                 
docsRphyCcapL2tpSessionInfoTable OBJECT-TYPE
    SYNTAX      SEQUENCE OF DocsRphyCcapL2tpSessionInfoEntry
    MAX-ACCESS  not-accessible
    STATUS      current
    DESCRIPTION
            "This table provides details for every session that 
             terminates at the CCAP-Core from the CCAP Core's point of 
             view.
             The attributes in this table are used to create an entry 
             for each L2TPv3 tunnel (session) terminated at an R-PHY 
             entity (CCAP-Core)."
    ::= { docsRphyCcapMibObjects 1 }

docsRphyCcapL2tpSessionInfoEntry OBJECT-TYPE
    SYNTAX      DocsRphyCcapL2tpSessionInfoEntry
    MAX-ACCESS  not-accessible
    STATUS      current
    DESCRIPTION
            "The conceptual row of docsRphyCcapL2tpSessionInfoTable.
        
             A row entry is created for every session the CCAP-Core 
             terminates."
    INDEX { docsRphyCcapL2tpSessionInfoLocalLcceIpAddrType,
            docsRphyCcapL2tpSessionInfoLocalLcceIpAddr,
            docsRphyCcapL2tpSessionInfoLocalId }
    ::= { docsRphyCcapL2tpSessionInfoTable 1 }

DocsRphyCcapL2tpSessionInfoEntry ::= SEQUENCE
    {
    docsRphyCcapL2tpSessionInfoLocalLcceIpAddrType   InetAddressType,
    docsRphyCcapL2tpSessionInfoLocalLcceIpAddr       InetAddress,
    docsRphyCcapL2tpSessionInfoLocalId               Unsigned32,
    docsRphyCcapL2tpSessionInfoRemoteLcceIpAddrType  InetAddressType,
    docsRphyCcapL2tpSessionInfoRemoteLcceIpAddr      InetAddress,
    docsRphyCcapL2tpSessionInfoRemoteId              Unsigned32,
    docsRphyCcapL2tpSessionInfoCoreId                MacAddress,
    docsRphyCcapL2tpSessionInfoConnCtrlID            Unsigned32,
    docsRphyCcapL2tpSessionInfoUdpPort               InetPortNumber,
    docsRphyCcapL2tpSessionInfoDescr                 SnmpAdminString,
    docsRphyCcapL2tpSessionInfoSessionType           INTEGER,
    docsRphyCcapL2tpSessionInfoSessionSubType        INTEGER,
    docsRphyCcapL2tpSessionInfoMaxPayload            Unsigned32,
    docsRphyCcapL2tpSessionInfoPathPayload           Unsigned32,
    docsRphyCcapL2tpSessionInfoCoreIfMtu             Unsigned32,
    docsRphyCcapL2tpSessionInfoIncludeDOCSISMsgs     TruthValue,
    docsRphyCcapL2tpSessionInfoErrorCode             INTEGER,
    docsRphyCcapL2tpSessionInfoCreationTime          TimeStamp,
    docsRphyCcapL2tpSessionInfoOperStatus            INTEGER,
    docsRphyCcapL2tpSessionInfoLocalStatus           BITS,
    docsRphyCcapL2tpSessionInfoLastChange            TimeTicks
    }

docsRphyCcapL2tpSessionInfoLocalLcceIpAddrType OBJECT-TYPE
    SYNTAX      InetAddressType
    MAX-ACCESS  not-accessible
    STATUS      current
    DESCRIPTION 
            "This attribute indicates whether the IP address provide in 
             docsRphyCcapL2tpSessionInfoLocalLcceIpAddr is IPv4 or IPv6."
    ::= { docsRphyCcapL2tpSessionInfoEntry 1 }

docsRphyCcapL2tpSessionInfoLocalLcceIpAddr OBJECT-TYPE
    SYNTAX      InetAddress
    MAX-ACCESS  not-accessible
    STATUS      current
    DESCRIPTION 
            "This attribute provides the local LCCE IP address on the 
             CCAP Core of the session detailed in the row entry."
    ::= { docsRphyCcapL2tpSessionInfoEntry 2 }
    
docsRphyCcapL2tpSessionInfoLocalId OBJECT-TYPE
    SYNTAX      Unsigned32
    MAX-ACCESS  not-accessible
    STATUS      current
    DESCRIPTION 
            "This attribute provides the value of the session ID 
             assigned to the session by the CCAP Core."
    ::= { docsRphyCcapL2tpSessionInfoEntry 3 }
    
docsRphyCcapL2tpSessionInfoRemoteLcceIpAddrType OBJECT-TYPE
    SYNTAX      InetAddressType
    MAX-ACCESS  read-only
    STATUS      current
    DESCRIPTION 
            "This attribute indicates whether the IP address provide in 
             docsRphyCcapL2tpSessionInfoRemoteLcceIpAddr is IPv4 or IPv6."
    ::= { docsRphyCcapL2tpSessionInfoEntry 4 }

docsRphyCcapL2tpSessionInfoRemoteLcceIpAddr OBJECT-TYPE
    SYNTAX      InetAddress
    MAX-ACCESS  read-only
    STATUS      current
    DESCRIPTION 
            "This attribute provides the remote-side LCCE IP address
             of the session detailed in the row entry."
    ::= { docsRphyCcapL2tpSessionInfoEntry 5 }
    
docsRphyCcapL2tpSessionInfoRemoteId OBJECT-TYPE
    SYNTAX      Unsigned32
    MAX-ACCESS  read-only
    STATUS      current
    DESCRIPTION 
            "This attribute provides the value of the session ID 
             assigned to the session by the remote peer 
             (CCAP Core)."
    ::= { docsRphyCcapL2tpSessionInfoEntry 6 }
    
docsRphyCcapL2tpSessionInfoCoreId OBJECT-TYPE
    SYNTAX      MacAddress
    MAX-ACCESS  read-only
    STATUS      current
    DESCRIPTION 
            "This attribute provides the MAC address of the CCAP Core 
             with which this session terminates. The CCAP Core sends its
             MAC address to the RPD periodically via the DOCSIS SYNC MAC
             Message in the Source Address field."
    ::= { docsRphyCcapL2tpSessionInfoEntry 7 }
    
docsRphyCcapL2tpSessionInfoConnCtrlID OBJECT-TYPE
    SYNTAX      Unsigned32
    MAX-ACCESS  read-only
    STATUS      current
    DESCRIPTION 
            "This attribute indicates the control connection
             identifier (CCID) for this session."
    ::= { docsRphyCcapL2tpSessionInfoEntry 8 }
    
docsRphyCcapL2tpSessionInfoUdpPort OBJECT-TYPE
    SYNTAX      InetPortNumber
    MAX-ACCESS  read-only
    STATUS      current
    DESCRIPTION 
            "This attribute provides the UDP Port reported by the 
             CCAP Core when the DEPI session uses L2TPv3 Header Over
             UDP. This attribute reports a value of 0 when the session 
             is running with the L2TPv3 Session IP Header. 
             This port number is negotiated between the CCAP Core and 
             the RPD according to the L2TPv3 RFC."
    ::= { docsRphyCcapL2tpSessionInfoEntry 9 }
    
docsRphyCcapL2tpSessionInfoDescr OBJECT-TYPE
    SYNTAX      SnmpAdminString
    MAX-ACCESS  read-only
    STATUS      current
    DESCRIPTION 
            "This attribute provides an ASCII string constructed with
             the form:
             
             RemoteEndId=(pp:mmm:ccc),…  
                  { repeated for multiple endpoints } 

             where
             pp is the 0-based port num signaled in the RemoteEndId AVP
             mmm is the channel-type enum value from the RemoteEndId AVP 
             ccc is the channel number from the RemoteEndId AVP."
    ::= { docsRphyCcapL2tpSessionInfoEntry 10 }
    
docsRphyCcapL2tpSessionInfoSessionType OBJECT-TYPE
    SYNTAX      INTEGER {
                           psp(1),
                           mpt(2)
                        }
    MAX-ACCESS  read-only
    STATUS      current
    DESCRIPTION 
            "This attribute specifies whether the session is an MPT 
             session or PSP session."
    ::= { docsRphyCcapL2tpSessionInfoEntry 11 }
    
docsRphyCcapL2tpSessionInfoSessionSubType OBJECT-TYPE
    SYNTAX      INTEGER {
                           mptLegacy(1),
                           pspLegacy(2),
                           mcm(3),
                           pspDepiMultichannel(4),
                           pspUepiScQam(5),
                           pspUepiOfdma(6),
                           pspBwReqScQam(7),
                           pspBwReqOfdma(8),
                           pspProbe(9),
                           pspRngReqScQam(10),
                           pspRngReqOfdma(11),
                           pspMapScQam(12),
                           pspMapOfdma(13),
                           pspSpecman(14),
                           pspPnm(15),
                           psp551Fwd(16),
                           psp551Ret(17),
                           psp552Fwd(18),
                           psp552Ret(19),
                           pspNdf(20),
                           pspNdr(21)
                        }
    MAX-ACCESS  read-only
    STATUS      current
    DESCRIPTION 
            "This attribute specifies the type of DEPI MPT or DEPI 
             PSP session."
    ::= { docsRphyCcapL2tpSessionInfoEntry 12 }

docsRphyCcapL2tpSessionInfoMaxPayload OBJECT-TYPE
    SYNTAX      Unsigned32
    MAX-ACCESS  read-only
    STATUS      current
    DESCRIPTION 
            "This attribute indicates the maximum MTU negotiated between
             the CCAP Core and the RPD during the session establishment 
             process. It considers the header subtractions as indicated 
             in the DEPI specification."
    REFERENCE
            "DEPI specification, Signaling
             DEPI specification Annex A."
    ::= { docsRphyCcapL2tpSessionInfoEntry 13 }

docsRphyCcapL2tpSessionInfoPathPayload OBJECT-TYPE
    SYNTAX      Unsigned32
    MAX-ACCESS  read-only
    STATUS      current
    DESCRIPTION 
            "This attribute indicates the maximum MTU traversing the CIN
             from CCAP Core to the RPD. This is calculated by the CCAP 
             Core by procedures such as MTU discovery as described in 
             the DEPI specification."
    REFERENCE
            "DEPI specification, Network MTU"
    ::= { docsRphyCcapL2tpSessionInfoEntry 14 }
    
docsRphyCcapL2tpSessionInfoCoreIfMtu OBJECT-TYPE
    SYNTAX      Unsigned32
    MAX-ACCESS  read-only
    STATUS      current
    DESCRIPTION 
            "This attribute provides the CCAP Core's CIN interface MTU
             and is read as the value of the following L2TPv3 AVP as 
             received by the device during session setup:
             
             DEPI Downstream PW          UEPI Upstream PW
             DEPI Local MTU AVP (ICRQ)   UEPI Local MTU AVP (ICRQ)."
    ::= { docsRphyCcapL2tpSessionInfoEntry 15 }

docsRphyCcapL2tpSessionInfoIncludeDOCSISMsgs OBJECT-TYPE
    SYNTAX      TruthValue
    MAX-ACCESS  read-only
    STATUS      current
    DESCRIPTION 
            "This attribute returns true if the CCAP Core includes 
             DOCSIS MAP messages and other MAC Management messages 
             in the interface entry associated with this control 
             entry. The CCAP Core determines whether the interface 
             includes DOCSIS messages as part of the payload."
    ::= { docsRphyCcapL2tpSessionInfoEntry 16 }

docsRphyCcapL2tpSessionInfoErrorCode OBJECT-TYPE
    SYNTAX      INTEGER {
        none(1),
        invalidMACInterfaceValue(2),
        invalidInterfaceValue(3),
        noResourcesForInterfaceIndex(4),
        l2tpv3Error(5),
        ifAdminStatusSetToDown(6)
        }
    MAX-ACCESS  read-only
    STATUS      current
    DESCRIPTION 
            "The error code raised when the session is in an error
            state. 
            'invalidMACInterfaceValue'  
               Indicates wrong assignment of the CCAP Core MAC interface
               ifIndex.
            'invalidInterfaceValue'  
               Indicates wrong assignment of the CCAP Core Downstream 
               interface ifIndex
            'noResourcesForInterfaceIfIndex' 
               Indicates the CCAP Core has no more resources to
               assign a session to this entry.
            'l2tpv3Error'
               An L2TPv3 StopCCN or CDN message was issued 
            'ifAdminStatusSetToDown'
               Indicates the ifAdminStatus was set to down and the
               session was torn down."
    ::= { docsRphyCcapL2tpSessionInfoEntry 17 }

docsRphyCcapL2tpSessionInfoCreationTime OBJECT-TYPE
    SYNTAX      TimeStamp
    MAX-ACCESS  read-only
    STATUS      current
    DESCRIPTION 
            "The attribute contains the sysUptime when the entry was 
             turned active."
    ::= { docsRphyCcapL2tpSessionInfoEntry 18 }
    
docsRphyCcapL2tpSessionInfoOperStatus OBJECT-TYPE
    SYNTAX      INTEGER {
                          other(0),
                          up(1),
                          down(2),
                          testing(3),
                          dormant(4),
                          notPresent(5),
                          lowerLayerDown(6)
                         }
    MAX-ACCESS  read-only
    STATUS      current
    DESCRIPTION 
            "This attribute provides the current status of the 
             pseudowire from the point of view of the specific 
             reporting entity (CCAP-Core). 
             Values are as follows:
             'other' 
                 indicates a vendor-specific operational status.
             'up'         
                 indicates that the pseudowire is ready to pass packets.
             'down' 
                 indicates that pseudowire signaling is not yet finished, 
                 or indications available at the service level indicate 
                 that the pseudowire is not passing packets.
             'testing' 
                 indicates that AdminStatus at the pseudowire level is 
                 set to test.
             'dormant' 
                 indicates that the pseudowire is not in a condition to 
                 pass packets but is in a 'pending' state, waiting for 
                 some external event.
             'notPresent' 
                 indicates that some component is missing to accomplish 
                 the setup of the pseudowire.  It can be a configuration 
                 error, incomplete configuration, or a missing H/W 
                 component.
             'lowerLayerDown' 
                 indicates one or more of the lower-layer 
                 interfaces responsible for running the underlying PSN
                 is not in OperStatus 'up' state."
    ::= { docsRphyCcapL2tpSessionInfoEntry 19 }

docsRphyCcapL2tpSessionInfoLocalStatus OBJECT-TYPE
    SYNTAX      BITS {
                      other(0),
                      pwNotForwarding(1), 
                      servicePwRxFault(2), 
                      servicePwTxFault(3), 
                      psnPwRxFault(4), 
                      psnPwTxFault(5)
    }
    MAX-ACCESS  read-only
    STATUS      current
    DESCRIPTION 
            "The attribute provides the status of the pseudowire 
             in the local node. If the 'other' bit is set, it indicates
             that an additional vendor-specific status is reported. 
             If none of the bits are set, it indicates no faults are 
             reported."
    ::= { docsRphyCcapL2tpSessionInfoEntry 20 }
    
docsRphyCcapL2tpSessionInfoLastChange OBJECT-TYPE
    SYNTAX      TimeTicks
    MAX-ACCESS  read-only
    STATUS      current
    DESCRIPTION 
            "The attribute provides the value of sysUpTime 
             when the session entered its current OperStatus 
             state from the point of view of the specific 
             reporting entity (CCAP-Core)."
    ::= { docsRphyCcapL2tpSessionInfoEntry 21 }
    
-- ---------------------------------------------------------
-- CCAP Core L2TP Session Statistics Table 
-- ---------------------------------------------------------
                 
docsRphyCcapL2tpSessionStatsTable OBJECT-TYPE
    SYNTAX      SEQUENCE OF DocsRphyCcapL2tpSessionStatsEntry
    MAX-ACCESS  not-accessible
    STATUS      current
    DESCRIPTION
            "This table provides statistics for every session that 
             terminates at the CCAP-Core from the CCAP Core's point of 
             view. It also provides statistics about each tunnel 
             session between the RPD and each CCAP Core with which the 
             RPD is associated from the RPD's point of view."
    ::= { docsRphyCcapMibObjects 2 }

docsRphyCcapL2tpSessionStatsEntry OBJECT-TYPE
    SYNTAX      DocsRphyCcapL2tpSessionStatsEntry
    MAX-ACCESS  not-accessible
    STATUS      current
    DESCRIPTION
            "The conceptual row of docsRphyCcapL2tpSessionStatsTable.
             This table is an augmentation of 
             docsRphyCcapL2tpSessionInfoTable."
    AUGMENTS { docsRphyCcapL2tpSessionInfoEntry }
    ::= { docsRphyCcapL2tpSessionStatsTable 1 }

DocsRphyCcapL2tpSessionStatsEntry ::= SEQUENCE
    {
    docsRphyCcapL2tpSessionStatsOutOfSeqPkts   Counter32
    }
    
docsRphyCcapL2tpSessionStatsOutOfSeqPkts OBJECT-TYPE
    SYNTAX      Counter32
    MAX-ACCESS  read-only
    STATUS      current
    DESCRIPTION 
            "This attribute indicates the count of session packets that
             were received out of sequence from the point of view of the
             reporting entity. It is vendor dependent the re-sequence of 
             packets. Implementations that do not re-sequence packets 
             also increase the value of ifInDiscards for the respective 
             entry."
    ::= { docsRphyCcapL2tpSessionStatsEntry 1 }
    

-- ---------------------------------------------------------
-- CCAP Core CIN Latency  Table 
-- ---------------------------------------------------------
                 
docsRphyCcapCinLatencyTable OBJECT-TYPE
    SYNTAX      SEQUENCE OF DocsRphyCcapCinLatencyEntry
    MAX-ACCESS  not-accessible
    STATUS      current
    DESCRIPTION
            "This table provides measurements on the latency on the CIN
             link for the session as measured by the CCAP-Core. These 
             measurements are based on the DEPI latency measurement, 
             specified in the Remote Downstream External PHY Interface
             Specification."
    ::= { docsRphyCcapMibObjects 3 }

docsRphyCcapCinLatencyEntry OBJECT-TYPE
    SYNTAX      DocsRphyCcapCinLatencyEntry
    MAX-ACCESS  not-accessible
    STATUS      current
    DESCRIPTION
            "The conceptual row of docsRphyCcapCinLatencyTable.
             A row entry is created for every session the CCAP Core 
             terminates. This is an extension to 
             docsRphyCcapL2tpSessionInfoTable for the CCAP Core."
    INDEX { docsRphyCcapL2tpSessionInfoLocalLcceIpAddrType,
            docsRphyCcapL2tpSessionInfoLocalLcceIpAddr,
            docsRphyCcapL2tpSessionInfoLocalId }
    ::= { docsRphyCcapCinLatencyTable 1 }

DocsRphyCcapCinLatencyEntry ::= SEQUENCE
    {
    docsRphyCcapCinLatencyLastVal           Unsigned32,
    docsRphyCcapCinLatencyLastValTime       TimeTicks,
    docsRphyCcapCinLatencyInterval          Unsigned32
    }

docsRphyCcapCinLatencyLastVal OBJECT-TYPE
    SYNTAX      Unsigned32
    MAX-ACCESS  read-only
    STATUS      current
    DESCRIPTION 
            "This attribute indicates the latest latency measurement
             on this session."
    ::= { docsRphyCcapCinLatencyEntry 1 }

docsRphyCcapCinLatencyLastValTime OBJECT-TYPE
    SYNTAX      TimeTicks
    MAX-ACCESS  read-only
    STATUS      current
    DESCRIPTION 
            "This attribute indicates the sysUpTime value of the last 
             time the docsRphyCcapCinLatencyPerfLastVal attribute was 
             updated."
    ::= { docsRphyCcapCinLatencyEntry 2 }
    
docsRphyCcapCinLatencyInterval OBJECT-TYPE
    SYNTAX      Unsigned32
    MAX-ACCESS  read-only
    STATUS      current
    DESCRIPTION 
            "This attribute provides the time interval used to measure
             periodically the CIN latency per DEPI session. Active 
             measurement of CIN latency applies to active DEPI sessions 
             only. This attribute is constrained to 420 seconds to 
             prevent Master Clock counter overruns. A value zero 
             indicates no CIN latency measurements are configured to 
             be performed."
    ::= { docsRphyCcapCinLatencyEntry 3 }
    
-- ---------------------------------------------------------
-- CCAP Core CIN Latency Performance Table 
-- ---------------------------------------------------------

docsRphyCcapCinLatencyPerfTable OBJECT-TYPE
    SYNTAX      SEQUENCE OF DocsRphyCcapCinLatencyPerfEntry
    MAX-ACCESS  not-accessible
    STATUS      current
    DESCRIPTION
            "This table provides cumulative measurements of the CIN
             latency on the network as measured by the CCAP Core. 
             When the table is full, the oldest measurement is 
             replaced with a new one. The SessionCinLatencyPerfTable
             object is based on the 
             docsIfMCmtsDepiSessionCinLatencyPerfTable object defined 
             in the DOCS-IF-M-CMTS-MIB and has been extended for 
             Remote PHY."
    ::= { docsRphyCcapMibObjects 4 }

docsRphyCcapCinLatencyPerfEntry OBJECT-TYPE
    SYNTAX      DocsRphyCcapCinLatencyPerfEntry
    MAX-ACCESS  not-accessible
    STATUS      current
    DESCRIPTION
            "The conceptual row of docsRphyCcapCinLatencyPerfTable.
             A row entry is created for every session the CCAP Core 
             terminates. This is an extension to 
             docsRphyCcapL2tpSessionInfoTable for the CCAP Core."
    INDEX { docsRphyCcapL2tpSessionInfoLocalLcceIpAddrType,
            docsRphyCcapL2tpSessionInfoLocalLcceIpAddr,
            docsRphyCcapL2tpSessionInfoLocalId }
    ::= { docsRphyCcapCinLatencyPerfTable 1 }

DocsRphyCcapCinLatencyPerfEntry ::= SEQUENCE
    {
    docsRphyCcapCinLatencyPerfIntervalSeq       Unsigned32,
    docsRphyCcapCinLatencyPerfVal               Unsigned32,
    docsRphyCcapCinLatencyPerfValTime           TimeTicks
    }

docsRphyCcapCinLatencyPerfIntervalSeq OBJECT-TYPE
    SYNTAX      Unsigned32
    MAX-ACCESS  read-only
    STATUS      current
    DESCRIPTION 
            "This attribute indicates the interval sequence where the 
             CIN latency measurement was taken. It is valid in an 
             implementation that overrides the oldest sequence number 
             entry with the most recent measurement."
    ::= { docsRphyCcapCinLatencyPerfEntry 1 }

docsRphyCcapCinLatencyPerfVal OBJECT-TYPE
    SYNTAX      Unsigned32
    MAX-ACCESS  read-only
    STATUS      current
    DESCRIPTION 
            "This attribute indicates the CIN latency value measured 
             for the session referenced by this entry."
    ::= { docsRphyCcapCinLatencyPerfEntry 2 }
    
docsRphyCcapCinLatencyPerfValTime OBJECT-TYPE
    SYNTAX      TimeTicks
    MAX-ACCESS  read-only
    STATUS      current
    DESCRIPTION 
            "This attribute provides the sysUpTime value for the last 
             time docsRphyCcapCinLatencyPerfVal was updated."
    ::= { docsRphyCcapCinLatencyPerfEntry 3 }
    
-- ---------------------------------------------------------
-- Conformance definitions 
-- ---------------------------------------------------------

 
docsRphyCompliances    OBJECT IDENTIFIER ::= { docsRphyConformance 1 } 
docsRphyGroups         OBJECT IDENTIFIER ::= { docsRphyConformance 2 } 


docsRphyCompliance MODULE-COMPLIANCE 
     STATUS current 
     DESCRIPTION 
          "The compliance statement for RPD management features."


MODULE -- docsRphyMib
          
-- conditionally mandatory groups


GROUP docsRphyRpdGroup 
        DESCRIPTION
            "Group of objects applicable to RPDs only.
            These objects are implemented on the CCAP Core
            but are derived from the RPD via the GCP protocol."

GROUP docsRphyCcapCoreGroup 
        DESCRIPTION
            "Group of objects applicable to CCAP Core only."
            
-- conditionally optional groups


::= { docsRphyCompliances 1}


docsRphyRpdGroup OBJECT-GROUP
        OBJECTS {
                docsRphyRpdInfoSysUpTime,
                docsRphyRpdIdVendorName,     
       			docsRphyRpdIdVendorId,            
       			docsRphyRpdIdModelNum,            
       			docsRphyRpdIdSerialNum,           
       			docsRphyRpdIdDeviceAlias,         
       			docsRphyRpdIdDeviceDescr,
       			docsRphyRpdIdHwRev,         
       			docsRphyRpdIdCurrSwVer,           
       			docsRphyRpdIdBootRomVer,
       			docsRphyRpdLocationDescr,              
       			docsRphyRpdLocationLatitude,           
       			docsRphyRpdLocationLongitude,
       			docsRphyRpdCoresConnectedCoreId,              
       			docsRphyRpdCoresConnectedAddressType,         
       			docsRphyRpdCoresConnectedAddress,             
       			docsRphyRpdCoresConnectedIsPrincipal,         
       			docsRphyRpdCoresConnectedName,	            
       			docsRphyRpdCoresConnectedVendorId,
       			docsRphyRpdCapabNumBiDirPorts,              
       			docsRphyRpdCapabNumDsPorts,                 
       			docsRphyRpdCapabNumUsPorts,                 
      		 	docsRphyRpdCapabNumTenGeNsPorts,            
       			docsRphyRpdCapabNumOneGeNsPorts,	          
       			docsRphyRpdCapabNumDsScQamChans,	          
       			docsRphyRpdCapabNumDsOfdmChans,	          
       			docsRphyRpdCapabNumUsScQamChans,	          
       			docsRphyRpdCapabNumUsOfdmaChans,	          
       			docsRphyRpdCapabNumDsOob551Chans,	          
       			docsRphyRpdCapabNumUsOob551Chans,	          
       			docsRphyRpdCapabNumDsOob552Chans,	          
       			docsRphyRpdCapabNumUsOob552Chans,	          
       			docsRphyRpdCapabNumNdfChans,	              
       			docsRphyRpdCapabNumNdrChans,	              
       			docsRphyRpdCapabSupportsUdpEncap,	          
       			docsRphyRpdCapabNumDsPspFlowsPerChan,       
       			docsRphyRpdCapabNumUsPspFlowsPerChan,       
       			docsRphyRpdCapabNumAsynchVideoChans,        
       			docsRphyRpdCapabNumCwToneGens,              
       			docsRphyRpdCapabLowestCwToneFreq,           
       			docsRphyRpdCapabHighestCwToneFreq,          
       			docsRphyRpdCapabMaxCwTonePwr,               
       			docsRphyRpdCapabQamAsPilot,
       			docsRphyRpdChanReachabilityStartChanIndex,
                docsRphyRpdChanReachabilityEndChanIndex,          
                docsRphyRpdDsUsRfPortAllocScQamChans,         
                docsRphyRpdDsUsRfPortAllocOfdmChans,          
                docsRphyRpdDsUsRfPortAllocOob551Chans,        
                docsRphyRpdDsUsRfPortAllocOob552Chans,	    
                docsRphyRpdDsUsRfPortAllocNdChans,
                docsRphyRpdL2tpSessionInfoRemoteLcceIpAddrType,
    			docsRphyRpdL2tpSessionInfoRemoteLcceIpAddr,      
    			docsRphyRpdL2tpSessionInfoRemoteId,                           
    			docsRphyRpdL2tpSessionInfoConnCtrlID,            
    			docsRphyRpdL2tpSessionInfoUdpPort,               
    			docsRphyRpdL2tpSessionInfoDescr,                 
   			 	docsRphyRpdL2tpSessionInfoSessionType,           
    			docsRphyRpdL2tpSessionInfoSessionSubType,        
    			docsRphyRpdL2tpSessionInfoMaxPayload,            
    			docsRphyRpdL2tpSessionInfoPathPayload,           
    			docsRphyRpdL2tpSessionInfoRpdIfMtu,              
    			docsRphyRpdL2tpSessionInfoErrorCode,             
    			docsRphyRpdL2tpSessionInfoCreationTime,          
    			docsRphyRpdL2tpSessionInfoOperStatus,            
    			docsRphyRpdL2tpSessionInfoLocalStatus,           
    			docsRphyRpdL2tpSessionInfoLastChange,
    			docsRphyRpdL2tpSessionStatsOutOfSeqPkts,   
                
                docsRphyRpdPhysEntityDescr,          
      			docsRphyRpdPhysEntityVendorType,     
      			docsRphyRpdPhysEntityContainedIn,    
      			docsRphyRpdPhysEntityClass,          
      			docsRphyRpdPhysEntityParentRelPos,   
      			docsRphyRpdPhysEntityName,           
      			docsRphyRpdPhysEntityHardwareRev,    
      			docsRphyRpdPhysEntityFirmwareRev,    
      			docsRphyRpdPhysEntitySoftwareRev,    
      			docsRphyRpdPhysEntitySerialNum,      
      			docsRphyRpdPhysEntityMfgName,        
      			docsRphyRpdPhysEntityModelName,      
      			docsRphyRpdPhysEntityAlias,          
      			docsRphyRpdPhysEntityAssetID,        
      			docsRphyRpdPhysEntityIsFRU,          
      			docsRphyRpdPhysEntityMfgDate,        
      			docsRphyRpdPhysEntityUris,           
      			docsRphyRpdPhysEntityUUID,
      			docsRphyRpdPhysEntityIfIndex,
      			docsRphyRpdPhysEntSensorType,            
        		docsRphyRpdPhysEntSensorScale,           
        		docsRphyRpdPhysEntSensorPrecision,       
        		docsRphyRpdPhysEntSensorValue,           
        		docsRphyRpdPhysEntSensorOperStatus,      
        		docsRphyRpdPhysEntSensorUnitsDisplay,    
        		docsRphyRpdPhysEntSensorValueTimeStamp,  
        		docsRphyRpdPhysEntSensorValueUpdateRate,
        		
        		docsRphyRpdEnetIfIndex,                 
                docsRphyRpdEnetIfDescr,                 
                docsRphyRpdEnetIfName,                  
                docsRphyRpdEnetIfAlias,                 
                docsRphyRpdEnetIfType,                  
                docsRphyRpdEnetIfMtu,                                   
                docsRphyRpdEnetIfPhysAddress,           
                docsRphyRpdEnetIfAdminStatus,           
                docsRphyRpdEnetIfOperStatus,            
                docsRphyRpdEnetIfLastChange,            
                docsRphyRpdEnetIfLinkUpDownTrapEnable,  
                docsRphyRpdEnetIfHighSpeed,             
                docsRphyRpdEnetIfPromiscuousMode,      
                docsRphyRpdEnetIfConnectorPresent,
        		docsRphyRpdEnetIfStatsInOctets,            
                docsRphyRpdEnetIfStatsOutOctets,           
                docsRphyRpdEnetIfStatsInFrames,            
                docsRphyRpdEnetIfStatsOutFrames,           
                docsRphyRpdEnetIfStatsInUnicastOctets,     
                docsRphyRpdEnetIfStatsOutUnicastOctets,   
                docsRphyRpdEnetIfStatsInUnicastFrames,     
                docsRphyRpdEnetIfStatsOutUnicastFrames,    
                docsRphyRpdEnetIfStatsInMulticastOctets,   
                docsRphyRpdEnetIfStatsOutMulticastOctets,  
                docsRphyRpdEnetIfStatsInMulticastFrames,   
                docsRphyRpdEnetIfStatsOutMulticastFrames,  
                docsRphyRpdEnetIfStatsInBroadcastOctets,    
                docsRphyRpdEnetIfStatsOutBroadcastOctets,  
                docsRphyRpdEnetIfStatsInBroadcastFrames,   
                docsRphyRpdEnetIfStatsOutBroadcastFrames,  
                docsRphyRpdEnetIfStatsInDiscards,          
                docsRphyRpdEnetIfStatsOutDiscards,         
                docsRphyRpdEnetIfStatsInErrors,            
                docsRphyRpdEnetIfStatsOutErrors,           
                docsRphyRpdEnetIfStatsInUnknownProtos,     
                docsRphyRpdEnetIfStatsCounterDiscontinuityTime, 
        		    			
    			docsRphyRpdIpv4GrpIpForwarding,                
                docsRphyRpdIpv4GrpDefaultTTL,                 
                docsRphyRpdIpv4GrpReasmTimeout,               
                docsRphyRpdIpGrpIpv4InterfaceTableLastChange,
                docsRphyRpdIpv6GrpIpForwarding,             
        		docsRphyRpdIpv6GrpIpDefaultHopLimit,        
        		docsRphyRpdIpv6GrpInterfaceTableLastChange, 
        		docsRphyRpdIpv6GrpIfStatsTableLastChange,                 
                docsRphyRpdIpv4InterfaceReasmMaxSize, 
                docsRphyRpdIpv4InterfaceEnableStatus,
                docsRphyRpdIpv4InterfaceRetransmitTime,
                docsRphyRpdIpv6InterfaceReasmMaxSize,   
                docsRphyRpdIpv6InterfaceIdentifier,
                docsRphyRpdIpv6InterfaceEnableStatus,   
                docsRphyRpdIpv6InterfaceReachableTime,
                docsRphyRpdIpv6InterfaceRetransmitTime, 
                docsRphyRpdIpv6InterfaceForwarding,                
                docsRphyRpdIpIfStatsInReceives,        
                docsRphyRpdIpIfStatsInOctets,
                docsRphyRpdIpIfStatsInHdrErrors,       
                docsRphyRpdIpIfStatsInNoRoutes,
                docsRphyRpdIpIfStatsInAddrErrors,      
                docsRphyRpdIpIfStatsInUnknownProtos,
                docsRphyRpdIpIfStatsInTruncatedPkts,   
                docsRphyRpdIpIfStatsInForwDatagrams,
                docsRphyRpdIpIfStatsReasmReqds,        
                docsRphyRpdIpIfStatsReasmOKs,
                docsRphyRpdIpIfStatsReasmFails,        
                docsRphyRpdIpIfStatsInDiscards,
                docsRphyRpdIpIfStatsInDelivers,        
                docsRphyRpdIpIfStatsOutRequests,
                docsRphyRpdIpIfStatsOutForwDatagrams,  
                docsRphyRpdIpIfStatsOutDiscards,
                docsRphyRpdIpIfStatsOutFragReqds,      
                docsRphyRpdIpIfStatsOutFragOKs,
                docsRphyRpdIpIfStatsOutFragFails,      
                docsRphyRpdIpIfStatsOutFragCreates,
                docsRphyRpdIpIfStatsOutTransmits,      
                docsRphyRpdIpIfStatsOutOctets,
                docsRphyRpdIpIfStatsInMcastPkts,       
                docsRphyRpdIpIfStatsInMcastOctets,
                docsRphyRpdIpIfStatsOutMcastPkts,      
                docsRphyRpdIpIfStatsOutMcastOctets,
                docsRphyRpdIpIfStatsDiscontinuityTime, 
                docsRphyRpdIpIfStatsRefreshRate,          
                docsRphyRpdIpIfStatsInBcastPkts, 
                docsRphyRpdIpIfStatsOutBcastPkts,
                docsRphyRpdIpIfStatsHCInOctets,      
                docsRphyRpdIpIfStatsHCOutOctets,
                docsRphyRpdIpIfStatsHCInMcastOctets, 
                docsRphyRpdIpIfStatsHCOutMcastOctets,
                docsRphyRpdIpIfStatsHCInReceives,       
                docsRphyRpdIpIfStatsHCInForwDatagrams,
                docsRphyRpdIpIfStatsHCInDelivers,       
                docsRphyRpdIpIfStatsHCOutRequests,
                docsRphyRpdIpIfStatsHCOutForwDatagrams, 
                docsRphyRpdIpIfStatsHCOutTransmits,
                docsRphyRpdIpIfStatsHCInMcastPkts,      
                docsRphyRpdIpIfStatsHCOutMcastPkts,
                docsRphyRpdIpIfStatsHCInBcastPkts, 
                docsRphyRpdIpIfStatsHCOutBcastPkts,
                docsRphyRpdIpAddressSpinLock,  
                docsRphyRpdIpAddressIfIndex,
                docsRphyRpdIpAddressType,      
                docsRphyRpdIpAddressPrefix,
                docsRphyRpdIpAddressOrigin,    
                docsRphyRpdIpAddressStatus,
                docsRphyRpdIpAddressCreated,   
                docsRphyRpdIpAddressLastChanged,
                docsRphyRpdIpAddressRowStatus, 
                docsRphyRpdIpAddressStorageType,
                docsRphyRpdIpNetToPhysicalPhysAddress, 
                docsRphyRpdIpNetToPhysicalLastUpdated,
                docsRphyRpdIpNetToPhysicalType,        
                docsRphyRpdIpNetToPhysicalState,
                docsRphyRpdIpNetToPhysicalRowStatus,
                docsRphyRpdIpDefaultRouterLifetime, 
                docsRphyRpdIpDefaultRouterPreference,
                docsRphyRpdIpIcmpStatsInMsgs,    
                docsRphyRpdIpIcmpStatsInErrors,
                docsRphyRpdIpIcmpStatsOutMsgs,   
                docsRphyRpdIpIcmpStatsOutErrors,
                docsRphyRpdIpIcmpMsgStatsInPkts, 
                docsRphyRpdIpIcmpMsgStatsOutPkts,
                docsRphyRpdPwIndex,
      			docsRphyRpdPwPeerAddrType,
      			docsRphyRpdPwPeerAddr,            
      			docsRphyRpdPwLocalIfMtu,          
      			docsRphyRpdPwRemoteIfMtu,         
      			docsRphyRpdPwOutboundLabel,       
      			docsRphyRpdPwName,                
      			docsRphyRpdPwDescr,               
      			docsRphyRpdPwCreateTime,          
      			docsRphyRpdPwUpTime,              
      			docsRphyRpdPwLastChange,          
      			docsRphyRpdPwOperStatus,          
      			docsRphyRpdPwLocalStatus                        	                           
        }
        STATUS      current
        DESCRIPTION
            "Group of objects implemented in CCAP Cores which
            represent RPD managed objects derived via the GCP 
            protocol."
        ::= { docsRphyGroups 1 }

docsRphyCcapCoreGroup OBJECT-GROUP
        OBJECTS {
                docsRphyCcapL2tpSessionInfoRemoteLcceIpAddrType,
    			docsRphyCcapL2tpSessionInfoRemoteLcceIpAddr,      
    			docsRphyCcapL2tpSessionInfoRemoteId,              
    			docsRphyCcapL2tpSessionInfoCoreId,                
    			docsRphyCcapL2tpSessionInfoConnCtrlID,            
    			docsRphyCcapL2tpSessionInfoUdpPort,               
    			docsRphyCcapL2tpSessionInfoDescr,                 
   			 	docsRphyCcapL2tpSessionInfoSessionType,           
    			docsRphyCcapL2tpSessionInfoSessionSubType,        
    			docsRphyCcapL2tpSessionInfoMaxPayload,            
    			docsRphyCcapL2tpSessionInfoPathPayload,                  
    			docsRphyCcapL2tpSessionInfoCoreIfMtu,             
    			docsRphyCcapL2tpSessionInfoIncludeDOCSISMsgs,     
    			docsRphyCcapL2tpSessionInfoErrorCode,             
    			docsRphyCcapL2tpSessionInfoCreationTime,          
    			docsRphyCcapL2tpSessionInfoOperStatus,            
    			docsRphyCcapL2tpSessionInfoLocalStatus,           
    			docsRphyCcapL2tpSessionInfoLastChange,
    			docsRphyCcapL2tpSessionStatsOutOfSeqPkts,
    			docsRphyCcapCinLatencyLastVal,           
                docsRphyCcapCinLatencyLastValTime,       
                docsRphyCcapCinLatencyInterval,
                docsRphyCcapCinLatencyPerfIntervalSeq,
                docsRphyCcapCinLatencyPerfVal,               
                docsRphyCcapCinLatencyPerfValTime                    
    	}
        STATUS      current
        DESCRIPTION
            "Group of objects implemented in CCAP Cores."
        ::= { docsRphyGroups 2 }
        END
