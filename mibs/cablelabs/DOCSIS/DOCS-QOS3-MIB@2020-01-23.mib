DOCS-QOS3-MIB DEFINITIONS ::= BEGIN
  IMPORTS
    MODULE-IDENTITY,
    OBJECT-TYPE,
    Unsigned32,
    Counter32,
    Counter64
             FROM SNMPv2-SMI           -- RFC 2578
    TEXTUAL-CONVENTION,
    RowStatus,
    TruthValue,
    MacAddress,
    TimeStamp,
    StorageType
             FROM SNMPv2-TC            -- RFC 2579
    OBJECT-GROUP,
    MODULE-COMPLIANCE
             FROM SNMPv2-CONF          -- RFC 2580
    CounterBasedGauge64
             FROM HCNUM-TC           -- RFC 2865
    SnmpAdminString
             FROM SNMP-FRAMEWORK-MIB   -- RFC 3411
    InterfaceIndex,
    ifIndex
             FROM IF-MIB               -- RFC 2863
    InetAddressType,
    InetAddress,
    InetPortNumber
             FROM INET-ADDRESS-MIB
    DscpOrAny
             FROM DIFFSERV-DSCP-TC
    IfDirection,
    AttributeMask,
    AttrAggrRuleMask,
    ChSetId,
    Dsid,
    ChId,
    ChannelList
             FROM DOCS-IF3-MIB
    clabProjDocsis,
    DocsL2vpnIfList
             FROM CLAB-DEF-MIB;

docsQosMib MODULE-IDENTITY
     LAST-UPDATED    "202001230000Z" -- January 23, 2020
     ORGANIZATION    "Cable Television Laboratories, Inc."
     CONTACT-INFO
        "Postal: Cable Television Laboratories, Inc.
        858 Coal Creek Circle
        Louisville, Colorado 80027-9750
        U.S.A.
        Phone: +1 303-661-9100
        Fax:   +1 303-661-9199
        E-mail: mibs@cablelabs.com"
     DESCRIPTION
        "This MIB module contains the management objects for the
        management of DOCSIS 3.0 and 3.1 features, primarily for the
        management of QOS for channel bonding.
        Copyright 1999-2019 Cable Television Laboratories, Inc.
        All rights reserved."
    REVISION    "202001230000Z" -- January 23, 2020
    DESCRIPTION
            "Revised Version includes ECN
             DOCS-QOS3-MIB-N-19.2065-2."
    REVISION    "201909050000Z" -- September 5, 2019
    DESCRIPTION
            "Revised Version includes ECN
             DOCS-QOS3-MIB-N-19.2045-1."
    REVISION    "201905020000Z" -- May 2, 2019
    DESCRIPTION
            "Revised Version includes ECN
             DOCS-QOS3-MIB-N-19.2010-5."
    REVISION    "201902070000Z" -- February 7, 2019
    DESCRIPTION
            "Revised Version includes ECN
             DOCS-QOS3-MIB-N-18.1989-2."
    REVISION    "201608180000Z" -- August 18, 2016
    DESCRIPTION
            "Revised Version includes ECN
             DOCS-QOS3-MIB-N-16.1552-3."
    REVISION    "201605050000Z" -- May 5, 2016
    DESCRIPTION
            "Revised Version includes ECN
            CCAP-OSSIv3.1-N-16.1455-2;
            supersedes CCAP-OSSIv3.1-N-16.1435-1."
    REVISION    "201504080000Z" -- April 8, 2015
    DESCRIPTION
            "Revised Version includes additions for AQM
            per CM-OSSIv3.1-N-15.1277-2."
    REVISION    "201407290000Z" -- July 29, 2014
    DESCRIPTION
            "Revised Version includes ECN
            OSSIv3.0-N-14.1151-2 and published as I24"
    REVISION    "201208090000Z" -- August 9, 2012
    DESCRIPTION
            "Revised Version includes ECN
            OSSIv3.0-N-12.1064-3 and published as I19"
    REVISION    "201203290000Z" -- March 29, 2012
    DESCRIPTION
            "Revised Version includes ECN
            OSSIv3.0-N-11.1025-3 and published as I18"
    REVISION    "201102100000Z" -- February 10, 2011
    DESCRIPTION
            "Revised Version includes ECN
            OSSIv3.0-N-10.0966-2 and OSSIv3.0-N-10.0984-1
            and published as I14"
    REVISION    "200910020000Z" -- October 2, 2009
    DESCRIPTION
            "Revised Version includes ECN
            OSSIv3.0-N-09.0776-4
            and published as I10"
    REVISION    "200905290000Z" -- May 29, 2009
    DESCRIPTION
            "Revised Version includes ECN
            OSSIv3.0-N-09.0775-3
            and published as I09"
    REVISION    "200901210000Z" -- January 21, 2009
    DESCRIPTION
            "Revised Version includes ECNs
            OSSIv3.0-N-08.0651-3
            OSSIv3.0-N-08.0700-4
            and published as I08"
     REVISION        "200805220000Z" -- May 22, 2008
     DESCRIPTION
        "Revised Version includes ECN OSSIv3.0-N-08.0645-4
        and published as I07"
     REVISION        "200712060000Z" -- December 6, 2007
     DESCRIPTION
        "Revised Version includes ECN OSSIv3.0-N-07.0522-3
        and published as I05"
     REVISION        "200708030000Z" -- August 03, 2007
     DESCRIPTION
        "Revised Version includes ECN OSSIv3.0-N-07.0480-3
        and published as I04"
     REVISION        "200705180000Z" -- May 18, 2007
     DESCRIPTION
        "Revised Version includes ECNs
        OSSIv3.0-N-07.0445-3
        OSSIv3.0-N-07.0437-4
        OSSIv3.0-N-07.0412-2
        OSSIv3.0-N-07.0410-4
        and published as I03"
     REVISION        "200612071700Z" -- Dec 7, 2006
     DESCRIPTION
        "Initial version, published as part of the CableLabs
        OSSIv3.0 specification CM-SP-OSSIv3.0-I01-061207."
     ::= {  clabProjDocsis 21 }

-- Textual Conventions

BitRate ::= TEXTUAL-CONVENTION
    DISPLAY-HINT "d"
    STATUS      current
    DESCRIPTION
       "The rate of traffic. The units are 
        specified by a multiplier attribute, DataRateUnitSetting, as bits 
        per second (bps), kilobits per second (kbps), megabits per second 
        (mbps), or gigabits per second (gbps).
        Kilobits per second is measured as 1,000 bits per second.
        Megabits per second is measured as 1 million bits per second.
        Gigabits per second is measured as 1 billion bits per second."
    SYNTAX          Unsigned32

SchedulingType ::= TEXTUAL-CONVENTION
    STATUS          current
    DESCRIPTION
       "The scheduling service provided by a CMTS for an
       upstream Service Flow.  If the parameter is omitted
       from an upstream QOS Parameter Set, this object
       takes the value of bestEffort (2).  This parameter
       must be reported as undefined (1) for downstream
       QOS Parameter Sets."
    SYNTAX      INTEGER {
                         undefined (1),
                         bestEffort (2),
                         nonRealTimePollingService(3),
                         realTimePollingService(4),
                         unsolictedGrantServiceWithAD(5),
                         unsolictedGrantService(6),
                         proactiveGrantService(7)
                        }

DataRateUnitType ::= TEXTUAL-CONVENTION
    STATUS          current
    DESCRIPTION
       "The base unit for traffic 
        rate parameters. The value of this data type allows
        for their interpretation in units of Bps, Kbps, Mbps 
        or Gbps. The enumeration starts from 0 to match 
        corresponding DOCSIS protocol TLV values.
        Kilobits per second is measured as 1,000 bits per second.
        Megabits per second is measured as 1 million bits per second.
        Gigabits per second is measured as 1 billion bits per second."
    SYNTAX      INTEGER {
                         bps(0),
                         kbps(1),
                         mbps(2),
                         gbps(3)                        
                          }

docsQosMibObjects  OBJECT IDENTIFIER ::= { docsQosMib 1 }

docsQosPktClassTable OBJECT-TYPE
     SYNTAX      SEQUENCE OF DocsQosPktClassEntry
     MAX-ACCESS  not-accessible
     STATUS      current
     DESCRIPTION
        "This object describes the packet classification
        configured on the CM or CMTS.
        The model is that a packet either received as input from
        an interface or transmitted for output on an interface
        may be compared against an ordered list of rules
        pertaining to the packet contents.  Each rule is an instance
        of this object.  A matching rule provides a Service
        Flow ID to which the packet is classified.
        All rules need to match for a packet to match a classifier.


        The attributes in this row correspond to a set of Classifier
        Encoding parameters in a DOCSIS MAC management
        message.  The BitMap attribute indicates which particular
        parameters were present in the classifier as
        signaled in the DOCSIS message.
        If the referenced parameter was not present in the signaled
        Classifier, the corresponding attribute in
        this instance reports a value as specified by that attribute
        description."
     REFERENCE
        "DOCSIS 3.0 MAC and Upper Layer Protocols Interface
        Specification CM-SP-MULPIv3.0-I08-080522, Service Flows and
        Classifiers section."
     ::= { docsQosMibObjects 1}

docsQosPktClassEntry OBJECT-TYPE
     SYNTAX      DocsQosPktClassEntry
     MAX-ACCESS  not-accessible
     STATUS      current
     DESCRIPTION
        "The conceptual row of docsQosPktClassTable.
         The ifIndex key corresponds to the MAC Domain interface
         of the service flow of this classifier."
     INDEX { ifIndex,
             docsQosServiceFlowId,
             docsQosPktClassId
           }
     ::= { docsQosPktClassTable 1 }

DocsQosPktClassEntry ::= SEQUENCE {
     docsQosPktClassId
                  Unsigned32,
     docsQosPktClassDirection
                  IfDirection,
     docsQosPktClassPriority
                  Unsigned32,
     docsQosPktClassIpTosLow
                  OCTET STRING,
     docsQosPktClassIpTosHigh
                  OCTET STRING,
     docsQosPktClassIpTosMask
                  OCTET STRING,
     docsQosPktClassIpProtocol
                  Unsigned32,
     docsQosPktClassIpSourceAddr
                  InetAddress,
     docsQosPktClassIpSourceMask
                  InetAddress,
     docsQosPktClassIpDestAddr
                  InetAddress,
     docsQosPktClassIpDestMask
                  InetAddress,
     docsQosPktClassSourcePortStart
                  InetPortNumber,
     docsQosPktClassSourcePortEnd
                  InetPortNumber,
     docsQosPktClassDestPortStart
                  InetPortNumber,
     docsQosPktClassDestPortEnd
                  InetPortNumber,
     docsQosPktClassDestMacAddr
                  MacAddress,
     docsQosPktClassDestMacMask
                  MacAddress,
     docsQosPktClassSourceMacAddr
                  MacAddress,
     docsQosPktClassEnetProtocolType
                  INTEGER,
     docsQosPktClassEnetProtocol
                  Unsigned32,
     docsQosPktClassUserPriLow
                  Unsigned32,
     docsQosPktClassUserPriHigh
                  Unsigned32,
     docsQosPktClassVlanId
                  Unsigned32,
     docsQosPktClassState
                  INTEGER,
     docsQosPktClassPkts
                  Counter64,
     docsQosPktClassBitMap
                  BITS,
     docsQosPktClassIpAddrType
                  InetAddressType,
     docsQosPktClassFlowLabel
                  Unsigned32,
     docsQosPktClassCmInterfaceMask
                  DocsL2vpnIfList,
     docsQosPktClassIcmpTypeLow
                  Unsigned32,
     docsQosPktClassIcmpTypeHigh
                  Unsigned32
     }

docsQosPktClassId OBJECT-TYPE
     SYNTAX      Unsigned32 (1..65535)
     MAX-ACCESS  not-accessible
     STATUS      current
     DESCRIPTION
        "This key indicates the assigned identifier to the
        packet classifier instance by the CMTS, which is unique
        per Service Flow.
        For UDCs this corresponds to the Service Flow Reference
        of the classifier."
     REFERENCE
        "DOCSIS 3.0 MAC and Upper Layer Protocols Interface
        Specification CM-SP-MULPIv3.0-I08-080522, Classifier
        Identifier section in the Common Radio Frequency Interface
        Encodings Annex."
     ::= { docsQosPktClassEntry 1 }

docsQosPktClassDirection OBJECT-TYPE
     SYNTAX      IfDirection
     MAX-ACCESS  read-only
     STATUS      current
     DESCRIPTION
        "This attribute indicates the direction to which the
        classifier is applied."
     ::= { docsQosPktClassEntry 2 }

docsQosPktClassPriority OBJECT-TYPE
     SYNTAX      Unsigned32 (0..255)
     MAX-ACCESS  read-only
     STATUS      current
     DESCRIPTION
        "This attribute specifies the order of evaluation
        of the classifiers.
        The higher the value, the higher the priority.
        The value of 0 is used as default in provisioned Service
        Flows Classifiers.
        The default value of 64 is used for dynamic Service Flow
        Classifiers.

        If the referenced parameter is not present in a classifier,
        this attribute reports the default
        value as defined above."
     REFERENCE
        "DOCSIS 3.0 MAC and Upper Layer Protocols Interface
        Specification CM-SP-MULPIv3.0-I08-080522, Rule Priority
        section in the Common Radio Frequency Interface Encodings
        Annex."
     ::= { docsQosPktClassEntry 3 }

docsQosPktClassIpTosLow OBJECT-TYPE
     SYNTAX      OCTET STRING (SIZE (1))
     MAX-ACCESS  read-only
     STATUS      current
     DESCRIPTION
        "This attribute indicates the low value of a range of
        TOS byte values.
        If the referenced parameter is not present in a classifier,
        this attribute reports the value of 0.

        The IP TOS octet, as originally defined in RFC 791, has
        been superseded by the 6-bit Differentiated Services
        Field (DSField, RFC 3260) and the 2-bit Explicit
        Congestion Notification Field (ECN field, RFC 3168).
        This object is defined as an 8-bit octet as per the DOCSIS
        Specification for packet classification."
     REFERENCE
        "DOCSIS 3.0 MAC and Upper Layer Protocols Interface
        Specification CM-SP-MULPIv3.0-I08-080522, IPv4 Type of
        Service Range and Mask and IPv6 Traffic Class Range and
        Mask sections in the Common Radio Frequency Interface
        Encodings Annex."
     ::= { docsQosPktClassEntry 4 }

docsQosPktClassIpTosHigh OBJECT-TYPE
     SYNTAX      OCTET STRING (SIZE (1))
     MAX-ACCESS  read-only
     STATUS      current
     DESCRIPTION
        "This attribute indicates the 8-bit high value of a
        range of TOS byte values.
        If the referenced parameter is not present in a classifier,
        this attribute reports the value of 0.
        The IP TOS octet as originally defined in RFC 791 has been
        superseded by the 6-bit Differentiated Services
        Field (DSField, RFC 3260) and the 2-bit Explicit Congestion
        Notification Field (ECN field, RFC 3168).
        This object is defined as an 8-bit octet as defined by
        the DOCSIS Specification for packet classification."
     REFERENCE
        "DOCSIS 3.0 MAC and Upper Layer Protocols Interface
        Specification CM-SP-MULPIv3.0-I08-080522, IPv4 Type of
        Service Range and Mask and IPv6 Traffic Class Range and
        Mask sections in the Common Radio Frequency Interface
        Encodings Annex."
     ::= { docsQosPktClassEntry 5 }

docsQosPktClassIpTosMask OBJECT-TYPE
     SYNTAX      OCTET STRING (SIZE (1))
     MAX-ACCESS  read-only
     STATUS      current
     DESCRIPTION
        "This attribute indicates the mask value is bitwise
        ANDed with TOS byte in an IP packet, and this value is
        used for range checking of TosLow and TosHigh.

        If the referenced parameter is not present in a classifier,
        this attribute reports the value of 0.

        The IP TOS octet as originally defined in RFC 791 has been
        superseded by the 6-bit Differentiated Services
        Field (DSField, RFC 3260) and the 2-bit Explicit Congestion
        Notification Field (ECN field, RFC 3168).
        This object is defined as an 8-bit octet per the DOCSIS
        Specification for packet classification."
     REFERENCE
        "DOCSIS 3.0 MAC and Upper Layer Protocols Interface
        Specification CM-SP-MULPIv3.0-I08-080522, IPv4 Type of
        Service Range and Mask and IPv6 Traffic Class Range and
        Mask sections in the Common Radio Frequency Interface
        Encodings Annex."
     ::= { docsQosPktClassEntry 6 }

docsQosPktClassIpProtocol OBJECT-TYPE
     SYNTAX      Unsigned32 (0..258)
     MAX-ACCESS  read-only
     STATUS      current
     DESCRIPTION
        "This attribute indicates the value of the IP Protocol
        field required for IP packets to match this rule.

        The value 256 matches traffic with any IP Protocol value.
        The value 257 by convention matches both TCP and
        UDP.
        If the referenced parameter is not present in a classifier,
        this attribute reports the value of 258."
     REFERENCE
        "DOCSIS 3.0 MAC and Upper Layer Protocols Interface
        Specification CM-SP-MULPIv3.0-I08-080522, IP Protocol and
        IPv6 Next Header Type sections in the Common Radio Frequency
        Interface Encodings Annex."
     ::= { docsQosPktClassEntry 7 }

docsQosPktClassIpSourceAddr OBJECT-TYPE
     SYNTAX      InetAddress
     MAX-ACCESS  read-only
     STATUS      current
     DESCRIPTION
        "This attribute specifies the value of the IP Source
        Address required for packets to match this rule.
        An IP packet matches the rule when the packet IP Source
        Address bitwise ANDed with the InetSourceMask value
        equals the InetSourceAddr value.
        The address type of this object is specified by InetAddressType.

        If the referenced parameter is not present in a classifier,
        this object reports the value of '00000000'H."
     REFERENCE
        "DOCSIS 3.0 MAC and Upper Layer Protocols Interface
        Specification CM-SP-MULPIv3.0-I08-080522, IPv4 Source Address
        and IPv6 Source Address sections in the Common Radio Frequency
        Interface Encodings Annex."
     ::= { docsQosPktClassEntry 8 }

docsQosPktClassIpSourceMask OBJECT-TYPE
     SYNTAX      InetAddress
     MAX-ACCESS  read-only
     STATUS      current
     DESCRIPTION
        "This attribute specifies which bits of a packet's
        IP Source Address are compared to match this rule.
        An IP packet matches the rule when the packet source address
        bitwise ANDed with the InetSourceMask value
        equals the docsIetfQosIpPktClassInetSourceAddr
        value.
        The address type of this attribute is specified by InetAddressType.

        If the referenced parameter is not present in a classifier,
        this attribute reports the value of 'FFFFFFFF'H."
     REFERENCE
        "DOCSIS 3.0 MAC and Upper Layer Protocols Interface
        Specification CM-SP-MULPIv3.0-I08-080522, IPv4 Source Mask
        and IPv6 Source Prefix Length (bits) sections in the Common Radio
        Frequency Interface Encodings Annex."
     ::= { docsQosPktClassEntry 9 }

docsQosPktClassIpDestAddr OBJECT-TYPE
     SYNTAX      InetAddress
     MAX-ACCESS  read-only
     STATUS      current
     DESCRIPTION
        "This attribute specifies the value of the IP Destination
        Address required for packets to match this rule.

        An IP packet matches the rule when the packet IP Destination
        Address bitwise ANDed with the InetDestMask
        value equals the InetDestAddr value.
        The address type of this attribute is specified by
        InetAddressType.

        If the referenced parameter is not present in a classifier,
        this attribute reports the value of '00000000'H."
     REFERENCE
        "DOCSIS 3.0 MAC and Upper Layer Protocols Interface
        Specification CM-SP-MULPIv3.0-I08-080522, IPv4 Destination
        Address and IPv6 Destination Address sections in the Common
        Radio Frequency Interface Encodings Annex."
     ::= { docsQosPktClassEntry 10 }

docsQosPktClassIpDestMask OBJECT-TYPE
     SYNTAX      InetAddress
     MAX-ACCESS  read-only
     STATUS      current
     DESCRIPTION
        "This attribute specifies which bits of a packet's
        IP Destination Address are compared to match this rule.

        An IP packet matches the rule when the packet destination
        address bitwise ANDed with the InetDestMask value
        equals the docsIetfQosIpPktClassInetDestAddr
        value.
        The address type of this attribute is specified by InetAddressType.

        If the referenced parameter is not present in a classifier,
        this attribute reports the value of 'FFFFFFFF'H."
     REFERENCE
        "DOCSIS 3.0 MAC and Upper Layer Protocols Interface
        Specification CM-SP-MULPIv3.0-I08-080522, IPv4 Destination
        Mask and IPv6 Destination Prefix Length (bits) sections in
        the Common Radio Frequency Interface Encodings Annex."
     ::= { docsQosPktClassEntry 11 }

docsQosPktClassSourcePortStart OBJECT-TYPE
     SYNTAX      InetPortNumber
     MAX-ACCESS  read-only
     STATUS      current
     DESCRIPTION
        "This attribute specifies the low-end inclusive range
        of TCP/UDP source port numbers to which a packet
        is compared.  This attribute is irrelevant for non-TCP/UDP
        IP packets.
        If the referenced parameter is not present in a classifier,
        this attribute reports the value of 0."
     REFERENCE
        "DOCSIS 3.0 MAC and Upper Layer Protocols Interface
        Specification CM-SP-MULPIv3.0-I08-080522, TCP/UDP Source
        Port Start section in the Common Radio Frequency Interface
        Encodings Annex."
     ::= { docsQosPktClassEntry 12 }

docsQosPktClassSourcePortEnd OBJECT-TYPE
     SYNTAX      InetPortNumber
     MAX-ACCESS  read-only
     STATUS      current
     DESCRIPTION
        "This attribute specifies the high-end inclusive
        range of TCP/UDP source port numbers to which a packet
        is compared.  This attribute is irrelevant for non-TCP/UDP
        IP packets.
        If the referenced parameter is not present in a classifier,
        this attribute reports the value of 65535."
     REFERENCE
        "DOCSIS 3.0 MAC and Upper Layer Protocols Interface
        Specification CM-SP-MULPIv3.0-I08-080522, TCP/UDP Source
        Port End section in the Common Radio Frequency Interface
        Encodings Annex."
     ::= { docsQosPktClassEntry 13 }

docsQosPktClassDestPortStart OBJECT-TYPE
     SYNTAX      InetPortNumber
     MAX-ACCESS  read-only
     STATUS      current
     DESCRIPTION
        "This attribute specifies the low-end inclusive  range
        of TCP/UDP destination port numbers to which a packet
        is compared.
        If the referenced parameter is not present in a classifier,
        this attribute reports the value of 0."
     REFERENCE
        "DOCSIS 3.0 MAC and Upper Layer Protocols Interface
        Specification CM-SP-MULPIv3.0-I08-080522, TCP/UDP
        Destination Port Start section in the Common Radio Frequency
        Interface Encodings Annex."
     ::= { docsQosPktClassEntry 14 }

docsQosPktClassDestPortEnd OBJECT-TYPE
     SYNTAX      InetPortNumber
     MAX-ACCESS  read-only
     STATUS      current
     DESCRIPTION
        "This attribute specifies the high-end inclusive
        range of TCP/UDP destination port numbers to which a
        packet is compared.
        If the referenced parameter is not present in a classifier,
        this attribute reports the value of 65535."
     REFERENCE
        "DOCSIS 3.0 MAC and Upper Layer Protocols Interface
        Specification CM-SP-MULPIv3.0-I08-080522, TCP/UDP Destination
        Port End section in the Common Radio Frequency Interface
        Encodings Annex."
     ::= { docsQosPktClassEntry 15 }

docsQosPktClassDestMacAddr OBJECT-TYPE
     SYNTAX      MacAddress
     MAX-ACCESS  read-only
     STATUS      current
     DESCRIPTION
        "An Ethernet packet matches an entry when its destination
        MAC address bitwise ANDed with DestMacMask equals
        the value of DestMacAddr.
        If the referenced parameter is not present in a classifier,
        this attribute reports the value of '000000000000'H."
     REFERENCE
        "DOCSIS 3.0 MAC and Upper Layer Protocols Interface
        Specification CM-SP-MULPIv3.0-I08-080522, Destination MAC
        Address section in the Common Radio Frequency Interface
        Encodings Annex."
     ::= { docsQosPktClassEntry 16 }

docsQosPktClassDestMacMask OBJECT-TYPE
     SYNTAX      MacAddress
     MAX-ACCESS  read-only
     STATUS      current
     DESCRIPTION
        "An Ethernet packet matches an entry when its destination
        MAC address bitwise ANDed with DestMacMask equals
        the value of DestMacAddr.
        If the referenced parameter is not present in a classifier,
        this attribute reports the value of '000000000000'H."
     REFERENCE
        "DOCSIS 3.0 MAC and Upper Layer Protocols Interface
        Specification CM-SP-MULPIv3.0-I08-080522, Destination
        MAC Address section in the Common Radio Frequency Interface
        Encodings Annex."
     ::= { docsQosPktClassEntry 17 }

docsQosPktClassSourceMacAddr OBJECT-TYPE
     SYNTAX      MacAddress
     MAX-ACCESS  read-only
     STATUS      current
     DESCRIPTION
        "An Ethernet packet matches this entry when its source
        MAC address equals the value of this attribute.
        If the referenced parameter is not present in a classifier,
        this attribute reports the value of 'FFFFFFFFFFFF'"
     REFERENCE
        "DOCSIS 3.0 MAC and Upper Layer Protocols Interface
        Specification CM-SP-MULPIv3.0-I08-080522, Source MAC
        Address section in the Common Radio Frequency Interface
        Encodings Annex."
     ::= { docsQosPktClassEntry 18 }

docsQosPktClassEnetProtocolType OBJECT-TYPE
     SYNTAX      INTEGER {

                        none(0),
                        ethertype(1),
                        dsap(2),
                        mac(3),
                        all(4)
                      }
     MAX-ACCESS  read-only
     STATUS      current
     DESCRIPTION
        "This attribute indicates the format of the layer 3
        protocol ID in the Ethernet packet.  A value of 'none'
        means that the rule does not use the layer 3 protocol type
        as a matching criteria.
        A value of 'ethertype' means that the rule applies only
        to frames that contain an EtherType value.  Ethertype
        values are contained in packets using the Dec-Intel-Xerox
        (DIX) encapsulation or the RFC1042 Sub-Network
        Access Protocol (SNAP) encapsulation formats.

        A value of 'dsap' means that the rule applies only to frames
        using the IEEE802.3 encapsulation format with
        a Destination Service Access Point (DSAP) other than
        0xAA (which is reserved for SNAP).

        A value of 'mac' means that the rule applies only to MAC
        management messages for MAC management messages.

        A value of 'all' means that the rule matches all Ethernet
        packets.
        If the Ethernet frame contains an 802.1P/Q Tag header
        (i.e., EtherType 0x8100), this attribute applies
        to the embedded EtherType field within the 802.1P/Q
        header.
        If the referenced parameter is not present in a classifier,
        this attribute reports the value of 0."
     REFERENCE
        "DOCSIS 3.0 MAC and Upper Layer Protocols Interface
        Specification CM-SP-MULPIv3.0-I08-080522,
        Ethertype/DSAP/MacType section in the Common Radio
        Frequency Interface Encodings Annex."
     ::= { docsQosPktClassEntry 19 }

docsQosPktClassEnetProtocol OBJECT-TYPE
     SYNTAX      Unsigned32 (0..65535)
     MAX-ACCESS  read-only
     STATUS      current
     DESCRIPTION
        "If EnetProtocolType is 'none', this attribute is
        ignored when considering whether a packet matches the
        current rule.
        If EnetProtocolType is 'ethertype', this attribute
        gives the 16-bit value of the EtherType that the packet
        must match in order to match the rule.
        If EnetProtocolType is 'dsap', the lower 8 bits of this
        attribute's value must match the DSAP byte of the packet
        in order to match the rule.
        If EnetProtocolType is 'mac', the lower 8 bits of this
        attribute's value represent a
        lower bound (inclusive) of MAC management message type
        codes matched, and the upper 8 bits represent the
        upper bound (inclusive) of matched MAC message type
        codes.  Certain message type codes are excluded from
        matching, as specified in the reference.
        If the Ethernet frame contains an 802.1P/Q Tag header
        (i.e., EtherType 0x8100), this attribute applies
        to the embedded EtherType field within the 802.1P/Q
        header.
        If the referenced parameter is not present in the classifier,
        the value of this attribute is reported as 0."
     REFERENCE
        "DOCSIS 3.0 MAC and Upper Layer Protocols Interface
        Specification CM-SP-MULPIv3.0-I08-080522,
        Ethertype/DSAP/MacType section in the Common Radio
        Frequency Interface Encodings Annex."
     ::= { docsQosPktClassEntry 20 }

docsQosPktClassUserPriLow OBJECT-TYPE
     SYNTAX      Unsigned32 (0..7)
     MAX-ACCESS  read-only
     STATUS      current
     DESCRIPTION
        "This attribute applies only to Ethernet frames using
        the 802.1P/Q tag header (indicated with EtherType
        0x8100).  Such frames include a 16-bit Tag that contains
        a 3-bit Priority field and a 12-bit VLAN number.

        Tagged Ethernet packets must have a 3-bit Priority field
        within the range of PriLow to PriHigh in order to
        match this rule.
        If the referenced parameter is not present in the classifier,
        the value of this attribute is reported as 0."
     REFERENCE
        "DOCSIS 3.0 MAC and Upper Layer Protocols Interface
        Specification CM-SP-MULPIv3.0-I08-080522, IEEE 802.1P
        User_Priority section in the Common Radio Frequency Interface
        Encodings Annex."
     ::= { docsQosPktClassEntry 22 }

docsQosPktClassUserPriHigh OBJECT-TYPE
     SYNTAX      Unsigned32 (0..7)
     MAX-ACCESS  read-only
     STATUS      current
     DESCRIPTION
        "This attribute applies only to Ethernet frames using
        the 802.1P/Qtag header (indicated with EtherType
        0x8100).  Such frames include a 16-bit Tag that contains
        a 3-bit Priority field and a 12-bit VLAN number.

        Tagged Ethernet packets must have a 3-bit Priority field
        within the range of PriLow to
        PriHigh in order to match this rule.
        If the referenced parameter is not present in the classifier,
        the value of this attribute is reported as 7."
     REFERENCE
        "DOCSIS 3.0 MAC and Upper Layer Protocols Interface
        Specification CM-SP-MULPIv3.0-I08-080522, IEEE 802.1P
        User_Priority section in the Common Radio Frequency Interface
        Encodings Annex."
     ::= { docsQosPktClassEntry 23 }

docsQosPktClassVlanId OBJECT-TYPE
     SYNTAX      Unsigned32 (0 | 1..4094)
     MAX-ACCESS  read-only
     STATUS      current
     DESCRIPTION
        "This attribute applies only to Ethernet frames
        using the 802.1P/Q tag header.
        Tagged packets must have a VLAN Identifier that matches
        the value in order to match the rule.
        If the referenced parameter is not present in the classifier,
        the value of this attribute is reported as 0."
     REFERENCE
        "DOCSIS 3.0 MAC and Upper Layer Protocols Interface
        Specification CM-SP-MULPIv3.0-I08-080522, IEEE 802.1Q VLAN_ID
        section in the Common Radio Frequency Interface Encodings Annex."
     ::= { docsQosPktClassEntry 24 }

docsQosPktClassState OBJECT-TYPE
     SYNTAX      INTEGER {
                        active(1),
                        inactive(2)
                      }
     MAX-ACCESS  read-only
     STATUS      current
     DESCRIPTION
        "This attribute indicates whether or not the classifier
        is enabled to classify packets to a Service Flow.

        If the referenced parameter is not present in the classifier,
        the value of this attribute is reported as 'true'."
     REFERENCE
        "DOCSIS 3.0 MAC and Upper Layer Protocols Interface
        Specification CM-SP-MULPIv3.0-I08-080522, Classifier
        Activation State section in the Common Radio Frequency Interface
        Encodings Annex."
     ::= { docsQosPktClassEntry 25 }

docsQosPktClassPkts OBJECT-TYPE
     SYNTAX      Counter64
     MAX-ACCESS  read-only
     STATUS      current
     DESCRIPTION
        "This attribute counts the number of packets that have
        been classified using this entry. This includes
        all packets delivered to a Service Flow maximum rate
        policing function, whether or not that function drops
        the packets.
        This counter's last discontinuity is the
        ifCounterDiscontinuityTime for the same ifIndex that
        indexes this attribute."
     ::= { docsQosPktClassEntry 26 }

docsQosPktClassBitMap OBJECT-TYPE
     SYNTAX      BITS {
                        rulePriority(0),
                        activationState(1),
                        ipTos(2),
                        ipProtocol(3),
                        ipSourceAddr(4),
                        ipSourceMask(5),
                        ipDestAddr(6),
                        ipDestMask(7),
                        sourcePortStart(8),
                        sourcePortEnd(9),
                        destPortStart(10),
                        destPortEnd(11),
                        destMac(12),
                        sourceMac(13),
                        ethertype(14),
                        userPri(15),
                        vlanId(16),
                        flowLabel(17),
                        cmInterfaceMask(18),
                        icmpTypeLow(19),
                        icmpTypeHigh(20)
                      }
     MAX-ACCESS  read-only
     STATUS      current
     DESCRIPTION
        "This attribute indicates which parameter encodings
        were actually present in the DOCSIS packet classifier
        encoding signaled in the DOCSIS message that created
        or modified the classifier.  Note that Dynamic
        Service Change messages have replace semantics, so
        that all non-default parameters must be present whether
        the classifier is being created or changed.
        A bit of this attribute is set to 1 if the parameter indicated
        by the comment was present in the classifier encoding,
        and to 0 otherwise.
        Note that BITS are encoded most significant bit first,
        so that if, for example, bits 6 and 7 are set, this attribute
        is encoded as the octet string '030000'H."
     ::= { docsQosPktClassEntry 27 }

docsQosPktClassIpAddrType OBJECT-TYPE
     SYNTAX      InetAddressType
     MAX-ACCESS  read-only
     STATUS      current
     DESCRIPTION
        "This attribute indicates the type of the Internet
        address for InetSourceAddr, InetSourceMask, InetDestAddr,
        and InetDestMask.
        If the referenced parameter is not present in a classifier,
        this object reports the value of 'ipv4'."
     ::= { docsQosPktClassEntry 28 }

docsQosPktClassFlowLabel OBJECT-TYPE
     SYNTAX      Unsigned32 (0..1048575)
     MAX-ACCESS  read-only
     STATUS      current
     DESCRIPTION
        "This attribute represents the Flow Label field in
        the IPv6 header to be matched by the classifier.
        The value zero indicates that the Flow Label is not specified
        as part of the classifier and is not matched against
        the packets."
     REFERENCE
        "DOCSIS 3.0 MAC and Upper Layer Protocols Interface
        Specification CM-SP-MULPIv3.0-I08-080522, IPv6 Flow Label
        section in the Common Radio Frequency Interface Encodings
        Annex."
     ::= { docsQosPktClassEntry 29 }

docsQosPktClassCmInterfaceMask OBJECT-TYPE
     SYNTAX      DocsL2vpnIfList
     MAX-ACCESS  read-only
     STATUS      current
     DESCRIPTION
        "This attribute represents a bit-mask of the CM in-bound
        interfaces to which this classifier applies.
        This attribute only applies to QOS upstream Classifiers
        and upstream Drop Classifiers. For QOS downstream
        classifiers this object reports the zero-length
        string."
     REFERENCE
        "DOCSIS 3.0 MAC and Upper Layer Protocols Interface
        Specification CM-SP-MULPIv3.0-I08-080522, CM Interface
        Mask (CMIM) Encoding section in the Common Radio Frequency
        Interface Encodings Annex."
     ::= { docsQosPktClassEntry 30 }

docsQosPktClassIcmpTypeLow OBJECT-TYPE
     SYNTAX      Unsigned32 (0..255)
     MAX-ACCESS  read-only
     STATUS      current
     DESCRIPTION
        "This attribute specifies the low-end inclusive range of the
        ICMP type numbers to which a packet is compared. If the
        referenced parameter is not present in a classifier, this
        attribute reports the value of 0."
     REFERENCE
        "DOCSIS 3.0 MAC and Upper Layer Protocols Interface
        Specification CM-SP-MULPIv3.0-I17-120329, TypeLow
        encodings section in the Common Radio Frequency
        Interface Encodings Annex."
     ::= { docsQosPktClassEntry 31 }

docsQosPktClassIcmpTypeHigh OBJECT-TYPE
     SYNTAX      Unsigned32 (0..255)
     MAX-ACCESS  read-only
     STATUS      current
     DESCRIPTION
        "This attribute specifies the high-end inclusive range of the
        ICMP type numbers to which a packet is compared. If the
        referenced parameter is not present in a classifier, this
        attribute reports the value of 255."
     REFERENCE
        "DOCSIS 3.0 MAC and Upper Layer Protocols Interface
        Specification CM-SP-MULPIv3.0-I17-120329, TypeLow
        encodings section in the Common Radio Frequency
        Interface Encodings Annex."
     ::= { docsQosPktClassEntry 32 }

docsQosParamSetTable OBJECT-TYPE
     SYNTAX      SEQUENCE OF DocsQosParamSetEntry
     MAX-ACCESS  not-accessible
     STATUS      current
     DESCRIPTION
        "This object describes the set of QOS parameters defined
        in a managed device.
        DOCSIS 1.0 COS service profiles are not represented
        in this object.
        Each row corresponds to a DOCSIS QOS Parameter Set as
        signaled via DOCSIS MAC management messages. Each attribute
        of an instance of this object corresponds to
        one or part of one Service Flow Encoding.
        The BitMap attribute indicates which particular parameters
        were signaled in the original registration
        or dynamic service request message that created the
        QOS Parameter Set.
        In many cases, even if a QOS Parameter Set parameter was
        not signaled, the DOCSIS specification calls for
        a default value to be used.  That default value is reported
        as the value of the corresponding attribute in this
        object instance.

        Many attributes are not applicable, depending on the
        Service Flow direction, upstream scheduling type
        or Service Flow bonding configuration.  The attribute
        value reported in this case is specified by those attributes
        descriptions.

        For CM devices supporting the ParamSet object, the CM MUST
        report only the active service flow parameter set values.  
        The CM MAY report the admitted and provisioned service 
        flow parameter sets.
		
		Beginning with CCAP OSSI specification I15, CCAP reporting 
		of admitted and provisioned service flow parameter sets becomes optional,
		as a means of reducing the volume of information reported by the CCAP.
        The CCAP MUST report the active service flow parameter set values. 
		The CCAP MAY report the admitted and provisioned service flow parameter sets."
     REFERENCE
        "DOCSIS 3.0 MAC and Upper Layer Protocols Interface
        Specification CM-SP-MULPIv3.0-I08-080522, Service Flow
        Encodings section in the Common Radio Frequency Interface
        Encodings Annex."
     ::= { docsQosMibObjects 2}

docsQosParamSetEntry OBJECT-TYPE
     SYNTAX      DocsQosParamSetEntry
     MAX-ACCESS  not-accessible
     STATUS      current
     DESCRIPTION
        "The conceptual row of docsQosParamSetTable.
         The ifIndex key corresponds to the MAC Domain interface of the
         service flow of this Qos Param Set."
     INDEX { ifIndex,
             docsQosParamSetType,
             docsQosParamSetServiceFlowId
           }
     ::= { docsQosParamSetTable 1 }

DocsQosParamSetEntry ::= SEQUENCE {
     docsQosParamSetServiceClassName
                  SnmpAdminString,
     docsQosParamSetPriority
                  Unsigned32,
     docsQosParamSetMaxTrafficRate
                  BitRate,
     docsQosParamSetMaxTrafficBurst
                  Unsigned32,
     docsQosParamSetMinReservedRate
                  BitRate,
     docsQosParamSetMinReservedPkt
                  Unsigned32,
     docsQosParamSetActiveTimeout
                  Unsigned32,
     docsQosParamSetAdmittedTimeout
                  Unsigned32,
     docsQosParamSetMaxConcatBurst
                  Unsigned32,
     docsQosParamSetSchedulingType
                  SchedulingType,
     docsQosParamSetNomPollInterval
                  Unsigned32,
     docsQosParamSetTolPollJitter
                  Unsigned32,
     docsQosParamSetUnsolicitGrantSize
                  Unsigned32,
     docsQosParamSetNomGrantInterval
                  Unsigned32,
     docsQosParamSetTolGrantJitter
                  Unsigned32,
     docsQosParamSetGrantsPerInterval
                  Unsigned32,
     docsQosParamSetTosAndMask
                  OCTET STRING,
     docsQosParamSetTosOrMask
                  OCTET STRING,
     docsQosParamSetMaxLatency
                  Unsigned32,
     docsQosParamSetType
                  INTEGER,
     docsQosParamSetRequestPolicyOct
                  OCTET STRING,
     docsQosParamSetBitMap
                  BITS,
     docsQosParamSetServiceFlowId
                  Unsigned32,
     docsQosParamSetRequiredAttrMask
                  AttributeMask,
     docsQosParamSetForbiddenAttrMask
                  AttributeMask,
     docsQosParamSetAttrAggrRuleMask
                  AttrAggrRuleMask,
     docsQosParamSetAppId
                  Unsigned32,
     docsQosParamSetMultiplierContentionReqWindow
                  Unsigned32,
     docsQosParamSetMultiplierBytesReq
                  Unsigned32,
     docsQosParamSetMaxReqPerSidCluster
                  Unsigned32,
     docsQosParamSetMaxOutstandingBytesPerSidCluster
                  Unsigned32,
     docsQosParamSetMaxTotBytesReqPerSidCluster
                  Unsigned32,
     docsQosParamSetMaxTimeInSidCluster
                  Unsigned32,
     docsQosParamSetPeakTrafficRate
                  BitRate,
     docsQosParamSetDsResequencing
                  INTEGER,
     docsQosParamSetMinimumBuffer
                  Unsigned32,
     docsQosParamSetTargetBuffer
                  Unsigned32,
     docsQosParamSetMaximumBuffer
                  Unsigned32,
     docsQosParamSetAqmDisabled
                  TruthValue,
     docsQosParamSetAqmLatencyTarget
                  Unsigned32,
     docsQosParamSetHCMaxTrafficRate
                  CounterBasedGauge64,
     docsQosParamSetHCMinReservedRate
                  CounterBasedGauge64,
     docsQosParamSetHCPeakTrafficRate
                  CounterBasedGauge64,
     docsQosParamSetAqmAlgInUse
                  INTEGER,
     docsQosParamSetGuaranteedGrantInterval
                  Unsigned32,
     docsQosParamSetGuaranteedGrantRate
                  Unsigned32,
     docsQosParamSetGuaranteedRequestInterval
                  Unsigned32,
     docsQosParamSetImmedAqmMaxThreshold
                  Unsigned32,
     docsQosParamSetImmedAqmRangeExponentRampFunc
                  Unsigned32
     }

docsQosParamSetServiceClassName OBJECT-TYPE
     SYNTAX      SnmpAdminString (SIZE(0..15))
     MAX-ACCESS  read-only
     STATUS      current
     DESCRIPTION
        "This attribute represents the Service Class Name
        from which the parameter set values were derived.
        If the referenced parameter is not present in the corresponding
        DOCSIS QOS Parameter Set, this attribute returns the
        zero-length string."
     REFERENCE
        "DOCSIS 3.0 MAC and Upper Layer Protocols Interface
        Specification CM-SP-MULPIv3.0-I08-080522, Service Class Name
        section in the Common Radio Frequency Interface
        Encodings Annex."
     ::= { docsQosParamSetEntry 4 }

docsQosParamSetPriority OBJECT-TYPE
     SYNTAX      Unsigned32 (0..7)
     MAX-ACCESS  read-only
     STATUS      current
     DESCRIPTION
        "This attribute represents the relative priority
        of a Service Flow. Higher numbers indicate higher priority.

        This priority should only be used to differentiate Service
        Flow from identical parameter sets.
        This attribute returns 0 if the referenced parameter
        is not present in the corresponding DOCSIS QOS Parameter
        Set or if the parameter is not applicable."
     REFERENCE
        "DOCSIS 3.0 MAC and Upper Layer Protocols Interface
        Specification CM-SP-MULPIv3.0-I08-080522, Traffic Priority
        section in the Common Radio Frequency Interface Encodings
        Annex."
     ::= { docsQosParamSetEntry 5 }

docsQosParamSetMaxTrafficRate OBJECT-TYPE
     SYNTAX      BitRate
     UNITS       "bps"
     MAX-ACCESS  read-only
     STATUS      current
     DESCRIPTION
        "This attribute represents the 4 byte value of the maximum 
        sustained traffic rate in bits/sec allowed for this Service Flow.
        It represents all MAC frame data PDUs from the bytes following
        the MAC header HCS to the end of the CRC. The number
        of bytes forwarded is limited during any time interval.
        The value 0 means no maximum traffic rate is enforced.
        This attribute applies to both upstream and
        downstream Service Flows.
        This attribute returns 0 if the referenced parameter
        is not present in the corresponding DOCSIS QOS Parameter
        Set, or if the parameter is not applicable.
        This attribute will also return 0 if DataRateUnitSetting
        is set to a non-default value (e.g. kbps, mbps, or gbps) and the
        resulting value cannot be represented in 32 bits.  In which case,
        docsQosParamSetHCMaxTrafficRate should be utilized."
     REFERENCE
        "DOCSIS 3.0 MAC and Upper Layer Protocols Interface
        Specification CM-SP-MULPIv3.0-I08-080522, Maximum Sustained
        Traffic Rate section in the Common Radio Frequency Interface
        Encodings Annex."
     ::= { docsQosParamSetEntry 6 }

docsQosParamSetMaxTrafficBurst OBJECT-TYPE
     SYNTAX      Unsigned32
     UNITS       "bytes"
     MAX-ACCESS  read-only
     STATUS      current
     DESCRIPTION
        "This attribute specifies the token bucket size in
        bytes for this parameter set. The value is calculated
        from the byte following the MAC header HCS to  the end
        of the CRC. This object is applied in conjunction with
        MaxTrafficRate to calculate maximum sustained traffic
        rate.
        If the referenced parameter is not present in the corresponding
        DOCSIS QOS Parameter Set, this attribute
        returns 3044 for scheduling types 'bestEffort', 'nonRealTimePollingService'
        and 'realTimePollingService'.

        If this parameter is not applicable, it is reported as
        0."
     REFERENCE
        "DOCSIS 3.0 MAC and Upper Layer Protocols Interface
        Specification CM-SP-MULPIv3.0-I08-080522, Maximum Traffic
        Burst section in the Common Radio Frequency Interface
        Encodings Annex."
     ::= { docsQosParamSetEntry 7 }

docsQosParamSetMinReservedRate OBJECT-TYPE
     SYNTAX      BitRate
     UNITS       "bps"
     MAX-ACCESS  read-only
     STATUS      current
     DESCRIPTION
        "This attribute represents the 4 byte value of the guaranteed 
        minimum rate in bits/sec allowed for this Service Flow. 
        The value is calculated from the byte following the MAC header HCS
        to the end of the CRC. The value of 0 indicates that no
        bandwidth is reserved.
        If the referenced parameter is not present in the corresponding
        DOCSIS QOS Parameter Set, this attribute
        returns 0. If the parameter is not applicable, it is
        reported as 0.

        This attribute will also return 0 if DataRateUnitSetting
        is set to a non-default value (e.g. kpbs, mbps, or gbps)
        and the resulting value cannot be represented in 32 bits.  
        In which case, HCMinReservedRate should be utilized."
     REFERENCE
        "DOCSIS 3.0 MAC and Upper Layer Protocols Interface
        Specification CM-SP-MULPIv3.0-I08-080522, Minimum Reserved
        Traffic Rate section of the Common Radio Frequency Interface
        Encodings Annex."
     ::= { docsQosParamSetEntry 8 }

docsQosParamSetMinReservedPkt OBJECT-TYPE
     SYNTAX      Unsigned32 (0..65535)
     UNITS       "bytes"
     MAX-ACCESS  read-only
     STATUS      current
     DESCRIPTION
        "This attribute specifies an assumed minimum packet
        size in bytes for which the MinReservedRate will be
        provided. The value is calculated from the byte following
        the MAC header HCS to the end of the CRC. If the referenced
        parameter is omitted from a DOCSIS QOS parameter
        set, the used and reported value is CMTS implementation
        and the CM reports a value of 0. If the referenced
        parameter is not applicable to the direction or
        scheduling type of the Service Flow, both CMTS and CM
        report the value 0."
     REFERENCE
        "DOCSIS 3.0 MAC and Upper Layer Protocols Interface
        Specification CM-SP-MULPIv3.0-I08-080522, Assumed Minimum
        Reserved Rate Packet Size, in the Common Radio Frequency
        Interface Encodings Annex."
     ::= { docsQosParamSetEntry 9 }

docsQosParamSetActiveTimeout OBJECT-TYPE
     SYNTAX      Unsigned32 (0..65535)
     UNITS       "seconds"
     MAX-ACCESS  read-only
     STATUS      current
     DESCRIPTION
        "This attribute specifies the maximum duration in
        seconds that resources remain unused on an active service
        flow before the CMTS signals that both the active
        and admitted parameter sets are null. The value 0 signifies
        an infinite amount of time.
        If the referenced parameter is not present in the corresponding
        DOCSIS QOS Parameter Set, this attribute
        returns 0."
     REFERENCE
        "DOCSIS 3.0 MAC and Upper Layer Protocols Interface
        Specification CM-SP-MULPIv3.0-I08-080522, Timeout for Active
        QoS Parameters section in the Common Radio Frequency Interface
        Encodings Annex."
     ::= { docsQosParamSetEntry 10 }

docsQosParamSetAdmittedTimeout OBJECT-TYPE
     SYNTAX      Unsigned32 (0..65535)
     UNITS       "seconds"
     MAX-ACCESS  read-only
     STATUS      current
     DESCRIPTION
        "This attribute specifies the maximum duration in
        seconds that resources remain in admitted state before
        resources must be released. The value of 0 signifies
        an infinite amount  of time. If the referenced parameter
        is not present in the corresponding DOCSIS QOS
        Parameter Set, this attribute returns 200."
     REFERENCE
        "DOCSIS 3.0 MAC and Upper Layer Protocols Interface
        Specification CM-SP-MULPIv3.0-I08-080522, Timeout for Admitted
        QoS Parameters section in the Common Radio Frequency Interface
        Encodings Annex."
     ::= { docsQosParamSetEntry 11 }

docsQosParamSetMaxConcatBurst OBJECT-TYPE
     SYNTAX      Unsigned32 (0..65535)
     UNITS       "bytes"
     MAX-ACCESS  read-only
     STATUS      current
     DESCRIPTION
        "This attribute specifies the maximum concatenated
        burst in bytes that an upstream Service Flow is allowed.

        The value is calculated from the FC byte of the Concatenation
        MAC Header to the last CRC byte of the last concatenated
        MAC frame, inclusive.  The value of 0 specifies
        no maximum burst.
        If the referenced parameter is not present in the corresponding
        DOCSIS QOS Parameter Set, this attribute
        returns the value of 1522 for scheduling types 'bestEffort',
        'nonRealTimePollingService', and  'realTimePollingService'.
        If the parameter is not applicable,
        it is reported as 0."
     REFERENCE
        "DOCSIS 3.0 MAC and Upper Layer Protocols Interface
        Specification CM-SP-MULPIv3.0-I08-080522, Maximum Concatenated
        Burst section in the Common Radio Frequency Interface
        Encodings Annex."
     ::= { docsQosParamSetEntry 12 }

docsQosParamSetSchedulingType OBJECT-TYPE
     SYNTAX      SchedulingType
     MAX-ACCESS  read-only
     STATUS      current
     DESCRIPTION
        "This attribute specifies the upstream scheduling
        service used for upstream Service Flow.
        If the referenced parameter is not present in the corresponding
        DOCSIS QOS Parameter Set of an upstream Service
        Flow, this attribute returns the value of 'bestEffort'.
        For QOS parameter sets of downstream Service
        Flows, this attribute's value is reported as 'undefined'."
     REFERENCE
        "DOCSIS 3.0 MAC and Upper Layer Protocols Interface
        Specification CM-SP-MULPIv3.0-I08-080522, Service Flow
        Scheduling Type section in the Common Radio Frequency Interface
        Encodings Annex."
     ::= { docsQosParamSetEntry 13 }

docsQosParamSetNomPollInterval OBJECT-TYPE
     SYNTAX      Unsigned32
     UNITS       "microseconds"
     MAX-ACCESS  read-only
     STATUS      current
     DESCRIPTION
        "This attribute specifies the nominal interval in
        microseconds between successive unicast request opportunities
        on an upstream Service Flow.
        This attribute applies only to upstream Service Flows
        with SchedulingType of value 'nonRealTimePollingService',
        'realTimePollingService', and 'unsolictedGrantServiceWithAD'.
        The parameter is mandatory
        for 'realTimePollingService'. If the parameter
        is omitted with 'nonRealTimePollingService',
        the CMTS uses an implementation-dependent value. If
        the parameter is omitted with 'unsolictedGrantServiceWithAD(5)'
        the CMTS uses the value of the Nominal
        Grant Interval parameter. In all cases, the CMTS reports
        the value it is using when the parameter is applicable.
        The CM reports the signaled parameter value
        if it was signaled. Otherwise, it returns 0.
        If the referenced parameter is not applicable to the
        direction or scheduling type of the corresponding DOCSIS
        QOS Parameter Set, both CMTS and CM report this
        attribute's value as 0."
     REFERENCE
        "DOCSIS 3.0 MAC and Upper Layer Protocols Interface
        Specification CM-SP-MULPIv3.0-I08-080522, Polling Interval
        section in the Common Radio Frequency Interface
        Encodings Annex."
     ::= { docsQosParamSetEntry 14 }

docsQosParamSetTolPollJitter OBJECT-TYPE
     SYNTAX      Unsigned32
     UNITS       "microseconds"
     MAX-ACCESS  read-only
     STATUS      current
     DESCRIPTION
        "This attribute specifies the maximum amount of time
        in microseconds that the unicast request interval
        may be delayed from the nominal periodic schedule on
        an upstream Service Flow. This parameter is applicable
        only to upstream Service Flows with a SchedulingType
        of 'realTimePollingService' or 'unsolictedGrantServiceWithAD'.

        If the referenced parameter is applicable but not present
        in the corresponding DOCSIS QOS Parameter Set,
        the CMTS uses an implementation-dependent value and
        reports the value it is using. The CM reports a value
        of 0 in this case.
        If the parameter is not applicable to the direction or
        upstream scheduling type of the Service Flow, both
        CMTS and CM report this attribute's value as 0."
     REFERENCE
        "DOCSIS 3.0 MAC and Upper Layer Protocols Interface
        Specification CM-SP-MULPIv3.0-I08-080522, Tolerated Poll
        Jitter section in the Common Radio Frequency Interface
        Encodings Annex."
     ::= { docsQosParamSetEntry 15 }

docsQosParamSetUnsolicitGrantSize OBJECT-TYPE
     SYNTAX      Unsigned32 (0..65535)
     UNITS       "bytes"
     MAX-ACCESS  read-only
     STATUS      current
     DESCRIPTION
        "This attribute specifies the unsolicited grant size
        in bytes. The grant size includes the entire MAC frame
        data PDU from the Frame Control byte to the end of
        the MAC frame.
        The referenced parameter is applicable only for upstream
        flows with a SchedulingType of  'unsolicitedGrantServicewithAD'
        or 'unsolicitedGrantService',
        and it is mandatory when applicable. Both CMTS and
        CM report the signaled value of the parameter in this
        case.
        If the referenced parameter is not applicable to the
        direction or scheduling type of the corresponding DOCSIS
        QOS Parameter Set, both CMTS and CM report this
        attribute's value as 0."
     REFERENCE
        "DOCSIS 3.0 MAC and Upper Layer Protocols Interface
        Specification CM-SP-MULPIv3.0-I08-080522, Unsolicited
        Grant Size section in the Common Radio Frequency Interface
        Encodings Annex."
     ::= { docsQosParamSetEntry 16 }

docsQosParamSetNomGrantInterval OBJECT-TYPE
     SYNTAX      Unsigned32
     UNITS       "microseconds"
     MAX-ACCESS  read-only
     STATUS      current
     DESCRIPTION
        "This attribute specifies the nominal interval in
        microseconds between successive data grant opportunities
        on an upstream Service Flow.
        The referenced parameter is applicable only for upstream
        flows with a SchedulingType of 'unsolicitedGrantServicewithAD'
        or 'unsolicitedGrantService(6)',
        and it is mandatory when applicable. Both CMTS
        and CM report the signaled value of the parameter in this
        case.
        If the referenced parameter is not applicable to the
        direction or scheduling type of the corresponding DOCSIS
        QOS Parameter Set, both CMTS and CM report this
        attribute's value as 0."
     REFERENCE
        "DOCSIS 3.0 MAC and Upper Layer Protocols Interface
        Specification CM-SP-MULPIv3.0-I08-080522, Nominal Grant
        Interval section in the Common Radio Frequency Interface
        Encodings Annex."
     ::= { docsQosParamSetEntry 17 }

docsQosParamSetTolGrantJitter OBJECT-TYPE
     SYNTAX      Unsigned32
     UNITS       "microseconds"
     MAX-ACCESS  read-only
     STATUS      current
     DESCRIPTION
        "This attribute specifies the maximum amount of time
        in microseconds that the transmission opportunities
        may be delayed from the nominal periodic schedule.
        The referenced parameter is applicable only for
        upstream flows with a SchedulingType of 'unsolicitedGrantServicewithAD'
        or 'unsolicitedGrantService(6)',
        and it is mandatory when applicable. Both CMTS
        and CM report the signaled value of the parameter
        in this case.
        If the referenced parameter is not applicable to the
        direction or scheduling type of the corresponding DOCSIS
        QOS Parameter Set, both CMTS and CM report this
        attribute's value as 0."
     REFERENCE
        "DOCSIS 3.0 MAC and Upper Layer Protocols Interface
        Specification CM-SP-MULPIv3.0-I08-080522, Tolerated Grant
        Jitter section in the Common Radio Frequency Interface
        Encodings Annex."
     ::= { docsQosParamSetEntry 18 }

docsQosParamSetGrantsPerInterval OBJECT-TYPE
     SYNTAX      Unsigned32 (0..127)
     UNITS       "dataGrants"
     MAX-ACCESS  read-only
     STATUS      current
     DESCRIPTION
        "This attribute specifies the number of data grants
        per Nominal Grant Interval (NomGrantInterval). The
        referenced parameter is applicable only for upstream
        flows with a SchedulingType of 'unsolicitedGrantServicewithAD'
        or 'unsolicitedGrantService',
        and it is mandatory when applicable. Both CMTS and CM
        report the signaled value of the parameter in this case.

        If the referenced parameter is not applicable to the
        direction or scheduling type of the corresponding DOCSIS
        QOS Parameter Set, both CMTS and CM report this
        attribute's value as 0."
     REFERENCE
        "DOCSIS 3.0 MAC and Upper Layer Protocols Interface
        Specification CM-SP-MULPIv3.0-I08-080522, Grants per
        Interval section in the Common Radio Frequency Interface
        Encodings Annex."
     ::= { docsQosParamSetEntry 19 }

docsQosParamSetTosAndMask OBJECT-TYPE
     SYNTAX      OCTET STRING (SIZE(1))
     MAX-ACCESS  read-only
     STATUS      current
     DESCRIPTION
        "This attribute specifies the AND mask for the IP TOS
        byte for overwriting an IPv4 packet's TOS value or IPv6
        packet's Traffic Class value. The IP packet TOS byte
        is bitwise ANDed with TosAndMask, then the result
        is bitwise ORed with TosORMask and the result is written
        to the IP packet TOS byte.
        A value of 'FF'H for TosAndMask and a value of '00'H for
        TosOrMask means that the IP Packet TOS byte is not overwritten.

        This combination is reported if the referenced parameter
        is not present in a QOS Parameter Set.
        The IP TOS octet as originally defined in RFC 791 has been
        superseded by the 6-bit Differentiated Services
        Field (DSField, RFC 3260) and the 2-bit Explicit Congestion
        Notification Field (ECN field, RFC 3168).
        The IPv6 Traffic Class octet RFC 2460 is consistent with
        that new definition.
        Network operators SHOULD avoid specifying values of
        TosAndMask and TosORMask that would result in the modification
        of the ECN bits.
        In particular, operators should not use values of TosAndMask
        that have either of the least-significant
        two bits set to 0. Similarly, operators should not use
        values of TosORMask that have either of the least-significant
        two bits set to 1.
        Even though this attribute is only enforced by the CMTS,
        the CM reports the value as signaled in the referenced
        parameter."
     REFERENCE
        "DOCSIS 3.0 MAC and Upper Layer Protocols Interface
        Specification CM-SP-MULPIv3.0-I08-080522, IP Type Of Service
        (DSCP) Overwrite section in the Common Radio Frequency
        Interface Encodings Annex; [RFC 3168]; [RFC 3260];
        [RFC 2460]; [RFC 791]."
     ::= { docsQosParamSetEntry 20 }

docsQosParamSetTosOrMask OBJECT-TYPE
     SYNTAX      OCTET STRING (SIZE (1))
     MAX-ACCESS  read-only
     STATUS      current
     DESCRIPTION
        "This attribute specifies the OR mask for the IPv4 TOS
        value or IPv6 Traffic Class value. See the description
        of TosAndMask for further details.
        The IP TOS octet, as originally defined in RFC 791 has
        been superseded by the 6-bit Differentiated Services
        Field (DSField, RFC 3260) and the 2-bit Explicit Congestion
        Notification Field (ECN field, RFC 3168).
        The IPv6 Traffic Class octet RFC 2460 is consistent
        with that new definition.
        Network operators SHOULD avoid specifying values of
        TosAndMask and TosORMask that would result in the modification
        of the ECN bits."
     REFERENCE
        "DOCSIS 3.0 MAC and Upper Layer Protocols Interface
        Specification CM-SP-MULPIv3.0-I08-080522, IP Type Of Service
        (DSCP) Overwrite section in the Common Radio Frequency
        Interface Encodings Annex; [RFC 3168]; [RFC 3260];
        [RFC 2460]; [RFC 791]."
     ::= { docsQosParamSetEntry 21 }

docsQosParamSetMaxLatency OBJECT-TYPE
     SYNTAX      Unsigned32
     UNITS       "microseconds"
     MAX-ACCESS  read-only
     STATUS      current
     DESCRIPTION
        "This attribute specifies the maximum latency between
        the reception of a packet by the CMTS on its NSI and
        the forwarding of the packet to the RF interface. A value
        of 0 signifies no maximum latency is enforced. This
        attribute only applies to downstream Service Flows.

        If the referenced parameter is not present in the corresponding
        downstream DOCSIS QOS Parameter Set, this
        attribute returns 0. This parameter is not applicable
        to upstream DOCSIS QOS Parameter Sets, so its value
        is reported as 0 in that case."
     REFERENCE
        "DOCSIS 3.0 MAC and Upper Layer Protocols Interface
        Specification CM-SP-MULPIv3.0-I08-080522, Maximum Downstream
        Latency section in the Common Radio Frequency Interface
        Encodings Annex."
     ::= { docsQosParamSetEntry 22 }

docsQosParamSetType OBJECT-TYPE
     SYNTAX      INTEGER {

                        active (1),
                        admitted(2),
                        provisioned(3)
                      }
     MAX-ACCESS  not-accessible
     STATUS      current
     DESCRIPTION
        "This key represents the QoS Parameter Set Type of the
        Service Flow.
        The following values are defined:
        'active'
        Indicates the Active QOS parameter set, describing
        the service currently being provided by the DOCSIS MAC
        domain to the service flow.
        'admitted'
        Indicates the Admitted QOS Parameter Set, describing
        services reserved by the DOCSIS MAC domain for use
        by the service flow.
        'provisioned'
        Indicates the QOS Parameter Set defined in the DOCSIS
        CM Configuration file for the service flow.
        Only the   'active ' service flow parameter set is required to 
        be reported.  The  'admitted ' and  'provisioned'sets are not 
        required to be reported."
     REFERENCE
        "DOCSIS 3.0 MAC and Upper Layer Protocols Interface
        Specification CM-SP-MULPIv3.0-I08-080522, Service Flow
        Scheduling Type section in the Common Radio Frequency
        Interface Encodings Annex; [RFC 4323]."
     ::= { docsQosParamSetEntry 23 }

docsQosParamSetRequestPolicyOct OBJECT-TYPE
     SYNTAX      OCTET STRING (SIZE (4))
                 -- A 32-bit mask represented most significant byte
                 -- first.  The 32-bit integer represented in this
                 -- manner equals the binary value of the referenced
                 -- integer parameter of the DOCSIS RFI
                 -- specification.
                 -- The BITS syntax is not used in order to avoid
                 -- the confusion caused by different bit-numbering
                 -- conventions.
     MAX-ACCESS  read-only
     STATUS      current
     DESCRIPTION
        "This attribute specifies which transmit interval
        opportunities the CM omits for upstream transmission
        requests and packet transmissions. This object
        takes its default value for downstream Service Flows.
        Unless otherwise indicated, a bit value of 1 means
        that a CM must not use that opportunity for upstream transmission.

        The format of this string enumerated the bits from 0 to
        31 from left to right, for example bit 0 corresponds
        to the left most bit of the fourth octet. (octets numbered
        from right to left). The bit positions are defined
        as follows:
           'broadcastReqOpp'
               all CMs broadcast request opportunities
           'priorityReqMulticastReq'
               priority request multicast request opportunities
           'reqDataForReq'
               request/data opportunities for requests
           'reqDataForData'
               request/data opportunities for data
           'piggybackReqWithData'
               piggyback requests with data
           'concatenateData'
               concatenate data
           'fragmentData'
               fragment data
           'suppressPayloadHeaders'
               suppress payload headers
           'dropPktsExceedUGSize'
               A value of 1 means that the service flow must drop
               packets that do not fit in the Unsolicited Grant size.

        If the referenced parameter is not present in a QOS Parameter
        Set, the value of this object is reported as '00000000'H."
     REFERENCE
        "DOCSIS 3.0 MAC and Upper Layer Protocols Interface
        Specification CM-SP-MULPIv3.0-I08-080522, Request/
        Transmission Policy section in the Common Radio Frequency
        Interface Encodings Annex."
     ::= { docsQosParamSetEntry 24 }

docsQosParamSetBitMap OBJECT-TYPE
     SYNTAX      BITS {

                        trafficPriority(0),
                        maxTrafficRate(1),
                        maxTrafficBurst(2),
                        minReservedRate(3),
                        minReservedPkt(4),
                        activeTimeout(5),
                        admittedTimeout(6),
                        maxConcatBurst(7),
                        schedulingType(8),
                        requestPolicy(9),
                        nomPollInterval(10),
                        tolPollJitter(11),
                        unsolicitGrantSize(12),
                        nomGrantInterval(13),
                        tolGrantJitter(14),
                        grantsPerInterval(15),
                        tosOverwrite(16),
                        maxLatency(17),
                        requiredAttrMask(18),
                        forbiddenAttrMask(19),
                        attrAggrMask(20),
                        applicationId(21),
                        multipCntnReqWindow(22),
                        multipBytesReq(23),
                        maxReqPerSidCluster(24),
                        maxOutstandingBytesPerSidCluster(25),
                        maxTotalBytesReqPerSidCluster(26),
                        maximumTimeInSidCluster(27),
                        peakTrafficRate(28),
                        dsResequencing(29),
                        minimumBuffer(30),
                        targetBuffer(31),
                        maximumBuffer(32),
                        aqmEnabled(33),
                        aqmLatencyTarget(34),
                        dataRateUnit(35),
                        aqmAlgInUse(36),
                        guaranteedGrantInterval(37),
                        guaranteedGrantRate(38),
                        guaranteedGrantRequestInterval(39)
                    }
     MAX-ACCESS  read-only
     STATUS      current
     DESCRIPTION
        "This attribute indicates the set of QOS Parameter
        Set parameters actually signaled in the DOCSIS registration
        or dynamic service request message that created
        or modified the QOS Parameter Set. A bit is set to
        1 when the associated parameter is present in the original
        request as follows:
        	'trafficPriority'  Traffic Priority
        	'maxTrafficRate'  Maximum Sustained Traffic Rate

        	'maxTrafficBurst'  Maximum Traffic Burst
        	'minReservedRate'  Minimum Reserved Traffic Rate

        	'minReservedPkt'  Assumed Minimum Reserved Rate Packet
        Size
        	'activeTimeout'  Timeout for Active QoS Parameters

        	'admittedTimeout'  Timeout for Admitted QoS Parameters

        	'maxConcatBurst'  Maximum Concatenated Burst
        	'schedulingType'  Service Flow Scheduling Type
        	'requestPolicy'  Request/Transmission Policy
        	'nomPollInterval'  Nominal Polling Interval
        	'tolPollJitter'  Tolerated Poll Jitter
        	'unsolicitGrantSize'  Unsolicited Grant Size
        	'nomGrantInterval'  Nominal Grant Interval
        	'tolGrantJitter'  Tolerated Grant Jitter
        	'grantsPerInterval'  Grants per Interval
        	'tosOverwrite'  IP Type of Service (DSCP) Overwrite
        	'maxLatency'  Maximum Downstream Latency
        	'requiredAttrMask'  Service Flow Required Attribute
                              Mask
        	'forbiddenAttrMask  Service Flow Forbidden Attribute
                              Mask
        	'attrAggrMask'  Service Flow Attribute Aggregation
                          Mask
        	'applicationId'  Application Identifier
        	'multipCntnReqWindow'  Multiplier to Contention
                                 Request Backoff Window
        	'multipBytesReq'  Multiplier to Number of Bytes Requested
        	'maxReqPerSidCluster'  Maximum Requests per SID Cluster
        	'maxOutstandingBytesPerSidCluster'  Maximum Outstanding
                                              Bytes per SID Cluster
        	'maxTotalBytesReqPerSidCluster'  Maximum Total
                                           Bytes Requested per SID
                                           Cluster
        	'maximumTimeInSidCluster'  Maximum Time in the SID Cluster
        	'peakTrafficRate'  Peak Traffic Rate
        	'dsResequencing'   Downstream Resequencing
            'minimumBuffer'    Minimum Buffer
            'targetBuffer'     Target Buffer
            'maximumBuffer'    Maximum Buffer C
            'aqmEnabled '      SF AQM Enabled
            'aqmLatencyTarget' Classic AQM Latency Target
            'dataRateUnit'     Data Rate Unit Setting
            'aqmAlgInUse'      AQM Algorithm in Use
            'guaranteedGrantInterval'        Guaranteed Grant Interval
            'guaranteedGrantRate'            Guaranteed Grant Rate
            'guaranteedGrantRequestInterval' Guaranteed Grant Request Interval

        Note that when Service Class names are expanded, the
        registration or dynamic response message may contain
        parameters expanded by the CMTS based on a stored service
        class. These expanded parameters are not indicated
        by a 1 bit in this attribute.
        Note that even though some QOS Parameter Set parameters
        may not be signaled in a message (so that the parameter's
        bit in this object is 0), the DOCSIS specification
        requires that default values be used. These default
        values are reported as the corresponding attribute."
     REFERENCE
        "DOCSIS 3.0 MAC and Upper Layer Protocols Interface
        Specification CM-SP-MULPIv3.0-I08-080522, Service Flow
        Encodings section in the Common Radio Frequency Interface
        Encodings Annex."
     ::= { docsQosParamSetEntry 25 }

docsQosParamSetServiceFlowId OBJECT-TYPE
     SYNTAX      Unsigned32 (1.. 4294967295)
     MAX-ACCESS  not-accessible
     STATUS      current
     DESCRIPTION
        "This key represents the Service Flow ID for the service
        flow."
     REFERENCE
        "DOCSIS 3.0 MAC and Upper Layer Protocols Interface
        Specification CM-SP-MULPIv3.0-I08-080522, Service
        Identifier section in the Common Radio Frequency Interface
        Encodings Annex."
     ::= { docsQosParamSetEntry 26 }

docsQosParamSetRequiredAttrMask OBJECT-TYPE
     SYNTAX      AttributeMask
     MAX-ACCESS  read-only
     STATUS      current
     DESCRIPTION
        "This attribute specifies the Required Attribute
        Mask to compare with the Provisioned Required Attributes
        when selecting the bonding groups for the service
        flow.
        If the referenced parameter is not present in the corresponding
        DOCSIS QOS Parameter Set, this attribute returns '00000000'H."
     REFERENCE
        "DOCSIS 3.0 MAC and Upper Layer Protocols Interface
        Specification CM-SP-MULPIv3.0-I08-080522, Service Flow Required
        Attribute Mask section in the Common Radio Frequency Interface
        Encodings Annex."
     ::= { docsQosParamSetEntry 27 }

docsQosParamSetForbiddenAttrMask OBJECT-TYPE
     SYNTAX      AttributeMask
     MAX-ACCESS  read-only
     STATUS      current
     DESCRIPTION
        "This attribute specifies the Forbidden Attribute
        Mask to compare with the Provisioned Forbidden Attributes
        when selecting the bonding groups for the service
        flow.
        If the referenced parameter is not present in the corresponding
        DOCSIS QOS Parameter Set, this attribute returns '00000000'H."
     REFERENCE
        "DOCSIS 3.0 MAC and Upper Layer Protocols Interface
        Specification CM-SP-MULPIv3.0-I08-080522, Service Flow Forbidden
        Attribute Mask section in the Common Radio Frequency Interface
        Encodings Annex."
     ::= { docsQosParamSetEntry 28 }

docsQosParamSetAttrAggrRuleMask OBJECT-TYPE
     SYNTAX      AttrAggrRuleMask
     MAX-ACCESS  read-only
     STATUS      current
     DESCRIPTION
        "This attribute specifies the Attribute Aggregation
        Mask to compare the Service Flow Required and Forbidden
        Attributes with the CMTS dynamically-created
        bonding group when selecting the bonding groups for
        the service flow.
        If the referenced parameter is not present in the corresponding
        DOCSIS QOS Parameter Set, this attribute returns '00000000'H."
     REFERENCE
        "DOCSIS 3.0 MAC and Upper Layer Protocols Interface
        Specification CM-SP-MULPIv3.0-I08-080522, Service Flow
        Attribute Aggregation Mask section in the Common Radio
        Frequency Interface Encodings Annex."
     ::= { docsQosParamSetEntry 29 }

docsQosParamSetAppId OBJECT-TYPE
     SYNTAX      Unsigned32
     MAX-ACCESS  read-only
     STATUS      current
     DESCRIPTION
        "This attribute represents the Application Identifier
        associated with the service flow for purposes beyond the
        scope of this specification.
        If the referenced parameter is not present in the corresponding
        DOCSIS QOS Parameter Set, this attribute returns 0."
     REFERENCE
        "DOCSIS 3.0 MAC and Upper Layer Protocols Interface
        Specification CM-SP-MULPIv3.0-I08-080522, Application
        Identifier section in the Common Radio Frequency Interface
        Encodings Annex."
     ::= { docsQosParamSetEntry 30 }

docsQosParamSetMultiplierContentionReqWindow OBJECT-TYPE
     SYNTAX      Unsigned32 (4..12)
     UNITS       "eighths"
     MAX-ACCESS  read-only
     STATUS      current
     DESCRIPTION
        "This attribute specifies the multiplier to be applied by a
        CM when performing contention request backoff for data requests.
        This attribute only applies to upstream Service Flows in 3.0
        operation. If the referenced parameter is not present in the
        upstream DOCSIS QOS Parameter Set or is not applicable, this
        attribute returns 8."
     REFERENCE
        "DOCSIS 3.0 MAC and Upper Layer Protocols Interface
        Specification CM-SP-MULPIv3.0-I08-080522, Multiplier to
        Contention Request Backoff Window section in the Common
        Radio Frequency Interface Encodings Annex."
     ::= { docsQosParamSetEntry 31 }

docsQosParamSetMultiplierBytesReq OBJECT-TYPE
     SYNTAX      Unsigned32 (1 | 2 | 4 | 8 | 16)
     UNITS       "requests"
     MAX-ACCESS  read-only
     STATUS      current
     DESCRIPTION
        "This attribute specifies the assumed bandwidth request
        multiplier. This attribute only applies to upstream Service
        Flows in 3.0 operation. If the referenced parameter is not
        present in the upstream DOCSIS QOS Parameter Set, or is not
        applicable, this attribute returns 4."
     REFERENCE
        "DOCSIS 3.0 MAC and Upper Layer Protocols Interface
        Specification CM-SP-MULPIv3.0-I08-080522, Multiplier
        to Number of Bytes Requested section in the Common
        Radio Frequency Interface Encodings Annex."
     ::= { docsQosParamSetEntry 32 }

docsQosParamSetMaxReqPerSidCluster OBJECT-TYPE
     SYNTAX      Unsigned32 (0..255)
     UNITS       "bytes"
     MAX-ACCESS  read-only
     STATUS      deprecated
     DESCRIPTION
        "This attribute specifies the maximum number of requests
        that a CM can make within a given SID Cluster before it must
        switch to a different SID Cluster to make further requests.
        A value of 0 indicates there is no limit.

        This attribute only applies to upstream Service Flows in 3.0
        operation, in other cases it is reported as 0. If the
        referenced parameter is not present in the DOCSIS QOS
        Parameter Set, this attribute returns 0.

        This attribute has been deprecated and replaced with
        docsQosServiceFlowMaxReqPerSidCluster in the
        docsQosServiceFlowTable."
     REFERENCE
        "DOCSIS 3.0 MAC and Upper Layer Protocols Interface
        Specification CM-SP-MULPIv3.0-I08-080522, Maximum Requests
        per SID Cluster section in the Common Radio Frequency
        Interface Encodings Annex."
     ::= { docsQosParamSetEntry 33 }

docsQosParamSetMaxOutstandingBytesPerSidCluster OBJECT-TYPE
     SYNTAX      Unsigned32
     UNITS       "bytes"
     MAX-ACCESS  read-only
     STATUS      deprecated
     DESCRIPTION
        "This attribute specifies the maximum number of bytes
        for which a CM can have requests outstanding on a given
        SID Cluster. If defined number of bytes are outstanding
        and further requests are required, the CM must switch to
        a different SID Cluster if one is available. A value of 0
        indicates there is no limit.

        This attribute only applies to upstream Service Flows in 3.0
        operation, in other cases it is reported as 0.
        If the referenced parameter is not present in the DOCSIS QOS
        Parameter Set, this attribute returns 0.

        This attribute has been deprecated and replaced with
        docsQosServiceFlowMaxOutstandingBytesPerSidCluster in the
        docsQosServiceFlowTable."
     REFERENCE
        "DOCSIS 3.0 MAC and Upper Layer Protocols Interface
        Specification CM-SP-MULPIv3.0-I08-080522, Maximum
        Outstanding Bytes per SID Cluster section in the Common
        Radio Frequency Interface Encodings Annex."
     ::= { docsQosParamSetEntry 34 }

docsQosParamSetMaxTotBytesReqPerSidCluster OBJECT-TYPE
     SYNTAX      Unsigned32
     UNITS       "bytes"
     MAX-ACCESS  read-only
     STATUS      deprecated
     DESCRIPTION
        "This attribute specifies the maximum total number of bytes
        a CM can have requested using a given SID Cluster before it
        must switch to a different SID Cluster to make further
        requests. A value of 0 indicates there is no limit.

        This attribute only applies to upstream Service Flows in 3.0
        operation, in other cases it is reported as 0.
        If the referenced parameter is not present in the DOCSIS QOS
        Parameter Set, this attribute returns 0.

        This attribute has been deprecated and replaced with
        docsQosServiceFlowMaxTotBytesReqPerSidCluster in the
        docsQosServiceFlowTable."
     REFERENCE
        "DOCSIS 3.0 MAC and Upper Layer Protocols Interface
        Specification CM-SP-MULPIv3.0-I08-080522, Maximum Total Bytes
        Requested per SID Cluster section in the Common Radio
        Frequency Interface Encodings Annex."
     ::= { docsQosParamSetEntry 35 }

docsQosParamSetMaxTimeInSidCluster OBJECT-TYPE
     SYNTAX      Unsigned32 (0..65535)
     UNITS       "milliseconds"
     MAX-ACCESS  read-only
     STATUS       deprecated
     DESCRIPTION
        "This attribute specifies the maximum time in milliseconds
        that a CM may use a particular SID Cluster before it must
        switch to a different SID Cluster to make further requests.
        A value of 0 indicates there is no limit.

        This attribute only applies to upstream Service Flows in 3.0
        operation, in other cases it is reported as 0.
        If the referenced parameter is not present in the DOCSIS QOS
        Parameter Set, this attribute returns 0.

        This attribute has been deprecated and replaced with
        docsQosServiceFlowMaxTimeInSidCluster in the
        docsQosServiceFlowTable."
     REFERENCE
        "DOCSIS 3.0 MAC and Upper Layer Protocols Interface
        Specification CM-SP-MULPIv3.0-I08-080522, Maximum Time in
        the SID Cluster section in the Common Radio Frequency
        Interface Encodings Annex."
     ::= { docsQosParamSetEntry 36 }

docsQosParamSetPeakTrafficRate OBJECT-TYPE
     SYNTAX      BitRate
     UNITS       "bps"
     MAX-ACCESS  read-only
     STATUS      current
     DESCRIPTION
        "This attribute represents the 4-byte value of the rate 
        parameter 'P' of a token-bucket-based peak rate limiter
        for packets of a service flow. A value of 0 signifies no
        Peak Traffic Rate is enforced.

        If the referenced parameter is not present in the
        corresponding DOCSIS QOS Parameter Set,
        this attribute returns 0.

        This attribute will also return 0 if DataRateUnitSetting
        is set to a non-default value (e.g. kbps, mbps, or gbps)
        and the resulting value cannot be represented in 32 bits.
        In which case, HCPeakTrafficRate should be utilized."
     REFERENCE
        "DOCSIS 3.0 MAC and Upper Layer Protocols Interface
        Specification CM-SP-MULPIv3.0-I08-080522,
        Peak Traffic Rate section in the Common Radio Frequency
        Interface Encodings Annex."
     ::= { docsQosParamSetEntry 37 }

docsQosParamSetDsResequencing OBJECT-TYPE
     SYNTAX      INTEGER {
                          resequencingDsidIfBonded(0),
                          noResequencingDsid(1),
                          notApplicable(2)
                         }
     MAX-ACCESS  read-only
     STATUS      current
     DESCRIPTION
        "This attribute specifies if a resequencing DSID need to be
        allocated to the service flow.
        The value 'resequencingDsidIfBonded' indicates that a resequencing DSID
        is required if the service flow is assigned to a downstream
        bonding group.
        The value 'noResequencingDsid' indicates no resequencing DSID
        is associated with the service flow.
        The value 'notApplicable' indicates the value of this attribute
        is not applicable.

        This attribute only applies to downstream Service Flows in 3.0
        operation. If the referenced parameter is not present in the
        corresponding downstream DOCSIS QOS Parameter Set, this
        attribute returns 'resequencingDsidIfBonded'. This parameter is not applicable to
        upstream DOCSIS QOS Parameter Sets, so the value 'notApplicable' is reported
        in that case."
     REFERENCE
        "DOCSIS 3.0 MAC and Upper Layer Protocols Interface
        Specification CM-SP-MULPIv3.0-I08-080522,
        Peak Traffic Rate section in the Common Radio Frequency
        Interface Encodings Annex."
     ::= { docsQosParamSetEntry 38 }

docsQosParamSetMinimumBuffer OBJECT-TYPE
     SYNTAX      Unsigned32 (0..4294967295)
     UNITS       "bytes"
     MAX-ACCESS  read-only
     STATUS      current
     DESCRIPTION
        "This attribute represents the configured minimum buffer size
        for the service flow."
     REFERENCE
        "DOCSIS 3.0 MAC and Upper Layer Protocols Interface
        Specification CM-SP-MULPIv3.0-I15-110210, Buffer Control
        section in the Common Radio Frequency Interface Encodings
        Annex."
     ::= { docsQosParamSetEntry 39 }

docsQosParamSetTargetBuffer OBJECT-TYPE
     SYNTAX      Unsigned32 (0..4294967295)
     UNITS       "bytes"
     MAX-ACCESS  read-only
     STATUS      current
     DESCRIPTION
        "This attribute represents the configured target buffer size
        for the service flow. The value 0 indicates that no target buffer
        size was configured, and the device will use a vendor specific
        value."
     REFERENCE
        "DOCSIS 3.0 MAC and Upper Layer Protocols Interface
        Specification CM-SP-MULPIv3.0-I15-110210, Buffer Control
        section in the Common Radio Frequency Interface Encodings
        Annex."
     ::= { docsQosParamSetEntry 40 }

docsQosParamSetMaximumBuffer OBJECT-TYPE
     SYNTAX      Unsigned32 (0..4294967295)
     UNITS       "bytes"
     MAX-ACCESS  read-only
     STATUS      current
     DESCRIPTION
        "This attribute represents the configured maximum buffer size
        for the service flow. The value 4294967295 indicates that no maximum buffer
        size was configured, and thus there is no limit to the buffer size."
     REFERENCE
        "DOCSIS 3.0 MAC and Upper Layer Protocols Interface
        Specification CM-SP-MULPIv3.0-I15-110210, Buffer Control
        section in the Common Radio Frequency Interface Encodings
        Annex."
     ::= { docsQosParamSetEntry 41 }

docsQosParamSetAqmDisabled OBJECT-TYPE
     SYNTAX      TruthValue
     MAX-ACCESS  read-only
     STATUS      current
     DESCRIPTION
        "If this attribute returns 'true', AQM is disabled on the
         upstream or downstream service flow specified by
         docsQosParamSetServiceFlowId."
     REFERENCE
        "DOCSIS 3.1 MAC and Upper Layer Protocols Interface
        Specification CM-SP-MULPIv3.1-I04-141218, AQM Encodings section
        in the Common Radio Frequency Interface Encodings Annex."
     ::= { docsQosParamSetEntry 42 }

docsQosParamSetAqmLatencyTarget OBJECT-TYPE
     SYNTAX      Unsigned32(0..256)
     UNITS       "milliseconds"
     MAX-ACCESS  read-only
     STATUS      current
     DESCRIPTION
        "This attribute provides the target latency for this service flow 
         when operating under Classic Active Queue Management 
         (e.g. DOCSIS-PIE). If set to 0, the value in the 
		 AqmGlobalLatencyTarget attribute of the DocsQosCfg 
		 object will be used. This attribute applies to both upstream 
		 and downstream service flows. This attribute is only used when 
		 AqmGlobalEnable in the DocsQosCfg object is set to 'true' and the
		 AqmEnable attribute is set to 'true'. This parameter will be ignored
		 if the AQM Algorithm used by the Service Flow is ImmediateAqm."
     REFERENCE
        "DOCSIS 3.1 MAC and Upper Layer Protocols Interface
        Specification CM-SP-MULPIv3.1-I04-141218, AQM Encodings section
        in the Common Radio Frequency Interface Encodings Annex."
     ::= { docsQosParamSetEntry 43 }

docsQosParamSetHCMaxTrafficRate OBJECT-TYPE
     SYNTAX      CounterBasedGauge64
     UNITS       "bps"
     MAX-ACCESS  read-only
     STATUS      current
     DESCRIPTION
        "This attribute is a 64-bit representation of the maximum
        sustained traffic rate in bits/sec allowed for this Service Flow.
        It counts all MAC frame data PDUs from the bytes following
        the MAC header HCS to the end of the CRC. The number
        of bytes forwarded is limited during any time interval.
        The value 0 means no maximum traffic rate is enforced.
        This attribute applies to both upstream and
        downstream Service Flows.
        This attribute returns 0 if the referenced parameter
        is not present in the corresponding DOCSIS QOS Parameter
        Set, or if the parameter is not applicable."
     REFERENCE
        "DOCSIS 3.0 MAC and Upper Layer Protocols Interface
        Specification CM-SP-MULPIv3.0-I08-080522, Maximum Sustained
        Traffic Rate section in the Common Radio Frequency Interface
        Encodings Annex."
     ::= { docsQosParamSetEntry 44 }

docsQosParamSetHCMinReservedRate OBJECT-TYPE
     SYNTAX      CounterBasedGauge64
     UNITS       "bps"
     MAX-ACCESS  read-only
     STATUS      current
     DESCRIPTION
        "This attribute is a 64-bit representation of the guaranteed
        minimum rate in bits/sec allowed for this Service flow. 
        The value is calculated from the byte following the MAC 
        header HCS to the end of the CRC. The value of 0 indicates that no
        bandwidth is reserved.
        If the referenced parameter is not present in the corresponding
        DOCSIS QOS Parameter Set, this attribute
        returns 0. If the parameter is not applicable, it is
        reported as 0."
     REFERENCE
        "DOCSIS 3.0 MAC and Upper Layer Protocols Interface
        Specification CM-SP-MULPIv3.0-I08-080522, Minimum Reserved
        Traffic Rate section of the Common Radio Frequency Interface
        Encodings Annex."
     ::= { docsQosParamSetEntry 45 }

docsQosParamSetHCPeakTrafficRate OBJECT-TYPE
     SYNTAX      CounterBasedGauge64
     UNITS       "bps"
     MAX-ACCESS  read-only
     STATUS      current
     DESCRIPTION
        "This attribute specifies the rate parameter 'P' of a
        token-bucket-based peak rate limiter for packets of a
        service flow. A value of 0 signifies no
        Peak Traffic Rate is enforced.

        If the referenced parameter is not present in the
        corresponding DOCSIS QOS Parameter Set,
        this attribute returns 0."
     REFERENCE
        "DOCSIS 3.0 MAC and Upper Layer Protocols Interface
        Specification CM-SP-MULPIv3.0-I08-080522,
        Peak Traffic Rate section in the Common Radio Frequency
        Interface Encodings Annex."
     ::= { docsQosParamSetEntry 46 }

docsQosParamSetAqmAlgInUse OBJECT-TYPE
     SYNTAX      INTEGER {
                     unknown(1),
                     other(2),
                     docsisPIE(3),
                     immediateAqm(4)
                     }
     MAX-ACCESS  read-only
     STATUS      current
     DESCRIPTION
        "This attribute specifies the AQM algorithm in use for this
         service flow. 
         The value unknown(1) is reported for downstream service flows
         or when AQM is disabled.
         The value other(2) indicates a vendor proprietary algorithm
         for upstream queue management.
         The value docsisPIE(3) indicates the upstream queue management
         Proportional Integral controller Enhanced (PIE) algorithm.
         The value immediateAqm(4) indicates the Immediate AQM algorithm."
     REFERENCE
        "DOCSIS 3.1 MAC and Upper Layer Protocols Interface
        Specification CM-SP-MULPIv3.1-I08-151210,
        Proportional-Integral-Enhanced Active Queue Management
        Algorithm Annex."
     ::= { docsQosParamSetEntry 47 }

docsQosParamSetGuaranteedGrantInterval OBJECT-TYPE
     SYNTAX      Unsigned32
     UNITS       "microseconds"
     MAX-ACCESS  read-only
     STATUS      current
     DESCRIPTION
        "This attribute specifies the maximum interval between
        successive data transmission opportunities, for a PGS Service
        Flow. The valid range of this parameter is specific to the CMTS. 
		If the referenced parameter is not applicable to the direction 
		or scheduling type of the corresponding DOCSIS QoS Parameter Set, 
		both CMTS and CM report this attribute's value as 0."
     REFERENCE
        "DOCSIS 3.1 MAC and Upper Layer Protocols Interface
        Specification CM-SP-MULPIv3.1-I17,
        Guaranteed Grant Interval section in the Common 
        TLV Encodings Annex"
     ::= { docsQosParamSetEntry 48 }

docsQosParamSetGuaranteedGrantRate OBJECT-TYPE
     SYNTAX      Unsigned32
     UNITS       "bps"
     MAX-ACCESS  read-only
     STATUS      current
     DESCRIPTION
        "This attribute specifies the minimum granting rate, for an
         upstream PGS service flow. The valid range of this parameter
		 is specific to the CMTS."
     REFERENCE
        "DOCSIS 3.1 MAC and Upper Layer Protocols Interface
        Specification CM-SP-MULPIv3.1-I17,
        Guaranteed Grant Rate section in the Common 
        TLV Encodings Annex."
     ::= { docsQosParamSetEntry 49 }

docsQosParamSetGuaranteedRequestInterval OBJECT-TYPE
     SYNTAX      Unsigned32
     UNITS       "microseconds"
     MAX-ACCESS  read-only
     STATUS      current
     DESCRIPTION
        "The value of this parameter specifies the maximum interval (in
        units of microseconds) between successive request opportunities
        (including unicast request opportunities and piggyback request
        opportunities) for an upstream PGS service flow. This attribute is a 
        16-bit representation of the request interval in units of microseconds. 
        The value zero represents polling disabled. "
     REFERENCE
        "DOCSIS 3.1 MAC and Upper Layer Protocols Interface
        Specification CM-SP-MULPIv3.1-I17,
        Guaranteed Request Interval section in the
        Common TLV Encodings Annex."
     ::= { docsQosParamSetEntry 50 }

docsQosParamSetImmedAqmMaxThreshold OBJECT-TYPE
     SYNTAX      Unsigned32 (0..65535)
     UNITS       "microseconds"
     MAX-ACCESS  read-only
     STATUS      current
     DESCRIPTION
        "This attribute provides provides the maximum threshold in
        microseconds of the ramp function used by the Immediate AQM
        algorithm and the Queue Protection algorithm. This attribute reports
        the actual ImmedAqmMaxThreshold rather than the configured value."
     REFERENCE
        "DOCSIS 3.1 MAC and Upper Layer Protocols Interface
        Specification CM-SP-MULPIv3.1-I17, MAXTH calculated per Annex C,
        Annex N"
     ::= { docsQosParamSetEntry 51 }

docsQosParamSetImmedAqmRangeExponentRampFunc OBJECT-TYPE
     SYNTAX      Unsigned32 (0..255)
     UNITS       "log2(nanoseconds)"
     MAX-ACCESS  read-only
     STATUS      current
     DESCRIPTION
        "This attribute specifies the range in nanoseconds of the ramp
        function used by the Immediate AQM algorithm and the Queue Protection
        algorithm.  It is expressed as an exponent of 2, e.g. a value of 19 means
        the range of the ramp will be 2^19 = 524288 ns (roughly 524 microseconds).
        This parameter is only defined if the AQM algorithm used by the Service
        Flow is ImmediateAqm, otherwise it returns a 0."
     REFERENCE
        "DOCSIS 3.1 MAC and Upper Layer Protocols Interface
        Specification CM-SP-MULPIv3.1-I17, Active Queue Management Algorithm
        Annexes."
     ::= { docsQosParamSetEntry 52 }

docsQosServiceFlowTable OBJECT-TYPE
     SYNTAX      SEQUENCE OF DocsQosServiceFlowEntry
     MAX-ACCESS  not-accessible
     STATUS      current
     DESCRIPTION
        "This object describes the set of DOCSIS-QOS Service
        Flows in a managed device."
     REFERENCE
        "DOCSIS 3.0 MAC and Upper Layer Protocols Interface
        Specification CM-SP-MULPIv3.0-I08-080522,  Service
        lows and Classifiers section."
     ::= { docsQosMibObjects 3}

docsQosServiceFlowEntry OBJECT-TYPE
     SYNTAX      DocsQosServiceFlowEntry
     MAX-ACCESS  not-accessible
     STATUS      current
     DESCRIPTION
        "The conceptual row of docsQosServiceFlowTable.
        The ifIndex key corresponds to the MAC Domain interface
        of this service flow."
     INDEX { ifIndex,
             docsQosServiceFlowId
           }
     ::= { docsQosServiceFlowTable 1 }

DocsQosServiceFlowEntry ::= SEQUENCE {
     docsQosServiceFlowId
                  Unsigned32,
     docsQosServiceFlowSID
                  Unsigned32,
     docsQosServiceFlowDirection
                  IfDirection,
     docsQosServiceFlowPrimary
                  TruthValue,
     docsQosServiceFlowParamSetTypeStatus
                  BITS,
     docsQosServiceFlowChSetId
                  ChSetId,
     docsQosServiceFlowAttrAssignSuccess
                  TruthValue,
     docsQosServiceFlowDsid
                  Dsid,
     docsQosServiceFlowMaxReqPerSidCluster
                  Unsigned32,
     docsQosServiceFlowMaxOutstandingBytesPerSidCluster
                  Unsigned32,
     docsQosServiceFlowMaxTotBytesReqPerSidCluster
                  Unsigned32,
     docsQosServiceFlowMaxTimeInSidCluster
                  Unsigned32,
     docsQosServiceFlowBufferSize
                  Unsigned32,
     docsQosServiceFlowIatcProfileName
                  SnmpAdminString,
     docsQosServiceFlowAggregateServiceFlowId
                  Unsigned32
     }

docsQosServiceFlowId OBJECT-TYPE
     SYNTAX      Unsigned32 
     MAX-ACCESS  not-accessible
     STATUS      current
     DESCRIPTION
        "This key represents an identifier assigned to a Service
        Flow by CMTS within a MAC Domain.
        The value 0 is used only for the purpose of reporting instances
        of the PktClass object pertaining UDCs and
        not used for association of QOS classifiers to service
        flows."
     REFERENCE
        "DOCSIS 3.0 MAC and Upper Layer Protocols Interface
        Specification CM-SP-MULPIv3.0-I08-080522, Service Flow
        Identifier section in the Common Radio Frequency Interface
        Encodings Annex."
     ::= { docsQosServiceFlowEntry 1 }

docsQosServiceFlowSID OBJECT-TYPE
     SYNTAX      Unsigned32 (0..16383)
     MAX-ACCESS  read-only
     STATUS      current
     DESCRIPTION
        "Service Identifier (SID) assigned to an admitted
        or active Service Flow.  This attribute
        reports a value of 0 if a Service ID is not associated with
        the Service Flow.  Only active
        or admitted upstream Service Flows will have a Service
        ID (SID)."
     REFERENCE
        "DOCSIS 3.0 MAC and Upper Layer Protocols Interface
        Specification CM-SP-MULPIv3.0-I08-080522, Service
        Identifier section in the Common Radio Frequency Interface
        Encodings Annex."
     ::= { docsQosServiceFlowEntry 6 }

docsQosServiceFlowDirection OBJECT-TYPE
     SYNTAX      IfDirection
     MAX-ACCESS  read-only
     STATUS      current
     DESCRIPTION
        "This attribute represents the direction of the Service
        Flow."
     ::= { docsQosServiceFlowEntry 7 }

docsQosServiceFlowPrimary OBJECT-TYPE
     SYNTAX      TruthValue
     MAX-ACCESS  read-only
     STATUS      current
     DESCRIPTION
        "This attribute reflects whether Service Flow is the
        primary
        or a secondary Service Flow."
     ::= { docsQosServiceFlowEntry 8 }

docsQosServiceFlowParamSetTypeStatus OBJECT-TYPE
     SYNTAX      BITS {

                        active(0),
                        admitted(1),
                        provisioned(2)
                      }
     MAX-ACCESS  read-only
     STATUS      current
     DESCRIPTION
        "This attribute represents the status of the service
        flow based on the admission state.
        'active' bit set to '1' indicates that the service flow
        is active and that the corresponding QOS ParamSet
        is stored in the CMTS.
        'admitted' bit set to '1' indicates that the service
        flow resources were reserved  and that the corresponding
        QOS ParamSet is stored in the CMTS.
        'provisioned' bit set to '1' indicates that the service
        flow was defined in the CM config file and that the
        corresponding QOS ParamSet is stored in the CMTS."
     REFERENCE
        "DOCSIS 3.0 MAC and Upper Layer Protocols Interface
        Specification CM-SP-MULPIv3.0-I08-080522, Service
        Flow Section."
     ::= { docsQosServiceFlowEntry 9 }

docsQosServiceFlowChSetId OBJECT-TYPE
     SYNTAX      ChSetId
     MAX-ACCESS  read-only
     STATUS      current
     DESCRIPTION
        "This attribute represents the Channel Set Id associated
        with the service flow."
     ::= { docsQosServiceFlowEntry 10 }

docsQosServiceFlowAttrAssignSuccess OBJECT-TYPE
     SYNTAX      TruthValue
     MAX-ACCESS  read-only
     STATUS      current
     DESCRIPTION
        "If set to 'true', this attribute indicates that the
        current channel set associated with the service flow
        meets the Required and Forbidden Attribute Mask encodings.
        Since this attribute is not applicable for a CM, the
        CM always returns 'false'."
     REFERENCE
        "DOCSIS 3.0 MAC and Upper Layer Protocols Interface
        Specification CM-SP-MULPIv3.0-I08-080522, Service Flow
        section."
     ::= { docsQosServiceFlowEntry 11 }

docsQosServiceFlowDsid OBJECT-TYPE
     SYNTAX      Dsid
     MAX-ACCESS  read-only
     STATUS      current
     DESCRIPTION
        "This attribute indicates the DSID associated with
        the downstream service flow. downstream service flows
        without a DSID or upstream Service Flows report
        the value zero."
     ::= { docsQosServiceFlowEntry 12 }

docsQosServiceFlowMaxReqPerSidCluster OBJECT-TYPE
     SYNTAX      Unsigned32 (0..255)
     UNITS       "bytes"
     MAX-ACCESS  read-only
     STATUS      current
     DESCRIPTION
        "This attribute specifies the maximum number of requests
        that a CM can make within a given SID Cluster before it
        must switch to a different SID Cluster to make further
        requests. A value of 0 indicates there is no limit.
        This attribute only applies to upstream Service Flows in 3.0
        operation, in other cases it is reported as 0."
     REFERENCE
        "DOCSIS 3.0 MAC and Upper Layer Protocols Interface
        Specification CM-SP-MULPIv3.0-I08-080522, Maximum Requests
        per SID Cluster section in the Common Radio Frequency
        Interface Encodings Annex."
     ::= { docsQosServiceFlowEntry 13 }

docsQosServiceFlowMaxOutstandingBytesPerSidCluster OBJECT-TYPE
     SYNTAX      Unsigned32
     UNITS       "bytes"
     MAX-ACCESS  read-only
     STATUS      current
     DESCRIPTION
        "This attribute specifies the maximum number of bytes
        for which a CM can have requests outstanding on a given
        SID Cluster. If defined number of bytes are outstanding
        and further requests are required, the CM must switch to
        a different SID Cluster if one is available. A value of 0
        indicates there is no limit.
        This attribute only applies to upstream Service Flows
        in 3.0 operation, in other cases it is reported as 0."
     REFERENCE
        "DOCSIS 3.0 MAC and Upper Layer Protocols Interface
        Specification CM-SP-MULPIv3.0-I08-080522, Maximum
        Outstanding Bytes per SID Cluster section in the Common
        Radio Frequency Interface Encodings Annex."
     ::= { docsQosServiceFlowEntry 14 }

docsQosServiceFlowMaxTotBytesReqPerSidCluster OBJECT-TYPE
     SYNTAX      Unsigned32
     UNITS       "bytes"
     MAX-ACCESS  read-only
     STATUS      current
     DESCRIPTION
        "This attribute specifies the maximum total number of
        bytes a CM can have requested using a given SID Cluster
        before it must switch to a different SID Cluster to make
        further requests. A value of 0 indicates there is no
        limit.
        This attribute only applies to upstream Service Flows
        in 3.0 operation, in other cases it is reported as 0."
     REFERENCE
        "DOCSIS 3.0 MAC and Upper Layer Protocols Interface
        Specification CM-SP-MULPIv3.0-I08-080522, Maximum Total
        Bytes Requested per SID Cluster section in the
        Common Radio Frequency Interface Encodings Annex."
     ::= { docsQosServiceFlowEntry 15 }

docsQosServiceFlowMaxTimeInSidCluster OBJECT-TYPE
     SYNTAX      Unsigned32 (0..65535)
     UNITS       "milliseconds"
     MAX-ACCESS  read-only
     STATUS      current
     DESCRIPTION
        "This attribute specifies the maximum time in
        milliseconds that a CM may use a particular SID Cluster
        before it must switch to a different SID Cluster to
        make further requests.
        A value of 0 indicates there is no limit.
        This attribute only applies to upstream Service Flows
        in 3.0 operation, in other cases it is reported as 0."
     REFERENCE
        "DOCSIS 3.0 MAC and Upper Layer Protocols Interface
        Specification CM-SP-MULPIv3.0-I08-080522, Maximum Time in
        the SID Cluster section in the Common Radio Frequency
        Interface Encodings Annex."
     ::= { docsQosServiceFlowEntry 16 }

docsQosServiceFlowBufferSize OBJECT-TYPE
     SYNTAX      Unsigned32 (0..4294967295)
     UNITS       "bytes"
     MAX-ACCESS  read-only
     STATUS      current
     DESCRIPTION
        "This attribute specifies the buffer size for the service
        flow.  For the CM this attribute only applies to upstream
        Service Flows, for the CMTS this attribute only applies to
        downstream Service Flows, in other cases it is reported as
        0."
     REFERENCE
        "DOCSIS 3.0 MAC and Upper Layer Protocols Interface
        Specification CM-SP-MULPIv3.0-I15-110210, Buffer Control
        section in the Common Radio Frequency Interface Encodings
        Annex."
     ::= { docsQosServiceFlowEntry 17 }

docsQosServiceFlowIatcProfileName OBJECT-TYPE
     SYNTAX      SnmpAdminString
     MAX-ACCESS  read-only
     STATUS      current
     DESCRIPTION
        "This attribute indicates the name of the IATC Profile for
         which this Service Flow belongs.  If this Service Flow is
         not part of an IATC Profile, this attribute returns an
         empty string.

         For the CM this attribute does not apply. This attribute
         is only applicable for the CCAP."
     ::= { docsQosServiceFlowEntry 18 }

docsQosServiceFlowAggregateServiceFlowId OBJECT-TYPE
     SYNTAX      Unsigned32
     MAX-ACCESS  read-only
     STATUS      current
     DESCRIPTION
          "This attribute indicates the Aggregate Service Flow to which
           this Service Flow belongs. If this Service Flow is not part
           of an ASF this attribute returns a 0."
     ::= { docsQosServiceFlowEntry 19 }

docsQosServiceFlowStatsTable OBJECT-TYPE
     SYNTAX      SEQUENCE OF DocsQosServiceFlowStatsEntry
     MAX-ACCESS  not-accessible
     STATUS      current
     DESCRIPTION
        "This object describes statistics associated with
        the  Service Flows in a managed device."
     ::= { docsQosMibObjects 4}

docsQosServiceFlowStatsEntry OBJECT-TYPE
     SYNTAX      DocsQosServiceFlowStatsEntry
     MAX-ACCESS  not-accessible
     STATUS      current
     DESCRIPTION
        "The conceptual row of docsQosServiceFlowStatsTable.
        The ifIndex key corresponds to the MAC Domain interface
        of the service flow."
     INDEX { ifIndex,
             docsQosServiceFlowId
           }
     ::= { docsQosServiceFlowStatsTable 1 }

DocsQosServiceFlowStatsEntry ::= SEQUENCE {
     docsQosServiceFlowPkts
                  Counter64,
     docsQosServiceFlowOctets
                  Counter64,
     docsQosServiceFlowTimeCreated
                  TimeStamp,
     docsQosServiceFlowTimeActive
                  Counter32,
     docsQosServiceFlowPHSUnknowns
                  Counter32,
     docsQosServiceFlowPolicedDropPkts
                  Counter32,
     docsQosServiceFlowPolicedDelayPkts
                  Counter32,
     docsQosServiceFlowAqmDroppedPkts
                  Counter64,
     docsQosServiceFlowSanctionedPkts
                  Counter64
     }

docsQosServiceFlowPkts OBJECT-TYPE
     SYNTAX      Counter64
     UNITS       "packets"
     MAX-ACCESS  read-only
     STATUS      current
     DESCRIPTION
        "For outgoing Service Flows, this attribute counts
        the number of Packet Data PDUs forwarded to this Service
        Flow.  For incoming upstream CMTS service flows,
        this attribute counts the number of Packet Data PDUs
        actually received on the Service Flow identified by
        the SID for which the packet was scheduled.  CMs not classifying
        downstream packets may report this attribute's
        value as 0 for downstream Service Flows.  This
        attribute does not count MAC-specific management
        messages.

        Particularly for UGS flows, packets sent on the primary
        Service Flow in violation of the UGS grant size should
        be counted only by the instance of this attribute
        that is associated with the primary service flow.

        Unclassified upstream user data packets (i.e., non-
        MAC-management) forwarded to the primary upstream
        Service Flow should be counted by the instance of this
        attribute that is associated with the primary service
        flow.

        This attribute does include packets counted by
        ServiceFlowPolicedDelayPkts, but does not include packets
        counted by ServiceFlowPolicedDropPkts and
        ServiceFlowPHSUnknowns.


        This counter's last discontinuity is the
        ifCounterDiscontinuityTime for of the associated MAC Domain
        interface index."
     ::= { docsQosServiceFlowStatsEntry 1 }

docsQosServiceFlowOctets OBJECT-TYPE
     SYNTAX      Counter64
     UNITS       "bytes"
     MAX-ACCESS  read-only
     STATUS      current
     DESCRIPTION
        "This attribute indicates the count of the number of
        octets from the byte after the MAC header HCS to the end
        of the CRC for all packets counted in the ServiceFlowPkts
        attribute for this row.  Note that this counts
        the octets after payload header suppression and before
        payload header expansion have been applied.

        This counter's last discontinuity is the
        ifCounterDiscontinuityTime for of the associated MAC Domain
        interface index."
     ::= { docsQosServiceFlowStatsEntry 2 }

docsQosServiceFlowTimeCreated OBJECT-TYPE
     SYNTAX      TimeStamp
     MAX-ACCESS  read-only
     STATUS      current
     DESCRIPTION
        "This attribute indicates the value of sysUpTime when
        the service flow was created."
     ::= { docsQosServiceFlowStatsEntry 3 }

docsQosServiceFlowTimeActive OBJECT-TYPE
     SYNTAX      Counter32
     UNITS       "seconds"
     MAX-ACCESS  read-only
     STATUS      current
     DESCRIPTION
        "This attribute indicates the number of seconds that
        the service flow has been active.

        This counter's last discontinuity is the
        ifCounterDiscontinuityTime for of the associated MAC Domain
        interface index."
     ::= { docsQosServiceFlowStatsEntry 4 }

docsQosServiceFlowPHSUnknowns OBJECT-TYPE
     SYNTAX      Counter32
     UNITS       "packets"
     MAX-ACCESS  read-only
     STATUS      current
     DESCRIPTION
        "For incoming upstream CMTS service flows, this attribute
        counts the number of packets received with an
        unknown payload header suppression index.
        The service flow is identified by the SID for which the
        packet was scheduled.
        On a CM, only this attribute's instance for the primary
        downstream service flow counts packets received
        with an unknown payload header suppression index.  All
        other downstream service flows on CM report this attributes
        value as 0.
        All outgoing service flows report this attribute's
        value as 0.

        This counter's last discontinuity is the
        ifCounterDiscontinuityTime for of the associated MAC Domain
        interface index."
     ::= { docsQosServiceFlowStatsEntry 5 }

docsQosServiceFlowPolicedDropPkts OBJECT-TYPE
     SYNTAX      Counter32
     UNITS       "packets"
     MAX-ACCESS  read-only
     STATUS      current
     DESCRIPTION
        "For outgoing service flows, this attribute counts
        the number of Packet Data PDUs classified to this service
        flow dropped due to:
        (1) exceeding the selected Buffer Size for the service flow; or

        (2) UGS packets dropped due to exceeding the Unsolicited
        Grant Size with a Request/Transmission policy
        that requires such packets to be dropped.

        Classified packets dropped due to other reasons must
        be counted in either AqmDroppedPkts or ifOutDiscards for the
        interface of this service flow (depending on the reason for the
        discard).  This attribute reports 0 for incoming service flows.

        This counter's last discontinuity is the
        ifCounterDiscontinuityTime for of the associated MAC Domain
        interface index."
     REFERENCE
        "DOCSIS 3.0 MAC and Upper Layer Protocols Interface
        Specification CM-SP-MULPIv3.0-I15-110210, Buffer Control section
        and Request/Transmission Policy section."
     ::= { docsQosServiceFlowStatsEntry 6 }

docsQosServiceFlowPolicedDelayPkts OBJECT-TYPE
     SYNTAX      Counter32
     UNITS       "packets"
     MAX-ACCESS  read-only
     STATUS      current
     DESCRIPTION
        "This attribute counts only outgoing packets delayed
        in order to maintain the Maximum Sustained Traffic
        Rate.  This attribute will always report a value of
        0 for UGS flows because the Maximum Sustained Traffic
        Rate does not apply.  This attribute is 0 for incoming
        service flows.

        This counter's last discontinuity is the
        ifCounterDiscontinuityTime for of the associated MAC Domain
        interface index."
     ::= { docsQosServiceFlowStatsEntry 7 }

docsQosServiceFlowAqmDroppedPkts OBJECT-TYPE
     SYNTAX      Counter64
     UNITS       "packets"
     MAX-ACCESS  read-only
     STATUS      current
     DESCRIPTION
        "For upstream service flows on which AQM is enabled, this
         attribute counts the number of Packet Data PDUs classified to
         this service flow dropped due to Active Queue Management drop
         decisions. Classified packets dropped due to other reasons are
         counted in either PolicedDropPkts or ifOutDiscards for the
         interface of this service flow (depending on the reason for the
         discard).  This attribute reports zero for downstream service
         flows. This counter's last discontinuity is the
         ifCounterDiscontinuityTime of the associated MAC Domain
         interface index."
     REFERENCE
        "DOCSIS 3.1 MAC and Upper Layer Protocols Interface
        Specification CM-SP-MULPIv3.1-I02-14MMDD, Active Queue
        Management Algorithm Section."
     ::= { docsQosServiceFlowStatsEntry 8 }

docsQosServiceFlowSanctionedPkts OBJECT-TYPE
     SYNTAX      Counter64
     UNITS       "packets"
     MAX-ACCESS  read-only
     STATUS      current
     DESCRIPTION
        "This attribute represents the number of packets redirected to the 
          Classic Service Flow queue by the Queue Protection function."
     REFERENCE
        "DOCSIS 3.1 MAC and Upper Layer Protocols Interface
        Specification CM-SP-MULPIv3.1-I17."
     ::= { docsQosServiceFlowStatsEntry 9 }

docsQosUpstreamStatsTable OBJECT-TYPE
     SYNTAX      SEQUENCE OF DocsQosUpstreamStatsEntry
     MAX-ACCESS  not-accessible
     STATUS      current
     DESCRIPTION
        "This object describes statistics associated with
        upstream service flows.  All counted frames must be
        received without a Frame Check Sequence (FCS) error."
     ::= { docsQosMibObjects 5}

docsQosUpstreamStatsEntry OBJECT-TYPE
     SYNTAX      DocsQosUpstreamStatsEntry
     MAX-ACCESS  not-accessible
     STATUS      current
     DESCRIPTION
        "The conceptual row of docsQosUpstreamStatsTable.
        The ifIndex key corresponds to the upstream logical channel
        interface of the service flow. A DOCSIS 3.0 CMTS populates
        entries in the docsQosUpstreamStatsTable with information
        for Pre-3.0 DOCSIS devices.  Devices operating in Multiple
        Transmit Channel mode will not be recorded in the
        docsQosUpstreamStatsTable and will instead be recorded in
        the docsQosServiceFlowCcfStatsTable."
     INDEX { ifIndex,
             docsQosSID
           }
     ::= { docsQosUpstreamStatsTable 1 }

DocsQosUpstreamStatsEntry ::= SEQUENCE {
     docsQosSID
                  Unsigned32,
     docsQosUpstreamFragments
                  Counter32,
     docsQosUpstreamFragDiscards
                  Counter32,
     docsQosUpstreamConcatBursts
                  Counter32
     }

docsQosSID OBJECT-TYPE
     SYNTAX      Unsigned32 (1..16383)
     MAX-ACCESS  not-accessible
     STATUS      current
     DESCRIPTION
        "This key identifies a service ID for an admitted
        or active upstream service flow."
     ::= { docsQosUpstreamStatsEntry 1 }

docsQosUpstreamFragments OBJECT-TYPE
     SYNTAX      Counter32
     UNITS       "fragments"
     MAX-ACCESS  read-only
     STATUS      current
     DESCRIPTION
        "This attribute indicates the number of fragmentation
        headers received on an upstream service flow, regardless
        of whether the fragment was correctly reassembled
        into a valid packet.

        This counter's last discontinuity is the
        ifCounterDiscontinuityTime for of the associated MAC Domain
        interface index."
     ::= { docsQosUpstreamStatsEntry 2 }

docsQosUpstreamFragDiscards OBJECT-TYPE
     SYNTAX      Counter32
     UNITS       "fragments"
     MAX-ACCESS  read-only
     STATUS      current
     DESCRIPTION
        "This attribute indicates the number of upstream fragments
        discarded and not assembled into a valid upstream
        packet.
        This counter's last discontinuity is the
        ifCounterDiscontinuityTime for of the associated MAC Domain
        interface index."
     ::= { docsQosUpstreamStatsEntry 3 }

docsQosUpstreamConcatBursts OBJECT-TYPE
     SYNTAX      Counter32
     UNITS       "headers"
     MAX-ACCESS  read-only
     STATUS      current
     DESCRIPTION
        "This attribute indicates the number of concatenation
        headers received on an upstream service flow.
        This counter's last discontinuity is the
        ifCounterDiscontinuityTime for of the associated MAC Domain
        interface index."
     ::= { docsQosUpstreamStatsEntry 4 }

docsQosDynamicServiceStatsTable OBJECT-TYPE
     SYNTAX      SEQUENCE OF DocsQosDynamicServiceStatsEntry
     MAX-ACCESS  not-accessible
     STATUS      current
     DESCRIPTION
        "This object describes statistics associated with
        the Dynamic Service Flows, Dynamic Channel Changes
        and Dynamic Bonding Changes in a managed device within
        a MAC Domain.
        For each MAC Domain there are two instances for the for
        the upstream and downstream
        direction.
        On the CMTS, the downstream direction instance indicates
        messages transmitted or transactions originated
        by the CMTS.  The upstream direction instance indicates
        messages received or transaction originated
        by the CM.
        On the CM, the downstream direction instance indicates
        messages received or transactions originated by
        the CMTS.  The upstream direction instance indicates
        messages transmitted by the CM or transactions originated
        by the CM."
     ::= { docsQosMibObjects 6}

docsQosDynamicServiceStatsEntry OBJECT-TYPE
     SYNTAX      DocsQosDynamicServiceStatsEntry
     MAX-ACCESS  not-accessible
     STATUS      current
     DESCRIPTION
        "The conceptual row of docsQosDynamicServiceStatsTable.
        The ifIndex key corresponds to the MAC Domain interface
        of the service flow."
     INDEX { ifIndex,
             docsQosIfDirection
           }
     ::= { docsQosDynamicServiceStatsTable 1 }

DocsQosDynamicServiceStatsEntry ::= SEQUENCE {
     docsQosIfDirection
                  IfDirection,
     docsQosDSAReqs
                  Counter32,
     docsQosDSARsps
                  Counter32,
     docsQosDSAAcks
                  Counter32,
     docsQosDSCReqs
                  Counter32,
     docsQosDSCRsps
                  Counter32,
     docsQosDSCAcks
                  Counter32,
     docsQosDSDReqs
                  Counter32,
     docsQosDSDRsps
                  Counter32,
     docsQosDynamicAdds
                  Counter32,
     docsQosDynamicAddFails
                  Counter32,
     docsQosDynamicChanges
                  Counter32,
     docsQosDynamicChangeFails
                  Counter32,
     docsQosDynamicDeletes
                  Counter32,
     docsQosDynamicDeleteFails
                  Counter32,
     docsQosDCCReqs
                  Counter32,
     docsQosDCCRsps
                  Counter32,
     docsQosDCCAcks
                  Counter32,
     docsQosDCCs
                  Counter32,
     docsQosDCCFails
                  Counter32,
     docsQosDCCRspDeparts
                  Counter32,
     docsQosDCCRspArrives
                  Counter32,
     docsQosDbcReqs
                  Counter32,
     docsQosDbcRsps
                  Counter32,
     docsQosDbcAcks
                  Counter32,
     docsQosDbcSuccesses
                  Counter32,
     docsQosDbcFails
                  Counter32,
     docsQosDbcPartial
                  Counter32
     }

docsQosIfDirection OBJECT-TYPE
     SYNTAX      IfDirection
     MAX-ACCESS  not-accessible
     STATUS      current
     DESCRIPTION
        "This attribute indicates the interface direction
        for the instance the statistics are collected."
     ::= { docsQosDynamicServiceStatsEntry 1 }

docsQosDSAReqs OBJECT-TYPE
     SYNTAX      Counter32
     MAX-ACCESS  read-only
     STATUS      current
     DESCRIPTION
        "This attribute indicates the number of Dynamic Service
        Addition Requests, including retries.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Addition section; [RFC 2863]."
     ::= { docsQosDynamicServiceStatsEntry 2 }

docsQosDSARsps OBJECT-TYPE
     SYNTAX      Counter32
     MAX-ACCESS  read-only
     STATUS      current
     DESCRIPTION
        "The number of Dynamic Service Addition Responses,
        including retries.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Addition section; [RFC 2863]."
     ::= { docsQosDynamicServiceStatsEntry 3 }

docsQosDSAAcks OBJECT-TYPE
     SYNTAX      Counter32
     MAX-ACCESS  read-only
     STATUS      current
     DESCRIPTION
        "The number of Dynamic Service Addition Acknowledgements,
        including retries.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Addition section; [RFC 2863]."
     ::= { docsQosDynamicServiceStatsEntry 4 }

docsQosDSCReqs OBJECT-TYPE
     SYNTAX      Counter32
     MAX-ACCESS  read-only
     STATUS      current
     DESCRIPTION
        "The number of Dynamic Service Change Requests, including
        retries.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Change section; [RFC 2863]."
     ::= { docsQosDynamicServiceStatsEntry 5 }

docsQosDSCRsps OBJECT-TYPE
     SYNTAX      Counter32
     MAX-ACCESS  read-only
     STATUS      current
     DESCRIPTION
        "The number of Dynamic Service Change Responses, including
        retries.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Change section; [RFC 2863]."
     ::= { docsQosDynamicServiceStatsEntry 6 }

docsQosDSCAcks OBJECT-TYPE
     SYNTAX      Counter32
     MAX-ACCESS  read-only
     STATUS      current
     DESCRIPTION
        "The number of Dynamic Service Change Acknowledgements,
        including retries.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Change section; [RFC 2863]."
     ::= { docsQosDynamicServiceStatsEntry 7 }

docsQosDSDReqs OBJECT-TYPE
     SYNTAX      Counter32
     MAX-ACCESS  read-only
     STATUS      current
     DESCRIPTION
        "The number of Dynamic Service Delete Requests, including
        retries.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Delete section; [RFC 2863]."
     ::= { docsQosDynamicServiceStatsEntry 8 }

docsQosDSDRsps OBJECT-TYPE
     SYNTAX      Counter32
     MAX-ACCESS  read-only
     STATUS      current
     DESCRIPTION
        "The number of Dynamic Service Delete Responses, including
        retries.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Delete section; [RFC 2863]."
     ::= { docsQosDynamicServiceStatsEntry 9 }

docsQosDynamicAdds OBJECT-TYPE
     SYNTAX      Counter32
     MAX-ACCESS  read-only
     STATUS      current
     DESCRIPTION
        "The number of successful Dynamic Service Addition
        transactions.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Addition section; [RFC 2863]."
     ::= { docsQosDynamicServiceStatsEntry 10 }

docsQosDynamicAddFails OBJECT-TYPE
     SYNTAX      Counter32
     MAX-ACCESS  read-only
     STATUS      current
     DESCRIPTION
        "The number of failed Dynamic Service Addition transactions.

        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Addition section; [RFC 2863]."
     ::= { docsQosDynamicServiceStatsEntry 11 }

docsQosDynamicChanges OBJECT-TYPE
     SYNTAX      Counter32
     MAX-ACCESS  read-only
     STATUS      current
     DESCRIPTION
        "The number of successful Dynamic Service Change transactions.

        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Change section; [RFC 2863]."
     ::= { docsQosDynamicServiceStatsEntry 12 }

docsQosDynamicChangeFails OBJECT-TYPE
     SYNTAX      Counter32
     MAX-ACCESS  read-only
     STATUS      current
     DESCRIPTION
        "The number of failed Dynamic Service Change transactions.

        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Change section; [RFC 2863]."
     ::= { docsQosDynamicServiceStatsEntry 13 }

docsQosDynamicDeletes OBJECT-TYPE
     SYNTAX      Counter32
     MAX-ACCESS  read-only
     STATUS      current
     DESCRIPTION
        "The number of successful Dynamic Service Delete transactions.

        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Delete section; [RFC 2863]."
     ::= { docsQosDynamicServiceStatsEntry 14 }

docsQosDynamicDeleteFails OBJECT-TYPE
     SYNTAX      Counter32
     MAX-ACCESS  read-only
     STATUS      current
     DESCRIPTION
        "The number of failed Dynamic Service Delete transactions.

        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Service
        Delete section; [RFC 2863]."
     ::= { docsQosDynamicServiceStatsEntry 15 }

docsQosDCCReqs OBJECT-TYPE
     SYNTAX      Counter32
     MAX-ACCESS  read-only
     STATUS      current
     DESCRIPTION
        "The number of Dynamic Channel Change Request messages
        traversing an interface.  This count is nonzero
        only on downstream direction rows. This count should
        include the number of retries.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Downstream
        and/or Upstream Channel Changes section; [RFC 2863]."
     ::= { docsQosDynamicServiceStatsEntry 16 }

docsQosDCCRsps OBJECT-TYPE
     SYNTAX      Counter32
     MAX-ACCESS  read-only
     STATUS      current
     DESCRIPTION
        "The number of Dynamic Channel Change Response messages
        traversing an interface. This count is nonzero
        only on upstream direction rows.  This count should
        include the number of retries.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Downstream
        and/or Upstream Channel Changes section; [RFC 2863]."
     ::= { docsQosDynamicServiceStatsEntry 17 }

docsQosDCCAcks OBJECT-TYPE
     SYNTAX      Counter32
     MAX-ACCESS  read-only
     STATUS      current
     DESCRIPTION
        "The number of Dynamic Channel Change Acknowledgement
        messages traversing an interface.  This count is
        nonzero only on downstream direction rows. This count
        should include the number of retries.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Downstream
        and/or Upstream Channel Changes section; [RFC 2863]."
     ::= { docsQosDynamicServiceStatsEntry 18 }

docsQosDCCs OBJECT-TYPE
     SYNTAX      Counter32
     MAX-ACCESS  read-only
     STATUS      current
     DESCRIPTION
        "The number of successful Dynamic Channel Change transactions.
        This count is nonzero only on downstream
        direction rows.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Downstream
        and/or Upstream Channel Changes section; [RFC 2863]."
     ::= { docsQosDynamicServiceStatsEntry 19 }

docsQosDCCFails OBJECT-TYPE
     SYNTAX      Counter32
     MAX-ACCESS  read-only
     STATUS      current
     DESCRIPTION
        "The number of failed Dynamic Channel Change transactions.
        This count is nonzero only on downstream direction
        rows.
        Discontinuities in the value of this counter can occur
        at reinitialization of the managed system, and at
        other times as indicated by the value of
        ifCounterDiscontinuityTime of the associated MAC Domain
        interface index."
     REFERENCE
        "DOCSIS 3.0 MAC and Upper Layer Protocols Interface
        Specification CM-SP-MULPIv3.0-I08-080522, Dynamic Downstream
        and/or Upstream Channel Changes section; [RFC 2863]."
     ::= { docsQosDynamicServiceStatsEntry 20 }

docsQosDCCRspDeparts OBJECT-TYPE
     SYNTAX      Counter32
     MAX-ACCESS  read-only
     STATUS      current
     DESCRIPTION
        "This attribute contains the number of Dynamic Channel
        Change Response (depart) messages. It only applies
        to upstream direction. Discontinuities in the
        value of this counter can occur at reinitialization
        of the managed system, and at other times as indicated
        by the value of ifCounterDiscontinuityTime of the
        associated MAC Domain interface index."
     REFERENCE
        "DOCSIS 3.0 MAC and Upper Layer Protocols Interface
        Specification CM-SP-MULPIv3.0-I08-080522, Dynamic Downstream
        and/or Upstream Channel Changes section; [RFC 2863]."
     ::= { docsQosDynamicServiceStatsEntry 21 }

docsQosDCCRspArrives OBJECT-TYPE
     SYNTAX      Counter32
     MAX-ACCESS  read-only
     STATUS      current
     DESCRIPTION
        "This attribute contains the number of Dynamic Channel
        Change Response (arrive) messages and should include
        retries. It only applies to the upstream direction.
        Discontinuities in the value of this counter
        can occur at reinitialization of the managed system,
        and at other times as indicated by the value of
        ifCounterDiscontinuityTime of the associated MAC Domain
        interface index."
     REFERENCE
        "DOCSIS 3.0 MAC and Upper Layer Protocols Interface
        Specification CM-SP-MULPIv3.0-I08-080522, Dynamic Downstream
        and/or Upstream Channel Changes section; [RFC 2863]."
     ::= { docsQosDynamicServiceStatsEntry 22 }

docsQosDbcReqs OBJECT-TYPE
     SYNTAX      Counter32
     MAX-ACCESS  read-only
     STATUS      current
     DESCRIPTION
        "This attribute contains the number of Dynamic Bonding
        Change Requests, including retries. It only applies
        to the upstream direction. Discontinuities in
        the value of this counter can occur at reinitialization
        of the managed system, and at other times as indicated
        by the value of ifCounterDiscontinuityTime of
        the associated MAC Domain interface index."
     REFERENCE
        "DOCSIS 3.0 MAC and Upper Layer Protocols Interface
        Specification CM-SP-MULPIv3.0-I08-080522, Dynamic Bonding
        Change (DBC) section; [RFC 2863]."
     ::= { docsQosDynamicServiceStatsEntry 23 }

docsQosDbcRsps OBJECT-TYPE
     SYNTAX      Counter32
     MAX-ACCESS  read-only
     STATUS      current
     DESCRIPTION
        "This attribute contains the number of Dynamic Bonding
        Change Responses, including retries. It only applies
        to the upstream direction. Discontinuities
        in the value of this counter can occur at reinitialization
        of the managed system, and at other times as indicated
        by the value of ifCounterDiscontinuityTime
        of the associated MAC Domain interface index."
     REFERENCE
        "DOCSIS 3.0 MAC and Upper Layer Protocols Interface
        Specification CM-SP-MULPIv3.0-I08-080522, Dynamic Bonding
        Change (DBC) section; [RFC 2863]."
     ::= { docsQosDynamicServiceStatsEntry 24 }

docsQosDbcAcks OBJECT-TYPE
     SYNTAX      Counter32
     MAX-ACCESS  read-only
     STATUS      current
     DESCRIPTION
        "This attribute contains the number of Dynamic Bonding
        Change Acknowledgements, including retries.
        It only applies to the downstream direction. Discontinuities
        in the value of this counter can occur at reinitialization
        of the managed system, and at other times
        as indicated by the value of ifCounterDiscontinuityTime
        of the associated MAC Domain interface index."
     REFERENCE
        "DOCSIS 3.0 MAC and Upper Layer Protocols Interface
        Specification CM-SP-MULPIv3.0-I08-080522, Dynamic Bonding
        Change (DBC) section; [RFC 2863]."
     ::= { docsQosDynamicServiceStatsEntry 25 }

docsQosDbcSuccesses OBJECT-TYPE
     SYNTAX      Counter32
     MAX-ACCESS  read-only
     STATUS      current
     DESCRIPTION
        "This attribute contains the number of fully successful
        Dynamic Bonding Change transactions. It only
        applies to the downstream direction and does not include
        DBC transactions that result in Partial Service.
        Discontinuities in the value of this counter can occur
        at reinitialization of the managed system, and
        at other times as indicated by the value of
        ifCounterDiscontinuityTime of the associated MAC Domain
        interface index."
     REFERENCE
        "DOCSIS 3.0 MAC and Upper Layer Protocols Interface
        Specification CM-SP-MULPIv3.0-I08-080522, Dynamic Bonding
        Change (DBC) section; [RFC 2863]."
     ::= { docsQosDynamicServiceStatsEntry 26 }

docsQosDbcFails OBJECT-TYPE
     SYNTAX      Counter32
     MAX-ACCESS  read-only
     STATUS      current
     DESCRIPTION
        "This attribute contains the number of failed Dynamic
        Bonding Change transactions. It only applies to
        the downstream direction. Note that Partial Service
        is not considered a failed transaction. Discontinuities
        in the value of this counter can occur at reinitialization
        of the managed system, and at other times
        as indicated by the value of ifCounterDiscontinuityTime
        of the associated MAC Domain interface index."
     REFERENCE
        "DOCSIS 3.0 MAC and Upper Layer Protocols Interface
        Specification CM-SP-MULPIv3.0-I08-080522, Dynamic Bonding
        Change (DBC) section; [RFC 2863]."
     ::= { docsQosDynamicServiceStatsEntry 27 }

docsQosDbcPartial OBJECT-TYPE
     SYNTAX      Counter32
     MAX-ACCESS  read-only
     STATUS      current
     DESCRIPTION
        "This attribute contains the number of unsuccessful
        Dynamic Bonding Change transactions that result
        in Partial Service. IT only applies to the downstream
        direction. Discontinuities in the value of this counter
        can occur at reinitialization of the managed system,
        and at other times as indicated by the value of
        ifCounterDiscontinuityTime of the associated MAC
        Domain interface index."
     REFERENCE
        "DOCSIS 3.0 MAC and Upper Layer Protocols Interface
        Specification CM-SP-MULPIv3.0-I08-080522, Dynamic Bonding
        Change (DBC) section; [RFC 2863]."
     ::= { docsQosDynamicServiceStatsEntry 28 }

docsQosServiceFlowLogTable OBJECT-TYPE
     SYNTAX      SEQUENCE OF DocsQosServiceFlowLogEntry
     MAX-ACCESS  not-accessible
     STATUS      current
     DESCRIPTION
        "This object contains a log of the disconnected Service
        Flows in a managed device."
     ::= { docsQosMibObjects 7}

docsQosServiceFlowLogEntry OBJECT-TYPE
     SYNTAX      DocsQosServiceFlowLogEntry
     MAX-ACCESS  not-accessible
     STATUS      current
     DESCRIPTION
        "The conceptual row of docsQosServiceFlowLogTable."
     INDEX { docsQosServiceFlowLogIndex }
     ::= { docsQosServiceFlowLogTable 1 }

DocsQosServiceFlowLogEntry ::= SEQUENCE {
     docsQosServiceFlowLogIndex
                  Unsigned32,
     docsQosServiceFlowLogIfIndex
                  InterfaceIndex,
     docsQosServiceFlowLogSFID
                  Unsigned32,
     docsQosServiceFlowLogCmMac
                  MacAddress,
     docsQosServiceFlowLogPkts
                  Counter64,
     docsQosServiceFlowLogOctets
                  Counter64,
     docsQosServiceFlowLogTimeDeleted
                  TimeStamp,
     docsQosServiceFlowLogTimeCreated
                  TimeStamp,
     docsQosServiceFlowLogTimeActive
                  Counter32,
     docsQosServiceFlowLogDirection
                  IfDirection,
     docsQosServiceFlowLogPrimary
                  TruthValue,
     docsQosServiceFlowLogServiceClassName
                  SnmpAdminString,
     docsQosServiceFlowLogPolicedDropPkts
                  Counter32,
     docsQosServiceFlowLogPolicedDelayPkts
                  Counter32,
     docsQosServiceFlowLogControl
                  INTEGER
     }

docsQosServiceFlowLogIndex OBJECT-TYPE
     SYNTAX      Unsigned32 (1..4294967295)
     MAX-ACCESS  not-accessible
     STATUS      current
     DESCRIPTION
        "This key indicates an unique index for a logged service
        flow."
     ::= { docsQosServiceFlowLogEntry 1 }

docsQosServiceFlowLogIfIndex OBJECT-TYPE
     SYNTAX      InterfaceIndex
     MAX-ACCESS  read-only
     STATUS      current
     DESCRIPTION
        "This attribute indicates the MAC Domain Interface
        index where the service flow was present."
     ::= { docsQosServiceFlowLogEntry 2 }

docsQosServiceFlowLogSFID OBJECT-TYPE
     SYNTAX      Unsigned32 (1..4294967295)
     MAX-ACCESS  read-only
     STATUS      current
     DESCRIPTION
        "This attribute indicates the identifier assigned
        to the service flow."
     ::= { docsQosServiceFlowLogEntry 3 }

docsQosServiceFlowLogCmMac OBJECT-TYPE
     SYNTAX      MacAddress
     MAX-ACCESS  read-only
     STATUS      current
     DESCRIPTION
        "This attribute indicates the MAC address of the cable
        modem associated with the service flow."
     ::= { docsQosServiceFlowLogEntry 4 }

docsQosServiceFlowLogPkts OBJECT-TYPE
     SYNTAX      Counter64
     UNITS       "packets"
     MAX-ACCESS  read-only
     STATUS      current
     DESCRIPTION
        "This attribute indicates the final value of the Pkts
        attribute in the ServiceFlowStats object for the
        service flow."
     ::= { docsQosServiceFlowLogEntry 5 }

docsQosServiceFlowLogOctets OBJECT-TYPE
     SYNTAX      Counter64
     UNITS       "bytes"
     MAX-ACCESS  read-only
     STATUS      current
     DESCRIPTION
        "This attribute indicates the final value of the Pkts
        attribute in the ServiceFlowStats object for the
        service flow."
     ::= { docsQosServiceFlowLogEntry 6 }

docsQosServiceFlowLogTimeDeleted OBJECT-TYPE
     SYNTAX      TimeStamp
     MAX-ACCESS  read-only
     STATUS      current
     DESCRIPTION
        "This attribute indicates the value of sysUpTime when
        the service flow was deleted."
     ::= { docsQosServiceFlowLogEntry 7 }

docsQosServiceFlowLogTimeCreated OBJECT-TYPE
     SYNTAX      TimeStamp
     MAX-ACCESS  read-only
     STATUS      current
     DESCRIPTION
        "This attribute indicates the value of sysUpTime when
        the service flow was created."
     ::= { docsQosServiceFlowLogEntry 8 }

docsQosServiceFlowLogTimeActive OBJECT-TYPE
     SYNTAX      Counter32
     UNITS       "seconds"
     MAX-ACCESS  read-only
     STATUS      current
     DESCRIPTION
        "This attribute indicates the total time that the service
        flow was active."
     ::= { docsQosServiceFlowLogEntry 9 }

docsQosServiceFlowLogDirection OBJECT-TYPE
     SYNTAX      IfDirection
     MAX-ACCESS  read-only
     STATUS      current
     DESCRIPTION
        "This attribute indicates the value of Service Flow
        direction for the service flow."
     ::= { docsQosServiceFlowLogEntry 11 }

docsQosServiceFlowLogPrimary OBJECT-TYPE
     SYNTAX      TruthValue
     MAX-ACCESS  read-only
     STATUS      current
     DESCRIPTION
        "If set to 'true', this attribute indicates that the
        Service Flow in the log was a Primary Service Flow, otherwise,
        a Secondary Service Flow."
     ::= { docsQosServiceFlowLogEntry 12 }

docsQosServiceFlowLogServiceClassName OBJECT-TYPE
     SYNTAX      SnmpAdminString (SIZE(0..15))
     MAX-ACCESS  read-only
     STATUS      current
     DESCRIPTION
        "This attribute indicates the value of ServiceClassName
        for the provisioned QOS Parameter Set of the service
        flow."
     ::= { docsQosServiceFlowLogEntry 13 }

docsQosServiceFlowLogPolicedDropPkts OBJECT-TYPE
     SYNTAX      Counter32
     UNITS       "packets"
     MAX-ACCESS  read-only
     STATUS      current
     DESCRIPTION
        "This attribute indicates the final value of PolicedDropPkts
        attribute of the ServiceFlowStats object
        for the service flow."
     ::= { docsQosServiceFlowLogEntry 14 }

docsQosServiceFlowLogPolicedDelayPkts OBJECT-TYPE
     SYNTAX      Counter32
     UNITS       "packets"
     MAX-ACCESS  read-only
     STATUS      current
     DESCRIPTION
        "This attribute indicates the final value of PolicedDelayPkts
        attribute of the ServiceFlowStats object
        for the service flow."
     ::= { docsQosServiceFlowLogEntry 15 }

docsQosServiceFlowLogControl OBJECT-TYPE
     SYNTAX      INTEGER {

                        active(1),
                        destroy(6)
                      }
     MAX-ACCESS  read-write
     STATUS      current
     DESCRIPTION
        "This attribute when set to 'destroy' removes this
        instance from the object.
        Reading this attribute returns the value 'active'."
     ::= { docsQosServiceFlowLogEntry 16 }

docsQosServiceClassTable OBJECT-TYPE
     SYNTAX      SEQUENCE OF DocsQosServiceClassEntry
     MAX-ACCESS  not-accessible
     STATUS      current
     DESCRIPTION
        "This object describes a provisioned service class
        on a CMTS.
        Each object instance defines a template for certain
        DOCSIS QOS Parameter Set values.  When a CM creates or
        modifies an Admitted QOS Parameter Set for a Service
        Flow, it may reference a Service Class Name instead of
        providing explicit QOS Parameter
        Set values.  In this case, the CMTS populates the QOS Parameter
        Set with the applicable
        corresponding values from the named Service Class.
        Subsequent changes to a Service Class row do not affect
        the QOS Parameter Set values of any service flows already
        admitted.
        A service class template applies to only a single direction,
        as indicated in the ServiceClassDirection
        attribute."
     ::= { docsQosMibObjects 8}

docsQosServiceClassEntry OBJECT-TYPE
     SYNTAX      DocsQosServiceClassEntry
     MAX-ACCESS  not-accessible
     STATUS      current
     DESCRIPTION
        "The conceptual row of docsQosServiceClassTable."
     INDEX { docsQosServiceClassName }
     ::= { docsQosServiceClassTable 1 }

DocsQosServiceClassEntry ::= SEQUENCE {
     docsQosServiceClassName
                  SnmpAdminString,
     docsQosServiceClassStatus
                  RowStatus,
     docsQosServiceClassPriority
                  Unsigned32,
     docsQosServiceClassMaxTrafficRate
                  BitRate,
     docsQosServiceClassMaxTrafficBurst
                  Unsigned32,
     docsQosServiceClassMinReservedRate
                  BitRate,
     docsQosServiceClassMinReservedPkt
                  Unsigned32,
     docsQosServiceClassMaxConcatBurst
                  Unsigned32,
     docsQosServiceClassNomPollInterval
                  Unsigned32,
     docsQosServiceClassTolPollJitter
                  Unsigned32,
     docsQosServiceClassUnsolicitGrantSize
                  Unsigned32,
     docsQosServiceClassNomGrantInterval
                  Unsigned32,
     docsQosServiceClassTolGrantJitter
                  Unsigned32,
     docsQosServiceClassGrantsPerInterval
                  Unsigned32,
     docsQosServiceClassMaxLatency
                  Unsigned32,
     docsQosServiceClassActiveTimeout
                  Unsigned32,
     docsQosServiceClassAdmittedTimeout
                  Unsigned32,
     docsQosServiceClassSchedulingType
                  SchedulingType,
     docsQosServiceClassRequestPolicy
                  OCTET STRING,
     docsQosServiceClassTosAndMask
                  OCTET STRING,
     docsQosServiceClassTosOrMask
                  OCTET STRING,
     docsQosServiceClassDirection
                  IfDirection,
     docsQosServiceClassStorageType
                  StorageType,
     docsQosServiceClassDSCPOverwrite
                  DscpOrAny,
     docsQosServiceClassRequiredAttrMask
                  AttributeMask,
     docsQosServiceClassForbiddenAttrMask
                  AttributeMask,
     docsQosServiceClassAttrAggrRuleMask
                  AttrAggrRuleMask,
     docsQosServiceClassAppId
                  Unsigned32,
     docsQosServiceClassMultiplierContentionReqWindow
                  Unsigned32,
     docsQosServiceClassMultiplierBytesReq
                  Unsigned32,
     docsQosServiceClassMaxReqPerSidCluster
                  Unsigned32,
     docsQosServiceClassMaxOutstandingBytesPerSidCluster
                  Unsigned32,
     docsQosServiceClassMaxTotBytesReqPerSidCluster
                  Unsigned32,
     docsQosServiceClassMaxTimeInSidCluster
                  Unsigned32,
     docsQosServiceClassPeakTrafficRate
                  BitRate,
     docsQosServiceClassDsResequencing
                  INTEGER,
     docsQosServiceClassMinimumBuffer
                  Unsigned32,
     docsQosServiceClassTargetBuffer
                  Unsigned32,
     docsQosServiceClassMaximumBuffer
                  Unsigned32,
     docsQosServiceClassAqmDisabled
                  TruthValue,
     docsQosServiceClassAqmLatencyTarget
                  Unsigned32,
     docsQosServiceClassHCMaxTrafficRate
                  CounterBasedGauge64,
     docsQosServiceClassHCMinReservedRate
                  CounterBasedGauge64,
     docsQosServiceClassHCPeakTrafficRate
                  CounterBasedGauge64,
     docsQosServiceClassGuaranteedGrantInterval
                  Unsigned32,
     docsQosServiceClassGuaranteedGrantRate
                  Unsigned32,
     docsQosServiceClassGuaranteedRequestInterval
                  Unsigned32,
     docsQosServiceClassAqmAlgorithm
                  INTEGER,
     docsQosServiceClassImmedAqmMaxThreshold
                  Unsigned32,
     docsQosServiceClassImmedAqmRangeExponentRampFunc
                  Unsigned32,
     docsQosServiceClassLatencyHistBinEdges
                  OCTET STRING,
     docsQosServiceClassDataRateUnitSetting
                   DataRateUnitType
     }

docsQosServiceClassName OBJECT-TYPE
     SYNTAX      SnmpAdminString (SIZE(1..15))
     MAX-ACCESS  not-accessible
     STATUS      current
     DESCRIPTION
        "This key indicates the Service Class Name associated
        with this object instance.  DOCSIS specifies
        that the maximum size is 16 ASCII characters including
        a terminating zero.  The terminating zero is not
        represented in this SnmpAdminString syntax attribute."
     REFERENCE
        "DOCSIS 3.0 MAC and Upper Layer Protocols Interface
        Specification CM-SP-MULPIv3.0-I08-080522, Service Class
        Name section in the Common Radio Frequency Interface
        Encodings Annex."
     ::= { docsQosServiceClassEntry 1 }

docsQosServiceClassStatus OBJECT-TYPE
     SYNTAX      RowStatus
     MAX-ACCESS  read-create
     STATUS      current
     DESCRIPTION
        "The conceptual row status of this object."
     ::= { docsQosServiceClassEntry 3 }

docsQosServiceClassPriority OBJECT-TYPE
     SYNTAX      Unsigned32 (0..7)
     MAX-ACCESS  read-create
     STATUS      current
     DESCRIPTION
        "This attribute is the template for the Priority attribute
        of the QoS Parameter Set."
     DEFVAL { 0 }
     ::= { docsQosServiceClassEntry 4 }

docsQosServiceClassMaxTrafficRate OBJECT-TYPE
     SYNTAX      BitRate
     UNITS       "bps,kpbs,mbps,or gbps"
     MAX-ACCESS  read-create
     STATUS      current
     DESCRIPTION
        "This attribute is the template for the MaxTrafficRate
        attribute of the QoS Parameter Set.

        This attribute represents the 4 byte value of the maximum 
        sustained traffic rate allowed for this Service Flow. All 
        MAC frame data PDUs from the bytes following the MAC header
        HCS to the end of the CRC are included in calculating the 
        maximum sustained traffic rate. The number of bytes forwarded
        is limited during any time interval. The value 0 indicates
        no maximum traffic rate is enforced. The rate is specified
        in units of bps, kbps, mbps or gbps as specified by the 
        DataRateUnitSetting attribute. This attribute applies to 
        both upstream and downstream Service Flows. This attribute 
        also returns 0 if the referenced parameter is not present 
        in the corresponding DOCSIS QOS Parameter Set, or if the 
        parameter is not applicable."
     DEFVAL { 0 }
     ::= { docsQosServiceClassEntry 5 }

docsQosServiceClassMaxTrafficBurst OBJECT-TYPE
     SYNTAX      Unsigned32
     UNITS       "bytes"
     MAX-ACCESS  read-create
     STATUS      current
     DESCRIPTION
        "This attribute is the template for the MaxTrafficBurst
        attribute of the QoS Parameter Set.
        If this value is not set, the default for DOCSIS 3.0 is 
        3044, and for DOCSIS 4.0 the default value is 3044, or 
        4000 if support for extended packet size is enabled."
     DEFVAL { 3044 }
     ::= { docsQosServiceClassEntry 6 }

docsQosServiceClassMinReservedRate OBJECT-TYPE
     SYNTAX      BitRate
     UNITS       "bps,kbps,mbps,or gbps"
     MAX-ACCESS  read-create
     STATUS      current
     DESCRIPTION
        "This attribute is the template for the MinReservedRate
        attribute of the QoS Parameter Set.

        This attribute represents the 4 byte value of the guaranteed
        minimum rate allowed for this Service Flow. The value is 
        calculated from the byte following the MAC header HCS to 
        the end of the CRC. The value 0 indicates that no bandwidth 
        is reserved. The rate is specified in units of Bps, Kbps, 
        Mbps or Gbps as specified by the DataRateUnitSetting attribute. 
        This attribute also returns 0 if the referenced parameter is
        not present in the corresponding DOCSIS QOS Parameter Set,
        or if the parameter is not applicable."
     DEFVAL { 0 }
     ::= { docsQosServiceClassEntry 7 }

docsQosServiceClassMinReservedPkt OBJECT-TYPE
     SYNTAX      Unsigned32 (0..65535)
     UNITS       "bytes"
     MAX-ACCESS  read-create
     STATUS      current
     DESCRIPTION
        "This attribute is the template for the MinReservedPkt
        attribute of the QoS Parameter Set."
     ::= { docsQosServiceClassEntry 8 }

docsQosServiceClassMaxConcatBurst OBJECT-TYPE
     SYNTAX      Unsigned32 (0..65535)
     UNITS       "bytes"
     MAX-ACCESS  read-create
     STATUS      current
     DESCRIPTION
        "This attribute is the template for the MaxConcatBurst
        attribute of the QoS Parameter Set."
     DEFVAL { 1522 }
     ::= { docsQosServiceClassEntry 9 }

docsQosServiceClassNomPollInterval OBJECT-TYPE
     SYNTAX      Unsigned32
     UNITS       "microseconds"
     MAX-ACCESS  read-create
     STATUS      current
     DESCRIPTION
        "This attribute is the template for the NomPollInterval
        attribute of the QoS Parameter Set."
     DEFVAL { 0 }
     ::= { docsQosServiceClassEntry 10 }

docsQosServiceClassTolPollJitter OBJECT-TYPE
     SYNTAX      Unsigned32
     UNITS       "microseconds"
     MAX-ACCESS  read-create
     STATUS      current
     DESCRIPTION
        "This attribute is the template for the TolPolJitter
        attribute of the QoS Parameter Set."
     DEFVAL { 0 }
     ::= { docsQosServiceClassEntry 11 }

docsQosServiceClassUnsolicitGrantSize OBJECT-TYPE
     SYNTAX      Unsigned32 (0..65535)
     UNITS       "bytes"
     MAX-ACCESS  read-create
     STATUS      current
     DESCRIPTION
        "This attribute is the template for the UnsolicitGrantSize
        attribute of the QoS Parameter Set."
     DEFVAL { 0 }
     ::= { docsQosServiceClassEntry 12 }

docsQosServiceClassNomGrantInterval OBJECT-TYPE
     SYNTAX      Unsigned32
     UNITS       "microseconds"
     MAX-ACCESS  read-create
     STATUS      current
     DESCRIPTION
        "This attribute is the template for the NomGrantInterval
        attribute of the QoS Parameter Set."
     DEFVAL { 0 }
     ::= { docsQosServiceClassEntry 13 }

docsQosServiceClassTolGrantJitter OBJECT-TYPE
     SYNTAX      Unsigned32
     UNITS       "microseconds"
     MAX-ACCESS  read-create
     STATUS      current
     DESCRIPTION
        "This attribute is the template for the TolGrantJitter
        attribute of the QoS Parameter Set."
     DEFVAL { 0 }
     ::= { docsQosServiceClassEntry 14 }

docsQosServiceClassGrantsPerInterval OBJECT-TYPE
     SYNTAX      Unsigned32 (0..127)
     UNITS       "dataGrants"
     MAX-ACCESS  read-create
     STATUS      current
     DESCRIPTION
        "This attribute is the template for the GrantsPerInterval
        attribute of the QoS Parameter Set."
     DEFVAL { 0 }
     ::= { docsQosServiceClassEntry 15 }

docsQosServiceClassMaxLatency OBJECT-TYPE
     SYNTAX      Unsigned32
     UNITS       "microseconds"
     MAX-ACCESS  read-create
     STATUS      current
     DESCRIPTION
        "This attribute is the template for the MaxLatency
        attribute of the QoS Parameter Set."
     DEFVAL { 0 }
     ::= { docsQosServiceClassEntry 16 }

docsQosServiceClassActiveTimeout OBJECT-TYPE
     SYNTAX      Unsigned32 (0..65535)
     UNITS           "seconds"
     MAX-ACCESS  read-create
     STATUS      current
     DESCRIPTION
        "This attribute is the template for the ActiveTimeout
        attribute of the QoS Parameter Set."
     DEFVAL { 0 }
     ::= { docsQosServiceClassEntry 17 }

docsQosServiceClassAdmittedTimeout OBJECT-TYPE
     SYNTAX      Unsigned32 (0..65535)
     UNITS           "seconds"
     MAX-ACCESS  read-create
     STATUS      current
     DESCRIPTION
        "This attribute is the template for the AddmitedTimeout
        attribute of the QoS Parameter Set."
     DEFVAL { 200 }
     ::= { docsQosServiceClassEntry 18 }

docsQosServiceClassSchedulingType OBJECT-TYPE
     SYNTAX      SchedulingType
     MAX-ACCESS  read-create
     STATUS      current
     DESCRIPTION
        "This attribute is the template for the SchedulingType
        attribute of the QoS Parameter Set."
     DEFVAL { bestEffort }
     ::= { docsQosServiceClassEntry 19 }

docsQosServiceClassRequestPolicy OBJECT-TYPE
     SYNTAX      OCTET STRING (SIZE(4))
     MAX-ACCESS  read-create
     STATUS      current
     DESCRIPTION
        "This attribute is the template for the ReqPolicyOct
        attribute of the QoS Parameter Set."
    DEFVAL       { '00000000'H }
     ::= { docsQosServiceClassEntry 20 }

docsQosServiceClassTosAndMask OBJECT-TYPE
     SYNTAX      OCTET STRING (SIZE(1))
     MAX-ACCESS  read-create
     STATUS      current
     DESCRIPTION
        "This attribute is the template for the TosAndMask
        attribute of the QoS Parameter Set."
     ::= { docsQosServiceClassEntry 21 }

docsQosServiceClassTosOrMask OBJECT-TYPE
     SYNTAX      OCTET STRING (SIZE(1))
     MAX-ACCESS  read-create
     STATUS      current
     DESCRIPTION
        "This attribute is the template for the TosOrMask attribute
        of the QoS Parameter Set."
     ::= { docsQosServiceClassEntry 22 }

docsQosServiceClassDirection OBJECT-TYPE
     SYNTAX      IfDirection
     MAX-ACCESS  read-create
     STATUS      current
     DESCRIPTION
        "This attribute is the template for the Direction attribute
        of the QoS Parameter Set."
     DEFVAL { upstream }
     ::= { docsQosServiceClassEntry 23 }

docsQosServiceClassStorageType OBJECT-TYPE
     SYNTAX      StorageType
     MAX-ACCESS  read-create
     STATUS      current
     DESCRIPTION
        "This attribute defines whether this row is kept in
        volatile storage and lost upon reboot or whether
        it is backed up by non-volatile or permanent storage.
        'permanent' entries need not allow writable access to
        any instance attribute."
     DEFVAL { nonVolatile }
     ::= { docsQosServiceClassEntry 24 }

docsQosServiceClassDSCPOverwrite OBJECT-TYPE
     SYNTAX      DscpOrAny
     MAX-ACCESS  read-create
     STATUS      current
     DESCRIPTION
        "This attribute allows the overwrite of the DSCP field
        per RFC 3260.
        If this attribute is -1, then the corresponding TosAndMask
        value is set to be 'FF'H and TosOrMask is set to
        '00'H.  Otherwise, this attribute is in the range of                     0..63,
        and the corresponding TosAndMask value is '03'H
        and TosOrMaskvalue is this attribute value shifted
        left by two bit positions."
     DEFVAL { -1 }
     ::= { docsQosServiceClassEntry 25 }

docsQosServiceClassRequiredAttrMask OBJECT-TYPE
     SYNTAX      AttributeMask
     MAX-ACCESS  read-create
     STATUS      current
     DESCRIPTION
        "This attribute is the template for the RequiredAttrMask
        attribute of the QoS Parameter Set."
     DEFVAL { {  } }
     ::= { docsQosServiceClassEntry 26 }

docsQosServiceClassForbiddenAttrMask OBJECT-TYPE
     SYNTAX      AttributeMask
     MAX-ACCESS  read-create
     STATUS      current
     DESCRIPTION
        "This attribute is the template for the ForbiddenAttrMask
        attribute of the QoS Parameter Set."
     DEFVAL { {  } }
     ::= { docsQosServiceClassEntry 27 }

docsQosServiceClassAttrAggrRuleMask OBJECT-TYPE
     SYNTAX      AttrAggrRuleMask
     MAX-ACCESS  read-create
     STATUS      current
     DESCRIPTION
        "This attribute is the template for the AttrAggregationMask
        attribute of the QoS Parameter Set."
     DEFVAL { "0000" }
     ::= { docsQosServiceClassEntry 28 }

docsQosServiceClassAppId OBJECT-TYPE
     SYNTAX      Unsigned32
     MAX-ACCESS  read-create
     STATUS      current
     DESCRIPTION
        "This attribute is the template for the AppId attribute
        of the QoS Parameter Set."
     ::= { docsQosServiceClassEntry 29 }

docsQosServiceClassMultiplierContentionReqWindow OBJECT-TYPE
     SYNTAX      Unsigned32 (4..12)
     UNITS       "eighths"
     MAX-ACCESS  read-create
     STATUS      current
     DESCRIPTION
        "This attribute is the template for the MultiplierContentionReqWindow
        attribute of the QoS Parameter
        Set."
     DEFVAL { 8 }
     ::= { docsQosServiceClassEntry 30 }

docsQosServiceClassMultiplierBytesReq OBJECT-TYPE
     SYNTAX      Unsigned32 (1 | 2 | 4 | 8 | 16)
     MAX-ACCESS  read-create
     STATUS      current
     DESCRIPTION
        "This attribute is the template for the MultiplierBytesReq
        attribute of the QoS Parameter Set."
     DEFVAL { 4 }
     ::= { docsQosServiceClassEntry 31 }

docsQosServiceClassMaxReqPerSidCluster OBJECT-TYPE
     SYNTAX      Unsigned32 (0..255)
     UNITS       "requests"
     MAX-ACCESS  read-create
     STATUS      deprecated
     DESCRIPTION
        "This attribute is the template for the MaxReqPerSidCluster
        attribute of the QoS Parameter Set.

        This attribute has been deprecated and replaced with
        docsQosServiceFlowMaxReqPerSidCluster in the
        docsQosServiceFlowTable."
     DEFVAL { 0 }
     ::= { docsQosServiceClassEntry 32 }

docsQosServiceClassMaxOutstandingBytesPerSidCluster OBJECT-TYPE
     SYNTAX      Unsigned32
     UNITS       "bytes"
     MAX-ACCESS  read-create
     STATUS      deprecated
     DESCRIPTION
        "This attribute is the template for the MaxOutstandingBytesPerSidCluster
        attribute of the QoS Parameter Set.

        This attribute has been deprecated and replaced with
        docsQosServiceFlowMaxOutstandingBytesPerSidCluster in the
        docsQosServiceFlowTable."
     DEFVAL { 0 }
     ::= { docsQosServiceClassEntry 33 }

docsQosServiceClassMaxTotBytesReqPerSidCluster OBJECT-TYPE
     SYNTAX      Unsigned32
     UNITS       "bytes"
     MAX-ACCESS  read-create
     STATUS      deprecated
     DESCRIPTION
        "This attribute is the template for the MaxTotBytesReqPerSidCluster
        attribute of the QoS Parameter Set.
        This attribute has been deprecated and replaced with
        docsQosServiceFlowMaxTotBytesReqPerSidCluster in the
        docsQosServiceFlowTable."

     DEFVAL { 0 }
     ::= { docsQosServiceClassEntry 34 }

docsQosServiceClassMaxTimeInSidCluster OBJECT-TYPE
     SYNTAX      Unsigned32 (0..65535)
     UNITS       "milliseconds"
     MAX-ACCESS  read-create
     STATUS      deprecated
     DESCRIPTION
        "This attribute is the template for the MaxTimeInSidCluster
        attribute of the QoS Parameter Set.

        This attribute has been deprecated and replaced with
        docsQosServiceFlowMaxTimeInSidCluster in the
        docsQosServiceFlowTable."
     DEFVAL { 0 }
     ::= { docsQosServiceClassEntry 35 }

docsQosServiceClassPeakTrafficRate OBJECT-TYPE
     SYNTAX      BitRate
     UNITS       "bps,kbps,mbps,or gbps"
     MAX-ACCESS  read-create
     STATUS      current
     DESCRIPTION
        "This attribute is the template for the PeakTrafficRate
        attribute of the QoS Parameter Set.

        This attribute represents the 4 byte value of the rate
        parameter 'P' of a token-bucket-based peak rate limiter
        for packets of this Service Flow. A value of 0 means 
        the downstream peak traffic rate is not limited. The 
        rate is specified in units of bps, kbps, mbps or gbps
        as specified by the DataRateUnitSetting attribute. 
        This attribute also returns 0 if the referenced parameter
        is not present in the corresponding DOCSIS QOS Parameter Set,
        or if the parameter is not applicable."
     DEFVAL { 0 }
     ::= { docsQosServiceClassEntry 36 }

docsQosServiceClassDsResequencing OBJECT-TYPE
     SYNTAX      INTEGER {
                          resequencingDsid(0),
                          noResequencingDsid(1)
                         }
     MAX-ACCESS  read-create
     STATUS      current
     DESCRIPTION
        "This attribute is the template for the DsResequencing
        attribute of the QoS Parameter Set."
     DEFVAL { 0 }
     ::= { docsQosServiceClassEntry 37 }

docsQosServiceClassMinimumBuffer OBJECT-TYPE
     SYNTAX      Unsigned32 (0..4294967295)
     UNITS       "bytes"
     MAX-ACCESS  read-create
     STATUS      current
     DESCRIPTION
        "This attribute is the template for the MinimumBuffer
        attribute of the QoS Parameter Set."
     DEFVAL { 0 }
     ::= { docsQosServiceClassEntry 38 }

docsQosServiceClassTargetBuffer OBJECT-TYPE
     SYNTAX      Unsigned32 (0..4294967295)
     UNITS       "bytes"
     MAX-ACCESS  read-create
     STATUS      current
     DESCRIPTION
        "This attribute is the template for the TargetBuffer
        attribute of the QoS Parameter Set."
     DEFVAL { 0 }
     ::= { docsQosServiceClassEntry 39 }

docsQosServiceClassMaximumBuffer OBJECT-TYPE
     SYNTAX      Unsigned32 (0..4294967295)
     UNITS       "bytes"
     MAX-ACCESS  read-create
     STATUS      current
     DESCRIPTION
        "This attribute is the template for the MaximumBuffer
        attribute of the QoS Parameter Set."
     DEFVAL { 4294967295 }
     ::= { docsQosServiceClassEntry 40 }

docsQosServiceClassAqmDisabled OBJECT-TYPE
     SYNTAX      TruthValue
     MAX-ACCESS  read-create
     STATUS      current
     DESCRIPTION
        "If this attribute returns 'true', AQM is disabled for
        Service Flows in this Service Class."
     REFERENCE
        "DOCSIS 3.1 MAC and Upper Layer Protocols Interface
        Specification CM-SP-MULPIv3.1-I04-141218, AQM Encodings section
        in the Common Radio Frequency Interface Encodings Annex."
     ::= { docsQosServiceClassEntry 42 }

docsQosServiceClassAqmLatencyTarget OBJECT-TYPE
     SYNTAX      Unsigned32(0..256)
     UNITS       "milliseconds"
     MAX-ACCESS  read-create
     STATUS      current
     DESCRIPTION
        "This attribute configures the target latency for this service flow
          when operating under Classic Active Queue Management (e.g. DOCSIS-PIE).
           If set to 0, the value in the AqmGlobalLatencyTarget attribute 
           of the DocsQosCfg object will be used. This attribute applies to 
           both upstream and downstream service flows. This attribute is
           only used when AqmGlobalEnable in the DocsQosCfg object is set
           to 'true' and the AqmEnable attribute is set to 'true'. This parameter 
           will be ignored if the AQM Algorithm used by the Service Flow is 
           ImmediateAqm."
     REFERENCE
        "DOCSIS 3.1 MAC and Upper Layer Protocols Interface
        Specification CM-SP-MULPIv3.1-I04-141218, AQM Encodings section
        in the Common Radio Frequency Interface Encodings Annex."
	 DEFVAL {0}
     ::= { docsQosServiceClassEntry 43 }

docsQosServiceClassHCMaxTrafficRate OBJECT-TYPE
     SYNTAX      CounterBasedGauge64
     UNITS       "bps"
     MAX-ACCESS  read-only
     STATUS      obsolete
     DESCRIPTION
        "This attribute is a 64-bit representation of the maximum
        sustained traffic rate allowed for this Service Flow
        in bits/sec.
        It counts all MAC frame data PDUs from the bytes following
        the MAC header HCS to the end of the CRC. The number
        of bytes forwarded is limited during any time interval.
        The value 0 means no maximum traffic rate is enforced.
        This attribute applies to both upstream and
        downstream Service Flows.
        This attribute returns 0 if the referenced parameter
        is not present in the corresponding DOCSIS QOS Parameter
        Set, or if the parameter is not applicable."
     REFERENCE
        "DOCSIS 3.0 MAC and Upper Layer Protocols Interface
        Specification CM-SP-MULPIv3.0-I08-080522, Maximum Sustained
        Traffic Rate section in the Common Radio Frequency Interface
        Encodings Annex."
     ::= { docsQosServiceClassEntry 44 }

docsQosServiceClassHCMinReservedRate OBJECT-TYPE
     SYNTAX      CounterBasedGauge64
     UNITS       "bps"
     MAX-ACCESS  read-only
     STATUS      obsolete
     DESCRIPTION
        "This attribute is a 64-bit representation of the guaranteed
        minimum rate in bits/sec for this parameter set. The value is
        calculated from the byte following the MAC header HCS
        to the end of the CRC. The value of 0 indicates that no
        bandwidth is reserved.
        If the referenced parameter is not present in the corresponding
        DOCSIS QOS Parameter Set, this attribute
        returns 0. If the parameter is not applicable, it is
        reported as 0."
     REFERENCE
        "DOCSIS 3.0 MAC and Upper Layer Protocols Interface
        Specification CM-SP-MULPIv3.0-I08-080522, Minimum Reserved
        Traffic Rate section of the Common Radio Frequency Interface
        Encodings Annex."
     ::= { docsQosServiceClassEntry 45 }

docsQosServiceClassHCPeakTrafficRate OBJECT-TYPE
     SYNTAX      CounterBasedGauge64
     UNITS       "bps"
     MAX-ACCESS  read-only
     STATUS      obsolete
     DESCRIPTION
        "This attribute specifies the rate parameter 'P' of a
        token-bucket-based peak rate limiter for packets of a
        service flow. A value of 0 signifies no
        Peak Traffic Rate is enforced.

        If the referenced parameter is not present in the
        corresponding DOCSIS QOS Parameter Set,
        this attribute returns 0."
     REFERENCE
        "DOCSIS 3.0 MAC and Upper Layer Protocols Interface
        Specification CM-SP-MULPIv3.0-I08-080522,
        Peak Traffic Rate section in the Common Radio Frequency
        Interface Encodings Annex."
     ::= { docsQosServiceClassEntry 46 }


docsQosServiceClassGuaranteedGrantInterval OBJECT-TYPE
     SYNTAX      Unsigned32 (0..65535)
     UNITS         "microseconds"
     MAX-ACCESS  read-create
     STATUS      current
     DESCRIPTION
        "This attribute specifies the maximum interval between
        successive data transmission opportunities, for a PGS Service
        Flow. This attribute is a 16-bit representation of the grant
        interval in units of microseconds"
     REFERENCE
        "DOCSIS 3.1 MAC and Upper Layer Protocols Interface
        Specification CM-SP-MULPIv3.1-I13-181213,
        Upstream-Specific QoS Parameter Encodings."
     ::= { docsQosServiceClassEntry 47 }

docsQosServiceClassGuaranteedGrantRate OBJECT-TYPE
     SYNTAX      Unsigned32 (0..4294967295)
     UNITS          "bps"
     MAX-ACCESS  read-create
     STATUS      current
     DESCRIPTION
        "The value of this parameter specifies the minimum granting
        rate, in bits/sec, for an upstream PGS service flow. The valid
        range of this parameter is specific to the CMTS. If configured
        and accepted, the CMTS MUST enforce this parameter as described
        for the GGI enforcement"
     REFERENCE
        "DOCSIS 3.1 MAC and Upper Layer Protocols Interface
        Specification CM-SP-MULPIv3.1-I13-181213,
        Upstream-Specific QoS Parameter Encodings."
	 DEFVAL {0}
     ::= { docsQosServiceClassEntry 48 }

docsQosServiceClassGuaranteedRequestInterval OBJECT-TYPE
     SYNTAX      Unsigned32 (0..65535)
     UNITS          "microseconds"
     MAX-ACCESS  read-create
     STATUS      current
     DESCRIPTION
        "The value of this parameter specifies the maximum interval (in
        units of microseconds) between successive request opportunities
        (including unicast request opportunities and piggyback request
        opportunities) for an upstream PGS service flow."
     REFERENCE
        "DOCSIS 3.1 MAC and Upper Layer Protocols Interface
        Specification CM-SP-MULPIv3.1-I13-181213,
        Upstream-Specific QoS Parameter Encodings."
     ::= { docsQosServiceClassEntry 49 }

docsQosServiceClassAqmAlgorithm OBJECT-TYPE
     SYNTAX      INTEGER {
                     unknown(1),
                     other(2),
                     docsisPIE(3),
                     immediateAqm(4)
                     }
     MAX-ACCESS  read-create
     STATUS      current
     DESCRIPTION
        "This attribute specifies the AQM algorithm in use for this
         service flow. If AQM is disabled on the service flow specified
         by ServiceFlowId, this attribute returns unknown(1).
         The value unknown(1) is reported for downstream service flows
         or when AQM is disabled.
         The value other(2) indicates a vendor proprietary algorithm
         for upstream queue management.
         The value docsisPIE(3) indicates the upstream queue management
         Proportional Integral controller Enhanced (PIE) algorithm.
         The value immediateAqm(4) indicates the upstream low latency
         queue management Immediate AQM algorithm."
     REFERENCE
        "DOCSIS 3.1 MAC and Upper Layer Protocols Interface
        Specification CM-SP-MULPIv3.1-I08-151210,
        Proportional-Integral-Enhanced Active Queue Management
        Algorithm Annex."
     ::= { docsQosServiceClassEntry 50 }

docsQosServiceClassImmedAqmMaxThreshold OBJECT-TYPE
     SYNTAX      Unsigned32 (0..65535)
     UNITS       "microseconds"
     MAX-ACCESS  read-create
     STATUS      current
     DESCRIPTION
        "This attribute provides provides the maximum threshold in
        microseconds of the ramp function used by the Immediate AQM
        algorithm and the Queue Protection algorithm. This attribute applies
        only if the 'SF AQM Algorithm' used by the Service Flow
        is configured as ImmediateAqm. Otherwise, it returns a 0. "
     REFERENCE
        "DOCSIS 3.1 MAC and Upper Layer Protocols Interface
        Specification CM-SP-MULPIv3.1-I04-141218, AQM Encodings section."
	 DEFVAL {475}
     ::= { docsQosServiceClassEntry 51 }

docsQosServiceClassImmedAqmRangeExponentRampFunc OBJECT-TYPE
     SYNTAX      Unsigned32 (0..255)
     UNITS       "log2(nanoseconds)"
     MAX-ACCESS  read-create
     STATUS      current
     DESCRIPTION
        "This attribute provides provides the range in nanoseconds of
        the ramp function used by the the Immediate AQM algorithm
        and the Queue Protection algorithm. It is expressed as
        an exponent of 2, e.g. a value of 19 means the range of the ramp
        will be 2^19 = 524288 ns. This parameter is only defined if
        the AQM algorithm used by the Service Flow is ImmediateAqm,
        otherwise it returns a 0."
     REFERENCE
        "DOCSIS 3.1 MAC and Upper Layer Protocols Interface
        Specification CM-SP-MULPIv3.1-I04-141218, AQM Encodings section"
	 DEFVAL {19}
     ::= { docsQosServiceClassEntry 52 }

docsQosServiceClassLatencyHistBinEdges OBJECT-TYPE
     SYNTAX      OCTET STRING (SIZE (0..30))
     UNITS       "10 microseconds"
     MAX-ACCESS  read-create
     STATUS      current
     DESCRIPTION
        "This attibute, if non-zero, enables Latency Reporting. The attribute is
        formatted as a string of unsigned 16-bit integers, each representing a
        histogram upper bin edge in units of 10 microseconds"
     REFERENCE
        "DOCSIS 3.1 MAC and Upper Layer Protocols Interface
        Specification CM-SP-MULPIv3.1-I04-141218, AQM Encodings section."
     ::= { docsQosServiceClassEntry 53 }

docsQosServiceClassDataRateUnitSetting  OBJECT-TYPE
     SYNTAX      DataRateUnitType
     UNITS       "bps"
     MAX-ACCESS  read-create
     STATUS      current
     DESCRIPTION
        "This attribute indicates the base unit for the ServiceClass
        traffic rate configuration attributes Maximum Sustained Traffic 
        Rate (MaxTrafficRate), Minimum Reserved Traffic Rate 
        (MinReservedRate), and Peak Traffic Rate (PeakTrafficeRate). 
        The value of this attribute allows for their interpretation in
        units of bps, kbps, mbps or gbps. The default value for 
        DataRateUnitSetting is bits per second (bps)."
     REFERENCE
        "DOCSIS 3.1 MAC and Upper Layer Protocols Interface
        Specification CM-SP-MULPIv3.1-I04-141218, AQM Encodings section."
     ::= { docsQosServiceClassEntry 54 }


docsQosPHSTable OBJECT-TYPE
     SYNTAX      SEQUENCE OF DocsQosPHSEntry
     MAX-ACCESS  not-accessible
     STATUS      obsolete
     DESCRIPTION
        "This object describes the set of payload header suppression
        of Service Flows."
     REFERENCE
        "DOCSIS 3.0 MAC and Upper Layer Protocols Interface
        Specification CM-SP-MULPIv3.0-I08-080522, Payload Header
        Suppression section in the Common Radio Frequency Interface
        Encodings Annex."
     ::= { docsQosMibObjects 10}

docsQosPHSEntry OBJECT-TYPE
     SYNTAX      DocsQosPHSEntry
     MAX-ACCESS  not-accessible
     STATUS      obsolete
     DESCRIPTION
        "The conceptual row of docsQosPHSTable.
        The ifIndex key corresponds to the MAC Domain interface
        of the service flow of the classifier that includes this
        PHS rule."
     INDEX { ifIndex,
             docsQosServiceFlowId,
             docsQosPktClassId
           }
     ::= { docsQosPHSTable 1 }

DocsQosPHSEntry ::= SEQUENCE {
     docsQosPHSField
                  OCTET STRING,
     docsQosPHSMask
                  OCTET STRING,
     docsQosPHSSize
                  Unsigned32,
     docsQosPHSVerify
                  TruthValue,
     docsQosPHSIndex
                  Unsigned32
     }

docsQosPHSField OBJECT-TYPE
     SYNTAX      OCTET STRING (SIZE (0..255))
     MAX-ACCESS  read-only
     STATUS      obsolete
     DESCRIPTION
        "This attribute indicates the Payload Header suppression
        field defines the bytes of the header that must
        be suppressed/restored by the sending/receiving
        device.
        The number of octets in this attribute should be the same
        as the value of PHSSize."
     REFERENCE
        "DOCSIS 3.0 MAC and Upper Layer Protocols Interface
        Specification CM-SP-MULPIv3.0-I08-080522, Payload Header
        Suppression Field (PHSF) section in the Common Radio
        Frequency Interface Encodings Annex."
     ::= { docsQosPHSEntry 2 }

docsQosPHSMask OBJECT-TYPE
     SYNTAX      OCTET STRING (SIZE (0..32))
     MAX-ACCESS  read-only
     STATUS      obsolete
     DESCRIPTION
        "This attribute defines the bit mask that is used in
        combination with the PHSField.  It defines which bytes
        in the header must be suppressed/restored by the sending
        or receiving device.

        Each bit of this bit mask corresponds to a byte in the PHSField,
        with the least
        significant bit corresponding to the first byte of the
        PHSField.

        Each bit of the bit mask specifies whether the corresponding
        byte should be suppressed in the packet.  A bit
        value of '1' indicates that the byte should be suppressed
        by the sending device and restored by the receiving
        device.
        A bit value of '0' indicates that the byte should not be
        suppressed by the sending device or restored by the
        receiving device.
        If the bit mask does not contain a bit for each byte in the
        PHSField, then the bit mask is extended with bit values
        of '1' to be the necessary length."
     REFERENCE
        "DOCSIS 3.0 MAC and Upper Layer Protocols Interface
        Specification CM-SP-MULPIv3.0-I08-080522, Payload Header
        Suppression Mask (PHSM) section in the Common Radio Frequency
        Interface Encodings Annex."
     ::= { docsQosPHSEntry 3 }

docsQosPHSSize OBJECT-TYPE
     SYNTAX      Unsigned32 (0..255)
     UNITS       "bytes"
     MAX-ACCESS  read-only
     STATUS      obsolete
     DESCRIPTION
        "This attribute specifies the number of bytes in the
        header to be suppressed  and restored.
        The value of this attribute matches the number of bytes
        in the Field attribute."
     REFERENCE
        "DOCSIS 3.0 MAC and Upper Layer Protocols Interface
        Specification CM-SP-MULPIv3.0-I08-080522, Payload Header Suppression
        Size (PHSS) section in the Common Radio Frequency Interface
        Encodings Annex."
     ::= { docsQosPHSEntry 4 }

docsQosPHSVerify OBJECT-TYPE
     SYNTAX      TruthValue
     MAX-ACCESS  read-only
     STATUS      obsolete
     DESCRIPTION
        "If 'true', this attribute indicates that the sender
        must verify that the PHS Field
        is the same as the content in the packet to be suppressed."
     REFERENCE
        "DOCSIS 3.0 MAC and Upper Layer Protocols Interface
        Specification CM-SP-MULPIv3.0-I08-080522, Payload Header
        Suppression Verification (PHSV) section in the Common Radio
        Frequency Interface Encodings Annex."
     ::= { docsQosPHSEntry 5 }

docsQosPHSIndex OBJECT-TYPE
     SYNTAX      Unsigned32 (1..255)
     MAX-ACCESS  read-only
     STATUS      obsolete
     DESCRIPTION
        "This attribute uniquely references the PHS rule for
        a given service flow."
     REFERENCE
        "DOCSIS 3.0 MAC and Upper Layer Protocols Interface
        Specification CM-SP-MULPIv3.0-I08-080522, Payload Header
        Suppression Index (PHSI) section in the Common Radio
        Frequency Interface Encodings Annex."
     ::= { docsQosPHSEntry 7 }

docsQosCmtsMacToSrvFlowTable OBJECT-TYPE
     SYNTAX      SEQUENCE OF DocsQosCmtsMacToSrvFlowEntry
     MAX-ACCESS  not-accessible
     STATUS      current
     DESCRIPTION
        "This object provides the mapping of unicast service
        flows with the cable modem the service flows belongs
        to."
     ::= { docsQosMibObjects 11}

docsQosCmtsMacToSrvFlowEntry OBJECT-TYPE
     SYNTAX      DocsQosCmtsMacToSrvFlowEntry
     MAX-ACCESS  not-accessible
     STATUS      current
     DESCRIPTION
        "The conceptual row of docsQosCmtsMacToSrvFlowTable."
     INDEX {
             docsQosCmtsCmMac,
             docsQosCmtsServiceFlowId
           }
     ::= { docsQosCmtsMacToSrvFlowTable 1 }

DocsQosCmtsMacToSrvFlowEntry ::= SEQUENCE {
     docsQosCmtsCmMac
                  MacAddress,
     docsQosCmtsServiceFlowId
                  Unsigned32,
     docsQosCmtsIfIndex
                  InterfaceIndex
     }

docsQosCmtsCmMac OBJECT-TYPE
     SYNTAX      MacAddress
     MAX-ACCESS  not-accessible
     STATUS      current
     DESCRIPTION
        "This key represents the MAC address for the referenced
        CM."
     ::= { docsQosCmtsMacToSrvFlowEntry 1 }

docsQosCmtsServiceFlowId OBJECT-TYPE
     SYNTAX      Unsigned32 (1..4294967295)
     MAX-ACCESS  not-accessible
     STATUS      current
     DESCRIPTION
        "This key represents the identifier of the Service
        Flow."
     ::= { docsQosCmtsMacToSrvFlowEntry 2 }

docsQosCmtsIfIndex OBJECT-TYPE
     SYNTAX      InterfaceIndex
     MAX-ACCESS  read-only
     STATUS      current
     DESCRIPTION
        "This attribute represents the interface index of
        the MAC domain of the Service Flow and where the CableModem
        is registered."
     ::= { docsQosCmtsMacToSrvFlowEntry 3 }

docsQosServiceFlowSidClusterTable OBJECT-TYPE
     SYNTAX      SEQUENCE OF DocsQosServiceFlowSidClusterEntry
     MAX-ACCESS  not-accessible
     STATUS      current
     DESCRIPTION
        "This object defines the SID clusters associated with
        an upstream service flow."
     REFERENCE
        "DOCSIS 3.0 MAC and Upper Layer Protocols Interface
        Specification CM-SP-MULPIv3.0-I08-080522,  Service Flow SID
        Cluster Assignments section in the Common Radio Frequency
        Interface Encodings Annex."
     ::= { docsQosMibObjects 12}

docsQosServiceFlowSidClusterEntry OBJECT-TYPE
     SYNTAX      DocsQosServiceFlowSidClusterEntry
     MAX-ACCESS  not-accessible
     STATUS      current
     DESCRIPTION
        "The conceptual row of docsQosServiceFlowSidClusterTable.
        The ifIndex key corresponds to the MAC Domain interface
        of the service flow."
     INDEX { ifIndex,
             docsQosServiceFlowId,
             docsQosServiceFlowSidClusterId,
             docsQosServiceFlowSidClusterUcid
            }
     ::= { docsQosServiceFlowSidClusterTable 1 }

DocsQosServiceFlowSidClusterEntry ::= SEQUENCE {
     docsQosServiceFlowSidClusterId
                  Unsigned32,
     docsQosServiceFlowSidClusterUcid
                  Unsigned32,
     docsQosServiceFlowSidClusterSid
                  Unsigned32
     }

docsQosServiceFlowSidClusterId OBJECT-TYPE
     SYNTAX      Unsigned32 (0..7)
     MAX-ACCESS  not-accessible
     STATUS      current
     DESCRIPTION
        "This key represents the SID Cluster ID of the SID Cluster."
     REFERENCE
        "DOCSIS 3.0 MAC and Upper Layer Protocols Interface
        Specification CM-SP-MULPIv3.0-I08-080522, SID Cluster ID
        section in the Common Radio Frequency Interface Encodings
        Annex."
     ::= { docsQosServiceFlowSidClusterEntry 1 }

docsQosServiceFlowSidClusterUcid OBJECT-TYPE
     SYNTAX      Unsigned32 (1..255)
     MAX-ACCESS  not-accessible
     STATUS      current
     DESCRIPTION
        "This key represents the upstream channel ID mapped
        to the corresponding SID."
     ::= { docsQosServiceFlowSidClusterEntry 2 }

docsQosServiceFlowSidClusterSid OBJECT-TYPE
     SYNTAX      Unsigned32 (1..16383)
     MAX-ACCESS  read-only
     STATUS      current
     DESCRIPTION
        "This attribute represents the SID assigned to the
        upstream channel in this SID Cluster."
     ::= { docsQosServiceFlowSidClusterEntry 3 }

docsQosGrpServiceFlowTable OBJECT-TYPE
     SYNTAX      SEQUENCE OF DocsQosGrpServiceFlowEntry
     MAX-ACCESS  not-accessible
     STATUS      current
     DESCRIPTION
        "This object provides extensions to the service flow
        information for Group Service Flows (GSFs)."
     REFERENCE
        "DOCSIS 3.0 MAC and Upper Layer Protocols Interface
        Specification CM-SP-MULPIv3.0-I08-080522, QoS Support
        for Joined IP Multicast Traffic section."
     ::= { docsQosMibObjects 13}

docsQosGrpServiceFlowEntry OBJECT-TYPE
     SYNTAX      DocsQosGrpServiceFlowEntry
     MAX-ACCESS  not-accessible
     STATUS      current
     DESCRIPTION
        "The conceptual row of docsQosGrpServiceFlowTable.
        The ifIndex key corresponds to the MAC Domain interface
        of the group service flow."
     INDEX { ifIndex,
             docsQosServiceFlowId
           }
     ::= { docsQosGrpServiceFlowTable 1 }

DocsQosGrpServiceFlowEntry ::= SEQUENCE {
     docsQosGrpServiceFlowIsDef
                  TruthValue,
     docsQosGrpServiceFlowQosConfigId
                  Unsigned32,
     docsQosGrpServiceFlowNumSess
                  Unsigned32,
     docsQosGrpServiceFlowSrcAddr
                  InetAddress,
     docsQosGrpServiceFlowGrpAddr
                  InetAddress,
     docsQosGrpServiceFlowAddrType
                  InetAddressType
     }

docsQosGrpServiceFlowIsDef OBJECT-TYPE
     SYNTAX      TruthValue
     MAX-ACCESS  read-only
     STATUS      current
     DESCRIPTION
        "This attribute indicates whether the GSF QOS Parameter
        Set corresponds to the Default Group Service Flow."
     REFERENCE
        "DOCSIS 3.0 Operations Support System Interface Specification
        CM-SP-OSSIv3.0-I07-080522, Multicast Requirements Annex."
     ::= { docsQosGrpServiceFlowEntry 1 }

docsQosGrpServiceFlowQosConfigId OBJECT-TYPE
     SYNTAX      Unsigned32 (0..65535)
     MAX-ACCESS  read-only
     STATUS      current
     DESCRIPTION
        "This attribute indicates the Group QoS Configuration
        (GQC) identifier used of the creation of this GSF.
        The value zero indicates that the Service Flow is using
        the default service flow."
     REFERENCE
        "DOCSIS 3.0 Operations Support System Interface Specification
        CM-SP-OSSIv3.0-I07-080522, Multicast Requirements Annex."
     ::= { docsQosGrpServiceFlowEntry 2 }

docsQosGrpServiceFlowNumSess OBJECT-TYPE
     SYNTAX      Unsigned32 (1..65535)
     UNITS       "sessions"
     MAX-ACCESS  read-only
     STATUS      current
     DESCRIPTION
        "This attribute indicates the number of sessions that
        are configured in an aggregated Service Flow.  If
        this is a single session replication, the value of this
        attribute is 1."
     REFERENCE
        "DOCSIS 3.0 Operations Support System Interface Specification
        CM-SP-OSSIv3.0-I07-080522, Multicast Requirements Annex."
     ::= { docsQosGrpServiceFlowEntry 3 }

docsQosGrpServiceFlowSrcAddr OBJECT-TYPE
     SYNTAX      InetAddress
     MAX-ACCESS  read-only
     STATUS      current
     DESCRIPTION
        "This attribute specifies the specific multicast Source Address
         that is configured in a single session Service Flow. If this
         is an aggregate Service Flow (NumSess attribute reports a value
         greater than 1) this attribute returns one of the multicast
         source addresses for the session.  For the case of Any Source
         Multicast (ASM), this attribute reports a value of 0.0.0.0 for
         IPv4 or 0::/0 for IPv6."
     ::= { docsQosGrpServiceFlowEntry 4 }

docsQosGrpServiceFlowGrpAddr OBJECT-TYPE
     SYNTAX      InetAddress
     MAX-ACCESS  read-only
     STATUS      current
     DESCRIPTION
        "This attribute specifies the specific Multicast Group Address
         that is configured in a single session Service Flow. If this
         is an aggregate Service Flow (NumSess attribute reports a value
         greater than 1) this attribute returns the multicast group
         address associated with the SrcAddr for the session."
     ::= { docsQosGrpServiceFlowEntry 5 }

docsQosGrpServiceFlowAddrType OBJECT-TYPE
     SYNTAX      InetAddressType
     MAX-ACCESS  read-only
     STATUS      current
     DESCRIPTION
        "This attribute indicates the type of the Internet
        address for ServiceFlowSrcAddr and ServiceFlowGrpAddr."
     ::= { docsQosGrpServiceFlowEntry 6 }

docsQosGrpPktClassTable OBJECT-TYPE
     SYNTAX      SEQUENCE OF DocsQosGrpPktClassEntry
     MAX-ACCESS  not-accessible
     STATUS      current
     DESCRIPTION
        "This object provides additional packet classification
        information for Group Classifier References
        (GCRs) in a Group Service Flow (GSF)."
     REFERENCE
        "DOCSIS 3.0 MAC and Upper Layer Protocols Interface
        Specification CM-SP-MULPIv3.0-I08-080522, QoS Support for
        Joined IP Multicast Traffic section."
     ::= { docsQosMibObjects 14}

docsQosGrpPktClassEntry OBJECT-TYPE
     SYNTAX      DocsQosGrpPktClassEntry
     MAX-ACCESS  not-accessible
     STATUS      current
     DESCRIPTION
        "The conceptual row of docsQosGrpPktClassTable.
        The ifIndex key corresponds to the MAC Domain interface of the
        service flow of this group classifier."
     INDEX { ifIndex,
             docsQosServiceFlowId,
             docsQosPktClassId
           }
     ::= { docsQosGrpPktClassTable 1 }

DocsQosGrpPktClassEntry ::= SEQUENCE {
     docsQosGrpPktClassGrpConfigId
                  Unsigned32
     }

docsQosGrpPktClassGrpConfigId OBJECT-TYPE
     SYNTAX      Unsigned32 (1..4294967295)
     MAX-ACCESS  read-only
     STATUS      current
     DESCRIPTION
        "This attribute indicates the GC identifier used of
        the creation of this GSF."
     REFERENCE
        "DOCSIS 3.0 Operations Support System Interface Specification
        CM-SP-OSSIv3.0-I07-080522, Multicast Requirements Annex."
     ::= { docsQosGrpPktClassEntry 1 }

docsQosUpChCounterExtTable OBJECT-TYPE
     SYNTAX      SEQUENCE OF DocsQosUpChCounterExtEntry
     MAX-ACCESS  not-accessible
     STATUS      current
     DESCRIPTION
        "This object provides extensions for service flow
        statistics for fragmentation for channel bonding."
     REFERENCE
        "DOCSIS 3.0 MAC and Upper Layer Protocols Interface
        Specification CM-SP-MULPIv3.0-I08-080522, Channel
        Bonding section."
     ::= { docsQosMibObjects 15}

docsQosUpChCounterExtEntry OBJECT-TYPE
     SYNTAX      DocsQosUpChCounterExtEntry
     MAX-ACCESS  not-accessible
     STATUS      current
     DESCRIPTION
        "The conceptual row of docsQosUpChCounterExtTable.
        The ifIndex key corresponds to the upstream Channel Interface
        of the service flow."
     INDEX { ifIndex }
     ::= { docsQosUpChCounterExtTable 1 }

DocsQosUpChCounterExtEntry ::= SEQUENCE {
     docsQosUpChCounterExtSgmtValids
                  Counter32,
     docsQosUpChCounterExtSgmtDiscards
                  Counter32
     }

docsQosUpChCounterExtSgmtValids OBJECT-TYPE
     SYNTAX      Counter32
     UNITS       "segments"
     MAX-ACCESS  read-only
     STATUS      current
     DESCRIPTION
        "This attribute represents the total number segments
        processed on this channel. Discontinuities in the
        value of this counter can occur at reinitialization
        of the managed system, and at other times as indicated
        by the value of ifCounterDiscontinuityTime of the
        associated MAC Domain interface index."
     REFERENCE
        "DOCSIS 3.0 MAC and Upper Layer Protocols Interface
        Specification CM-SP-MULPIv3.0-I08-080522, Upstream and
        Downstream Common Aspects section; [RFC 2863]."
     ::= { docsQosUpChCounterExtEntry 1 }

docsQosUpChCounterExtSgmtDiscards OBJECT-TYPE
     SYNTAX      Counter32
     UNITS       "segments"
     MAX-ACCESS  read-only
     STATUS      current
     DESCRIPTION
        "This attribute represents the total number of discarded
        segments on this channel due to segment HCS problems.
        Discontinuities in the value of this counter
        can occur at reinitialization of the managed system,
        and at other times as indicated by the value of
        ifCounterDiscontinuityTime of the associated MAC Domain
        interface index."
     REFERENCE
        "DOCSIS 3.0 MAC and Upper Layer Protocols Interface
        Specification CM-SP-MULPIv3.0-I08-080522, Continuous
        Concatenation and Fragmentation section;[RFC 2863]."
     ::= { docsQosUpChCounterExtEntry 2 }

docsQosServiceFlowCcfStatsTable OBJECT-TYPE
     SYNTAX      SEQUENCE OF DocsQosServiceFlowCcfStatsEntry
     MAX-ACCESS  not-accessible
     STATUS      current
     DESCRIPTION
        "This object provides upstream service flow statistics
        for Continuous Concatenation and Fragmentation
        (CCF).
        The CMTS may choose to not instantiate this object for service flows
        that do not use CCF or return a zero value for the individual
        counter statistics."
     REFERENCE
        "DOCSIS 3.0 MAC and Upper Layer Protocols Interface
        Specification CM-SP-MULPIv3.0-I08-080522, Continuous
        Concatenation and Fragmentation section."
     ::= { docsQosMibObjects 16}

docsQosServiceFlowCcfStatsEntry OBJECT-TYPE
     SYNTAX      DocsQosServiceFlowCcfStatsEntry
     MAX-ACCESS  not-accessible
     STATUS      current
     DESCRIPTION
        "The conceptual row of docsQosServiceFlowCcfStatsTable.
        The ifIndex key corresponds to the MAC Domain interface
        of the service flow."
     INDEX { ifIndex,
             docsQosServiceFlowId
           }
     ::= { docsQosServiceFlowCcfStatsTable 1 }

DocsQosServiceFlowCcfStatsEntry ::= SEQUENCE {
     docsQosServiceFlowCcfStatsSgmtValids
                  Counter32,
     docsQosServiceFlowCcfStatsSgmtLost
                  Counter32
     }

docsQosServiceFlowCcfStatsSgmtValids OBJECT-TYPE
     SYNTAX      Counter32
     UNITS       "segments"
     MAX-ACCESS  read-only
     STATUS      current
     DESCRIPTION
        "This attribute contains the number of segments counted
        on this service flow regardless of whether the
        fragment was correctly reassembled into valid packets.
        This attribute only gathers information for Segment
        Header On service flows. Discontinuities in the value of this
        counter can occur at reinitialization of the managed system,
        and other times as indicated by the value of
        ifCounterDiscontinuityTime of the associated MAC Domain
        interface index."
     REFERENCE
        "DOCSIS 3.0 MAC and Upper Layer Protocols Interface
        Specification CM-SP-MULPIv3.0-I08-080522, Continuous
        Concatenation and Fragmentation section; [RFC 2863]."
     ::= { docsQosServiceFlowCcfStatsEntry 1 }

docsQosServiceFlowCcfStatsSgmtLost OBJECT-TYPE
     SYNTAX      Counter32
     UNITS       "segments"
     MAX-ACCESS  read-only
     STATUS      current
     DESCRIPTION
        "This attribute counts the number of segments which
        the CMTS segment reassembly function determines were
        lost. This attribute only gathers information for Segment
        Header On service flows. Discontinuities in the value of this
        counter can occur at reinitialization of the managed system,
        and at other times as indicated by the value of
        ifCounterDiscontinuityTime of the associated MAC Domain
        interface index."
     REFERENCE
        "DOCSIS 3.0 MAC and Upper Layer Protocols Interface
        Specification CM-SP-MULPIv3.0-I08-080522, Continuous
        Concatenation and Fragmentation section; [RFC 2863]."
     ::= { docsQosServiceFlowCcfStatsEntry 2 }

docsQosCmServiceUsStatsTable OBJECT-TYPE
     SYNTAX      SEQUENCE OF DocsQosCmServiceUsStatsEntry
     MAX-ACCESS  not-accessible
     STATUS      current
     DESCRIPTION
        "This object defines DOCSIS MAC services primitive
        statistics of upstream service flows. In pre-3.0 DOCSIS
        devices this statistics exists per SID for either
        Cos or Qos services in the SNMP table docsIfCmServiceTable.

        A 3.0 CM with CoS configuration (DOCSIS 1.0 mode) reports
        the statistics defined in the SNMP table docsIfCmServiceTable.
        A 3.0 CM with QoS configuration reports
        this object regardless of whether Multiple Transmit
        Channel is enabled or disabled."
     REFERENCE
        "DOCSIS 3.0 MAC and Upper Layer Protocols Interface
        Specification CM-SP-MULPIv3.0-I08-080522, Upstream Data
        Transmission section."
     ::= { docsQosMibObjects 17}

docsQosCmServiceUsStatsEntry OBJECT-TYPE
     SYNTAX      DocsQosCmServiceUsStatsEntry
     MAX-ACCESS  not-accessible
     STATUS      current
     DESCRIPTION
        "The conceptual row of docsQosCmServiceUsStatsTable.
        The ifIndex key corresponds to the MAC Domain interface
        of the service flow."
     INDEX { ifIndex,
             docsQosServiceFlowId
           }
     ::= { docsQosCmServiceUsStatsTable 1 }

DocsQosCmServiceUsStatsEntry ::= SEQUENCE {
     docsQosCmServiceUsStatsTxSlotsImmed
                  Counter32,
     docsQosCmServiceUsStatsTxSlotsDed
                  Counter32,
     docsQosCmServiceUsStatsTxRetries
                  Counter32,
     docsQosCmServiceUsStatsTxExceededs
                  Counter32,
     docsQosCmServiceUsStatsRqRetries
                  Counter32,
     docsQosCmServiceUsStatsRqExceededs
                  Counter32,
     docsQosCmServiceUsStatsSgmts
                  Counter32
     }

docsQosCmServiceUsStatsTxSlotsImmed OBJECT-TYPE
     SYNTAX      Counter32
     UNITS       "mini-slots"
     MAX-ACCESS  read-only
     STATUS      current
     DESCRIPTION
        "This attribute contains the number of upstream mini-slots
        which have been used to transmit data PDUs in
        immediate (contention) mode. This includes only those
        PDUs that are presumed to have arrived at the head-end
        (i.e., those which were explicitly acknowledged.)
        It does not include retransmission attempts or
        mini-slots used by Requests.  Discontinuities in the
        value of this counter can occur at reinitialization
        of the managed system, and at other times as indicated
        by the value of ifCounterDiscontinuityTime of the
        associated MAC Domain interface index."
     REFERENCE
        "DOCSIS 3.0 MAC and Upper Layer Protocols Interface
        Specification CM-SP-MULPIv3.0-I08-080522, Upstream
        Bandwidth Allocation section; [RFC 2863]."
     ::= { docsQosCmServiceUsStatsEntry 1 }

docsQosCmServiceUsStatsTxSlotsDed OBJECT-TYPE
     SYNTAX      Counter32
     UNITS       "mini-slots"
     MAX-ACCESS  read-only
     STATUS      current
     DESCRIPTION
        "This attribute contains the number of upstream mini-slots
        which have been used to transmit data PDUs in
        dedicated mode (i.e., as a result of a unicast Data Grant).
        Discontinuities in the value of this counter
        can occur at reinitialization of the managed system,
        and at other times as indicated by the value of
        ifCounterDiscontinuityTime of the associated MAC Domain
        interface index."
     REFERENCE
        "DOCSIS 3.0 MAC and Upper Layer Protocols Interface
        Specification CM-SP-MULPIv3.0-I08-080522, Upstream Data
        Transmission section; [RFC 2863]."
     ::= { docsQosCmServiceUsStatsEntry 2 }

docsQosCmServiceUsStatsTxRetries OBJECT-TYPE
     SYNTAX      Counter32
     UNITS       "attempts"
     MAX-ACCESS  read-only
     STATUS      current
     DESCRIPTION
        "This attribute contains the number of attempts to
        transmit data PDUs containing requests for acknowledgment
        that did not result in acknowledgment. Discontinuities
        in the value of this counter can occur at
        reinitialization of the managed system, and at other
        times as indicated by the value of ifCounterDiscontinuityTime
        for the associated MAC Domain interface
        index."
     REFERENCE
        "DOCSIS 3.0 MAC and Upper Layer Protocols Interface
        Specification CM-SP-MULPIv3.0-I08-080522, Upstream Bandwidth
        Allocation section; [RFC 2863]."
     ::= { docsQosCmServiceUsStatsEntry 3 }

docsQosCmServiceUsStatsTxExceededs OBJECT-TYPE
     SYNTAX      Counter32
     UNITS       "attempts"
     MAX-ACCESS  read-only
     STATUS      current
     DESCRIPTION
        "This attribute contains the number of attempts to
        transmit bandwidth requests which did not result in
        acknowledgment. Discontinuities in the value of this
        counter can occur at reinitialization of the managed
        system, and at other times as indicated by the value
        of ifCounterDiscontinuityTime of the associated
        MAC Domain interface index."
     REFERENCE
        "DOCSIS 3.0 MAC and Upper Layer Protocols Interface
        Specification CM-SP-MULPIv3.0-I08-080522, Upstream Bandwidth
        Allocation section; [RFC 2863]."
     ::= { docsQosCmServiceUsStatsEntry 4 }

docsQosCmServiceUsStatsRqRetries OBJECT-TYPE
     SYNTAX      Counter32
     UNITS       "attempts"
     MAX-ACCESS  read-only
     STATUS      current
     DESCRIPTION
        "This attribute contains the number of attempts to
        transmit bandwidth requests which did not result in
        acknowledgment. Discontinuities in the value of this
        counter can occur at reinitialization of the managed
        system, and at other times as indicated by the value
        of ifCounterDiscontinuityTime of the associated
        MAC Domain interface index."
     REFERENCE
        "DOCSIS 3.0 MAC and Upper Layer Protocols Interface
        Specification CM-SP-MULPIv3.0-I08-080522, Upstream
        Bandwidth Allocation section; [RFC 2863]."
     ::= { docsQosCmServiceUsStatsEntry 5 }

docsQosCmServiceUsStatsRqExceededs OBJECT-TYPE
     SYNTAX      Counter32
     UNITS       "attempts"
     MAX-ACCESS  read-only
     STATUS      current
     DESCRIPTION
        "This attribute contains the number of requests for
        bandwidth which failed due to excessive retries without
        acknowledgment. Discontinuities in the value
        of this counter can occur at reinitialization of the
        managed system, and at other times as indicated by the
        value of ifCounterDiscontinuityTime of the associated
        MAC Domain interface index."
     REFERENCE
        "DOCSIS 3.0 MAC and Upper Layer Protocols Interface
        Specification CM-SP-MULPIv3.0-I08-080522, Upstream Bandwidth
        Allocation section; [RFC 2863]."
     ::= { docsQosCmServiceUsStatsEntry 6 }

docsQosCmServiceUsStatsSgmts OBJECT-TYPE
     SYNTAX      Counter32
     UNITS       "segments"
     MAX-ACCESS  read-only
     STATUS      current
     DESCRIPTION
        "This attribute contains the number of segments sent
        on this service flow. Discontinuities in the value
        of this counter can occur at reinitialization of the
        managed system, and at other times as indicated by the
        value of ifCounterDiscontinuityTime of the associated
        MAC Domain interface index."
     REFERENCE
        "DOCSIS 3.0 MAC and Upper Layer Protocols Interface
        Specification CM-SP-MULPIv3.0-I08-080522, Upstream and
        Downstream Common Aspects section; RFC 2863."
     ::= { docsQosCmServiceUsStatsEntry 7 }

docsQosCmtsDsidTable OBJECT-TYPE
     SYNTAX      SEQUENCE OF DocsQosCmtsDsidEntry
     MAX-ACCESS  not-accessible
     STATUS      current
     DESCRIPTION
        "This object describes DSID information stored in
        the CMTS.
        The CMTS reports the current status of existing DSIDs.
        When a DSID is created during the registration process
        or a DBC transaction, a corresponding object instance
        is created.   If a DSID is deleted or changed via
        a DBC message the corresponding object instance is deleted
        or updated respectively."
     ::= { docsQosMibObjects 18}

docsQosCmtsDsidEntry OBJECT-TYPE
     SYNTAX      DocsQosCmtsDsidEntry
     MAX-ACCESS  not-accessible
     STATUS      current
     DESCRIPTION
        "The conceptual row of docsQosCmtsDsidTable.
        The ifIndex key corresponds to the MAC Domain interface
        of the DSID."
     INDEX { ifIndex,
             docsQosCmtsDsidDsid
           }
     ::= { docsQosCmtsDsidTable 1 }

DocsQosCmtsDsidEntry ::= SEQUENCE {
     docsQosCmtsDsidDsid
                  Dsid,
     docsQosCmtsDsidUsage
                  BITS,
     docsQosCmtsDsidDsChSet
                  ChSetId,
     docsQosCmtsDsidReseqWaitTime
                  Unsigned32,
     docsQosCmtsDsidReseqWarnThrshld
                  Unsigned32,
     docsQosCmtsDsidStatusHldoffTimerSeqOutOfRng
                  Unsigned32,
     docsQosCmtsDsidCurrentSeqNum
                  Unsigned32
     }

docsQosCmtsDsidDsid OBJECT-TYPE
     SYNTAX      Dsid
     MAX-ACCESS  not-accessible
     STATUS      current
     DESCRIPTION
        "This key represents the DSID."
     ::= { docsQosCmtsDsidEntry 1 }

docsQosCmtsDsidUsage OBJECT-TYPE
     SYNTAX      BITS {

                        resequencing(0),
                        multicastCapable(1),
                        multicastReplication(2),
                        bonding(3)
                      }
     MAX-ACCESS  read-only
     STATUS      current
     DESCRIPTION
        "This attribute indicates the properties of the DSID.
        The bits are defined as follows:
        'resequencing' This bit is set to 1 for a Resequencing
        DSID.
        'multicastCapable'  This bit is set to 1 for a DSID that
        is capable of transporting multicast traffic (i.e.,
        the DSID has multicast forwarding attributes).
        'multicastReplication' This bit is set to 1 for a DSID
        that is used for transporting a multicast replication
        (i.e., there is a corresponding instance of the MulticastRepl
        object).
        'bonding' This bit is set to a 1 for a DSID that is associated
        with a bonding group."
     REFERENCE
        "DOCSIS 3.0 Operations Support System Interface Specification
        CM-SP-OSSIv3.0-I07-080522, Multicast Requirements Annex.
        DOCSIS 3.0 MAC and Upper Layer Protocols Interface
        Specification CM-SP-MULPIv3.0-I08-080522, DSID Encodings section
        in the Common Radio Frequency Interface Encodings Annex."
     ::= { docsQosCmtsDsidEntry 2 }

docsQosCmtsDsidDsChSet OBJECT-TYPE
     SYNTAX      ChSetId
     MAX-ACCESS  read-only
     STATUS      current
     DESCRIPTION
        "This attribute represents the Downstream Channel
        Set over which the DSID is being resequenced."
     ::= { docsQosCmtsDsidEntry 3 }

docsQosCmtsDsidReseqWaitTime OBJECT-TYPE
     SYNTAX      Unsigned32 (0|1..180)
     UNITS       "hundredMicroseconds"
     MAX-ACCESS  read-only
     STATUS      current
     DESCRIPTION
        "This attribute represents the DSID Resequencing
        Wait Time that is used for this DSID. This attribute is
        only valid when the Usage attribute has the resequencing
        bit set to 1. This attribute returns a value of 0
        when the Usage attribute has the resequencing bit set
        to 0."
     ::= { docsQosCmtsDsidEntry 4 }

docsQosCmtsDsidReseqWarnThrshld OBJECT-TYPE
     SYNTAX      Unsigned32 (0..179)
     UNITS       "hundredMicroseconds"
     MAX-ACCESS  read-only
     STATUS      current
     DESCRIPTION
        "This attribute represents the DSID Resequencing
        Warning Threshold that is used for this DSID. The value
        of 0 indicates that the threshold warnings are disabled.
        This attribute is only valid when the Usage attribute
        has the resequencing bit set to 1. This attribute
        returns a value of 0 when the Usage attribute has
        the resequencing bit set to 0."
     ::= { docsQosCmtsDsidEntry 5 }

docsQosCmtsDsidStatusHldoffTimerSeqOutOfRng OBJECT-TYPE
     SYNTAX      Unsigned32 (0..65535)
     UNITS       "20milliseconds"
     MAX-ACCESS  read-only
     STATUS      current
     DESCRIPTION
        "This attribute represents the hold-off timer for
        reporting Out-of-Range Events via the CM-STATUS MAC
        Management message. This attribute is only valid when
        the Usage attribute has the resequencing bit set
        to 1. This attribute returns a value of 0 when the Usage
        attribute has the resequencing bit set to 0."
     ::= { docsQosCmtsDsidEntry 6 }

docsQosCmtsDsidCurrentSeqNum OBJECT-TYPE
     SYNTAX      Unsigned32 (0..65535)
     MAX-ACCESS  read-only
     STATUS      current
     DESCRIPTION
        "This attribute reports the value of the most recent
        sequence number assigned by the CMTS for this DSID.
        This attribute is only valid when the Usage attribute
        has the resequencing bit set to 1. This attribute returns
        a value of 0 when the Usage attribute has the resequencing
        bit set to 0."
     ::= { docsQosCmtsDsidEntry 7 }

docsQosCmtsDebugDsidTable OBJECT-TYPE
     SYNTAX      SEQUENCE OF DocsQosCmtsDebugDsidEntry
     MAX-ACCESS  not-accessible
     STATUS      current
     DESCRIPTION
        "The CMTS Debug DSID object contains the control of
        DSID debug statistics reporting
        An instance in this object defines the DSID and MAC domain
        to which the CmtsDebugDsidStats collects statistics
        for the downstream channel associated with that
        DSID and MAC Domain. The deletion of an instance stops
        the reporting of statistics for the specified DSID.

        This object supports instance creation and deletion.

        The CMTS MUST support at least one instance of this object."
     ::= { docsQosMibObjects 19}

docsQosCmtsDebugDsidEntry OBJECT-TYPE
     SYNTAX      DocsQosCmtsDebugDsidEntry
     MAX-ACCESS  not-accessible
     STATUS      current
     DESCRIPTION
        "The conceptual row of docsQosCmtsDebugDsidTable.
        The ifIndex key corresponds to the MAC Domain interface
        of the DSID."
     INDEX { ifIndex,
             docsQosCmtsDebugDsidDsid
           }
     ::= { docsQosCmtsDebugDsidTable 1 }

DocsQosCmtsDebugDsidEntry ::= SEQUENCE {
     docsQosCmtsDebugDsidDsid
                  Dsid,
     docsQosCmtsDebugDsidRowStatus
                  RowStatus
     }

docsQosCmtsDebugDsidDsid OBJECT-TYPE
     SYNTAX      Dsid
     MAX-ACCESS  not-accessible
     STATUS      current
     DESCRIPTION
        "This attribute represents the DSID value to be debugged,
        identified by the IfIndex attribute of this object."
     ::= { docsQosCmtsDebugDsidEntry 1 }

docsQosCmtsDebugDsidRowStatus OBJECT-TYPE
     SYNTAX      RowStatus
     MAX-ACCESS  read-create
     STATUS      current
     DESCRIPTION
        "The conceptual row status of this object."
     ::= { docsQosCmtsDebugDsidEntry 2 }

docsQosCmtsDebugDsidStatsTable OBJECT-TYPE
     SYNTAX      SEQUENCE OF DocsQosCmtsDebugDsidStatsEntry
     MAX-ACCESS  not-accessible
     STATUS      current
     DESCRIPTION
        "The CMTS Debug DSID Stats object describes statistics
        at the CMTS for the forwarding of DSID-labeled downstream
        packets.
        The CMTS creates an instance for every combination of
        MAC Domain, DSID value, and downstream channel on which
        packets labeled with that DSID are transmitted.
        The CMTS does not delete such instances while the corresponding
        CmtsDebug object control instance exists."
     ::= { docsQosMibObjects 20}

docsQosCmtsDebugDsidStatsEntry OBJECT-TYPE
     SYNTAX      DocsQosCmtsDebugDsidStatsEntry
     MAX-ACCESS  not-accessible
     STATUS      current
     DESCRIPTION
        "The conceptual row of docsQosCmtsDebugDsidStatsTable.
        The ifIndex key corresponds to the MAC Domain interface
        of the DSID."
     INDEX { ifIndex,
             docsQosCmtsDebugDsidDsid,
             docsQosCmtsDebugDsidStatsDsIfIndex
           }
     ::= { docsQosCmtsDebugDsidStatsTable 1 }

DocsQosCmtsDebugDsidStatsEntry ::= SEQUENCE {
     docsQosCmtsDebugDsidStatsDsIfIndex
                  InterfaceIndex,
     docsQosCmtsDebugDsidStatsDsidPackets
                  Counter64,
     docsQosCmtsDebugDsidStatsDsidOctets
                  Counter64
     }

docsQosCmtsDebugDsidStatsDsIfIndex OBJECT-TYPE
     SYNTAX      InterfaceIndex
     MAX-ACCESS  not-accessible
     STATUS      current
     DESCRIPTION
        "This key represents an interface index of a downstream
        channel that belongs to the DSID"
     ::= { docsQosCmtsDebugDsidStatsEntry 1 }

docsQosCmtsDebugDsidStatsDsidPackets OBJECT-TYPE
     SYNTAX      Counter64
     UNITS       "packets"
     MAX-ACCESS  read-only
     STATUS      current
     DESCRIPTION
        "This attribute is a counter which contains the number
        of packets transmitted by the CMTS which are labeled
        with the DSID on the downstream channel. Discontinuities in
        the value of this counter can occur as indicated by the value
        of ifCounterDiscontinuityTime of the associated Downstream
        interface index."
     ::= { docsQosCmtsDebugDsidStatsEntry 2 }

docsQosCmtsDebugDsidStatsDsidOctets OBJECT-TYPE
     SYNTAX      Counter64
     UNITS       "octets"
     MAX-ACCESS  read-only
     STATUS      current
     DESCRIPTION
        "This attribute counts the number of bytes transmitted
        by the CMTS which are labeled with the DSID on the
        downstream interface. Discontinuities in the value of
        this counter can occur as indicated by the value of
        ifCounterDiscontinuityTime of the associated Downstream
        interface index."
     ::= { docsQosCmtsDebugDsidStatsEntry 3 }

docsQosCmDsidTable OBJECT-TYPE
     SYNTAX      SEQUENCE OF DocsQosCmDsidEntry
     MAX-ACCESS  not-accessible
     STATUS      current
     DESCRIPTION
        "When a DSID is created, during the registration process
        or a DBC transaction,. The CM reports the current
        status of existing DSID, for example, if a DSID  is deleted
        or changed via DBC messages the corresponding
        object instance is deleted or updated respectively."
     ::= { docsQosMibObjects 21}

docsQosCmDsidEntry OBJECT-TYPE
     SYNTAX      DocsQosCmDsidEntry
     MAX-ACCESS  not-accessible
     STATUS      current
     DESCRIPTION
        "The conceptual row of docsQosCmDsidTable
        The ifIndex key corresponds to the MAC Domain interface
        of the DSID."
     INDEX { ifIndex,
             docsQosCmDsidDsid
           }
     ::= { docsQosCmDsidTable 1 }

DocsQosCmDsidEntry ::= SEQUENCE {
     docsQosCmDsidDsid
                  Dsid,
     docsQosCmDsidUsage
                  BITS,
     docsQosCmDsidNumReseqChs
                  Unsigned32,
     docsQosCmDsidReseqChList
                  OCTET STRING,
     docsQosCmDsidReseqWaitTime
                  Unsigned32,
     docsQosCmDsidReseqWarnThrshld
                  Unsigned32,
     docsQosCmDsidStatusHldoffTimerSeqOutOfRng
                  Unsigned32,
     docsQosCmDsidOutOfRangeDiscards
                  Unsigned32,
     docsQosCmDsidNextExpectedSeqNum
                  Unsigned32,
     docsQosCmDsidCmInterfaceMask
                  DocsL2vpnIfList,
     docsQosCmDsidFwdCmInterfaceMask
                  DocsL2vpnIfList
     }

docsQosCmDsidDsid OBJECT-TYPE
     SYNTAX      Dsid
     MAX-ACCESS  not-accessible
     STATUS      current
     DESCRIPTION
        "This key represents the DSID."
     ::= { docsQosCmDsidEntry 1 }

docsQosCmDsidUsage OBJECT-TYPE
     SYNTAX      BITS {

                        resequencing(0),
                        multicastCapable(1)
                      }
     MAX-ACCESS  read-only
     STATUS      current
     DESCRIPTION
        "This attribute indicates the properties of the DSID.
        The bits are defined as follows:
        'resequencing' :  This bit is set to 1 for a Resequencing
        DSID.
        'multicastCapable' :  This bit is set to 1 for a DSID that
        is capable of transporting multicast traffic (e.g.,
        the DSID has multicast forwarding attributes)."
     ::= { docsQosCmDsidEntry 2 }

docsQosCmDsidNumReseqChs OBJECT-TYPE
     SYNTAX      Unsigned32 (0 | 1..65535)
     MAX-ACCESS  read-only
     STATUS      current
     DESCRIPTION
        "This attribute represents the number of channels
        in the downstream resequencing channel list for this
        DSID. When a DSID is used only for a non-bonded
        Multicast replication, this object returns a value of 0."
     ::= { docsQosCmDsidEntry 3 }

docsQosCmDsidReseqChList OBJECT-TYPE
     SYNTAX      OCTET STRING (SIZE (0 | 2..255))
     MAX-ACCESS  read-only
     STATUS      current
     DESCRIPTION
        "This attribute represents the Downstream Channel
        Set over which the DSID is being resequenced."
     ::= { docsQosCmDsidEntry 4 }

docsQosCmDsidReseqWaitTime OBJECT-TYPE
     SYNTAX      Unsigned32 (0 | 1..180)
     UNITS       "hundredMicroseconds"
     MAX-ACCESS  read-only
     STATUS      current
     DESCRIPTION
        "This attribute represents the DSID Resequencing
        Wait Time that is used for this DSID. This attribute is
        only valid when the Usage attribute has the resequencing
        bit set to 1. This attribute returns a value of 0
        when the Usage attribute has the resequencing bit set
        to 0."
     ::= { docsQosCmDsidEntry 5 }

docsQosCmDsidReseqWarnThrshld OBJECT-TYPE
     SYNTAX      Unsigned32 (0..179)
     UNITS       "hundredMicroseconds"
     MAX-ACCESS  read-only
     STATUS      current
     DESCRIPTION
        "This attribute represents the DSID Resequencing
        Warning Threshold that is used for this DSID. The value
        of 0 indicates that the threshold warnings are disabled.
        This attribute is only valid when the Usage attribute
        has the resequencing bit set to 1. This attribute
        returns a value of 0 when the Usage attribute has
        the resequencing bit set to 0."
     ::= { docsQosCmDsidEntry 6 }

docsQosCmDsidStatusHldoffTimerSeqOutOfRng OBJECT-TYPE
     SYNTAX      Unsigned32 (0..65535)
     UNITS       "20milliseconds"
     MAX-ACCESS  read-only
     STATUS      current
     DESCRIPTION
        "This attribute represents the hold-off timer for
        reporting Out-of-Range Events via the CM-STATUS MAC
        Management message. This attribute is only valid when
        the Usage attribute has the resequencing bit set
        to 1. This attribute returns a value of 0 when the Usage
        attribute has the resequencing bit set to 0."
     ::= { docsQosCmDsidEntry 7 }

docsQosCmDsidOutOfRangeDiscards OBJECT-TYPE
     SYNTAX      Unsigned32 (0..65535)
     MAX-ACCESS  read-only
     STATUS      current
     DESCRIPTION
        "This attribute represents the current count of out-of-range
        packets discarded by the CM for a given resequencing context
        since an in-range packet was received.  When this count exceeds
        1000 and more than two minutes have elapsed since an in-range
        packet was received, the CM will reacquire sequence numbers for
        this resequencing context."
     ::= { docsQosCmDsidEntry 8 }

docsQosCmDsidNextExpectedSeqNum OBJECT-TYPE
     SYNTAX      Unsigned32 (0..65535)
     MAX-ACCESS  read-only
     STATUS      current
     DESCRIPTION
        "This attribute represents the Next Expected Packet
        Sequence Number for a given resequencing context.
        This attribute is only valid when the Usage attribute
        has the resequencing bit set to 1. This attribute returns
        a value of 0 when the Usage attribute has the resequencing
        bit set to 0."
     ::= { docsQosCmDsidEntry 9 }

docsQosCmDsidCmInterfaceMask OBJECT-TYPE
     SYNTAX      DocsL2vpnIfList
     MAX-ACCESS  read-only
     STATUS      current
     DESCRIPTION
        "This attribute represents the bitmap of the interfaces
        communicated to the CM in a Multicast DSID encoding."
     ::= { docsQosCmDsidEntry 10 }

docsQosCmDsidFwdCmInterfaceMask OBJECT-TYPE
     SYNTAX      DocsL2vpnIfList
     MAX-ACCESS  read-only
     STATUS      current
     DESCRIPTION
        "This attribute represents the bitmap of the interfaces
        to which the CM forwards multicast traffic: a logical
        OR of interfaces identified in CmInterfaceMask
        and interfaces associated with the client MAC addresses
        identified in the instances for this DSID."
     ::= { docsQosCmDsidEntry 11 }

docsQosCmDsidStatsTable OBJECT-TYPE
     SYNTAX      SEQUENCE OF DocsQosCmDsidStatsEntry
     MAX-ACCESS  not-accessible
     STATUS      current
     DESCRIPTION
        "This object defines a set of statistics the CM collects
        per Dsid."
     ::= { docsQosMibObjects 22}

docsQosCmDsidStatsEntry OBJECT-TYPE
     SYNTAX      DocsQosCmDsidStatsEntry
     MAX-ACCESS  not-accessible
     STATUS      current
     DESCRIPTION
        "The conceptual row of docsQosCmDsidStatsTable."
     INDEX { docsQosCmDsidStatsDsid }
     ::= { docsQosCmDsidStatsTable 1 }

DocsQosCmDsidStatsEntry ::= SEQUENCE {
     docsQosCmDsidStatsDsid
                  Dsid,
     docsQosCmDsidStatsSeqNumMissing
                  Counter32,
     docsQosCmDsidStatsSkewThreshExceeds
                  Counter32,
     docsQosCmDsidStatsOutOfRangePackets
                  Counter32,
     docsQosCmDsidStatsNumPackets
                  Counter64
     }

docsQosCmDsidStatsDsid OBJECT-TYPE
     SYNTAX      Dsid
     MAX-ACCESS  not-accessible
     STATUS      current
     DESCRIPTION
        "This key represents the interface index of the MAC
        Domain associated with the DSID."
     ::= { docsQosCmDsidStatsEntry 1 }

docsQosCmDsidStatsSeqNumMissing OBJECT-TYPE
     SYNTAX      Counter32
     UNITS       "packets"
     MAX-ACCESS  read-only
     STATUS      current
     DESCRIPTION
        "This attribute counts the number of times the Next Expected
        Packet Sequence Number is declared lost. In this case one or
        more data packets are lost. This is generally caused by
        downstream packet loss."
     REFERENCE
        "DOCSIS 3.0 MAC and Upper Layer Protocols Interface
        Specification CM-SP-MULPIv3.0-I08-080522, Downstream
        Sequencing section."
     ::= { docsQosCmDsidStatsEntry 2 }

docsQosCmDsidStatsSkewThreshExceeds OBJECT-TYPE
     SYNTAX      Counter32
     UNITS       "packets"
     MAX-ACCESS  read-only
     STATUS      current
     DESCRIPTION
        "This attribute counts in-range sequenced packets
        which were successfully received by the CM after a wait
        time longer than the Resequencing Warning Threshold."
     REFERENCE
        "DOCSIS 3.0 MAC and Upper Layer Protocols Interface
        Specification CM-SP-MULPIv3.0-I08-080522, Skew Requirements
        section."
     ::= { docsQosCmDsidStatsEntry 3 }

docsQosCmDsidStatsOutOfRangePackets OBJECT-TYPE
     SYNTAX      Counter32
     UNITS       "packets"
     MAX-ACCESS  read-only
     STATUS      current
     DESCRIPTION
        "This attribute counts the number of packets Counter
        received in a DSID reassembly context where the sequence
        number which is out of range."
     REFERENCE
        "DOCSIS 3.0 MAC and Upper Layer Protocols Interface
        Specification CM-SP-MULPIv3.0-I08-080522, Receive Channels
        section."
     ::= { docsQosCmDsidStatsEntry 4 }

docsQosCmDsidStatsNumPackets OBJECT-TYPE
     SYNTAX      Counter64
     UNITS       "packets"
     MAX-ACCESS  read-only
     STATUS      current
     DESCRIPTION
        "This attribute counts the total number of data packets
        of a DSID context forwarded for further processing."
     ::= { docsQosCmDsidStatsEntry 5 }

docsQosCmDsidClientTable OBJECT-TYPE
     SYNTAX      SEQUENCE OF DocsQosCmDsidClientEntry
     MAX-ACCESS  not-accessible
     STATUS      current
     DESCRIPTION
        "This object contains the client MAC addresses that
        the CMTS requests that the CM uses to replicate Multicast
        DSIDs during registration or during a DBC transaction.

        When a DSID is created that includes client MAC addresses,
        or when client MAC addresses are added to a DSID,
        new rows are created to indicate the added client MAC
        addresses. When a Client MAC address is deleted from
        a DSID, the corresponding row is deleted.  When a DSID
        is deleted, all corresponding rows are deleted, too."
     REFERENCE
        "DOCSIS 3.0 MAC and Upper Layer Protocols Interface
        Specification CM-SP-MULPIv3.0-I08-080522, DSID Encodings
        section in the Common Radio Frequency Interface Encodings
        Annex."
     ::= { docsQosMibObjects 23}

docsQosCmDsidClientEntry OBJECT-TYPE
     SYNTAX      DocsQosCmDsidClientEntry
     MAX-ACCESS  not-accessible
     STATUS      current
     DESCRIPTION
        "The conceptual row of docsQosCmDsidClientTable."
     INDEX { docsQosCmDsidClientDsid,
             docsQosCmDsidClientClientMacId
           }
     ::= { docsQosCmDsidClientTable 1 }

DocsQosCmDsidClientEntry ::= SEQUENCE {
     docsQosCmDsidClientDsid
                  Dsid,
     docsQosCmDsidClientClientMacId
                  Unsigned32,
     docsQosCmDsidClientClientMacAddr
                  MacAddress
     }

docsQosCmDsidClientDsid OBJECT-TYPE
     SYNTAX      Dsid
     MAX-ACCESS  not-accessible
     STATUS      current
     DESCRIPTION
        "This key defines the DSID that the client MAC addresses
        are associated with."
     ::= { docsQosCmDsidClientEntry 1 }

docsQosCmDsidClientClientMacId OBJECT-TYPE
     SYNTAX      Unsigned32 (1..65535)
     MAX-ACCESS  not-accessible
     STATUS      current
     DESCRIPTION
        "This key defines a uniquely identified Client Mac
        Addresses associated with the DSID."
     ::= { docsQosCmDsidClientEntry 2 }

docsQosCmDsidClientClientMacAddr OBJECT-TYPE
     SYNTAX      MacAddress
     MAX-ACCESS  read-only
     STATUS      current
     DESCRIPTION
        "This attribute defines a client MAC address to which
        Multicast traffic labeled with this DSID should be
        forwarded."
     ::= { docsQosCmDsidClientEntry 3 }

docsQosCmSystemCfgState OBJECT IDENTIFIER ::= { docsQosMibObjects 24 }

docsQosCmSystemCfgStateAqmUsEnable OBJECT-TYPE
    SYNTAX      TruthValue
    MAX-ACCESS  read-only
    STATUS      current
    DESCRIPTION
        "If this attribute is set to 'false', the CM disables Active
         Queue Management (AQM) on all upstream service flows."
    ::= { docsQosCmSystemCfgState 1 }

docsQosCmSystemCfgStateDefaultUsTargetBuffer OBJECT-TYPE
    SYNTAX      Unsigned32 (0..65535)
    UNITS       "milliseconds"
    MAX-ACCESS  read-only
    STATUS      current
    DESCRIPTION
        "This attribute specifies the default upstream service flow
         target buffer size, in milliseconds, when not specified
         otherwise in service flow TLV encodings."
    REFERENCE
         "DOCSIS 3.1 MAC and Upper Layer Protocols Interface
         Specification CM-SP-MULPIv3.1-I03-140610,
         Default Upstream Target Buffer Configuration Annex."
    ::= { docsQosCmSystemCfgState 2 }

-- ---------------------------------------------------------------------
-- CMTS IATC Profile Stats Table
-- ---------------------------------------------------------------------
docsQosCmtsIatcProfileStatsTable OBJECT-TYPE
     SYNTAX      SEQUENCE OF DocsQosCmtsIatcProfileStatsEntry
     MAX-ACCESS  not-accessible
     STATUS      current
     DESCRIPTION
        "This object provides IATC statistics on a per profile basis.
         The IATC Profile statistics are associated with a DOCSIS
         channel or bonding group and one or more Service Flows.
         The CMTS is not required to persist instances of this object
         across reinitializations."
     REFERENCE
        "DOCSIS 3.1 MAC and Upper Layer Protocols Interface
        Specification CM-SP-MULPIv3.1-I08-151210, IATC Profiles
        section."
     ::= { docsQosMibObjects 25}

docsQosCmtsIatcProfileStatsEntry OBJECT-TYPE
     SYNTAX      DocsQosCmtsIatcProfileStatsEntry
     MAX-ACCESS  not-accessible
     STATUS      current
     DESCRIPTION
        "The conceptual row of docsQosCmtsIatcProfileStatsTable."
     INDEX { docsQosCmtsIatcProfileStatsName
           }
     ::= { docsQosCmtsIatcProfileStatsTable 1 }

DocsQosCmtsIatcProfileStatsEntry ::= SEQUENCE {
     docsQosCmtsIatcProfileStatsName
                  SnmpAdminString,
     docsQosCmtsIatcProfileStatsIfIndex
                  Unsigned32,
     docsQosCmtsIatcProfileStatsDirection
                  IfDirection,
     docsQosCmtsIatcProfileStatsPkts
                  Counter64,
     docsQosCmtsIatcProfileStatsOctets
                  Counter64,
     docsQosCmtsIatcProfileStatsPolicedDropPkts
                  Counter64,
     docsQosCmtsIatcProfileStatsPolicedDelayPkts
                  Counter64
     }

docsQosCmtsIatcProfileStatsName OBJECT-TYPE
     SYNTAX      SnmpAdminString
     MAX-ACCESS  not-accessible
     STATUS      current
     DESCRIPTION
        "This key represents the IATC Profile to which this instance
         applies."
     ::= { docsQosCmtsIatcProfileStatsEntry 1 }

docsQosCmtsIatcProfileStatsIfIndex OBJECT-TYPE
     SYNTAX      Unsigned32
     MAX-ACCESS  read-only
     STATUS      current
     DESCRIPTION
        "This attribute represents the index, such as the ifIndex,
         of the DOCSIS channel or the index of the bonding group to
         which this instance applies."
     ::= { docsQosCmtsIatcProfileStatsEntry 2 }

docsQosCmtsIatcProfileStatsDirection OBJECT-TYPE
     SYNTAX      IfDirection
     MAX-ACCESS  read-only
     STATUS      current
     DESCRIPTION
        "This attribute indicates the direction to which the IATC
         Profile is applied."
     ::= { docsQosCmtsIatcProfileStatsEntry 3 }

docsQosCmtsIatcProfileStatsPkts OBJECT-TYPE
     SYNTAX      Counter64
     UNITS       "Packets"
     MAX-ACCESS  read-only
     STATUS      current
     DESCRIPTION
        "This attribute counts the number of Packet Data PDUs forwarded
         to this IATC Profile."
     ::= { docsQosCmtsIatcProfileStatsEntry 4 }

docsQosCmtsIatcProfileStatsOctets OBJECT-TYPE
     SYNTAX      Counter64
     UNITS       "Octets"
     MAX-ACCESS  read-only
     STATUS      current
     DESCRIPTION
        "This attribute counts the number of octets forwarded to this
         IATC Profile."
     ::= { docsQosCmtsIatcProfileStatsEntry 5 }

docsQosCmtsIatcProfileStatsPolicedDropPkts OBJECT-TYPE
     SYNTAX      Counter64
     UNITS       "Packets"
     MAX-ACCESS  read-only
     STATUS      current
     DESCRIPTION
        "This attribute counts the number of dropped Packet Data PDUs
         classified to this IATC Profile."
     ::= { docsQosCmtsIatcProfileStatsEntry 6 }

docsQosCmtsIatcProfileStatsPolicedDelayPkts OBJECT-TYPE
     SYNTAX      Counter64
     UNITS       "Packets"
     MAX-ACCESS  read-only
     STATUS      current
     DESCRIPTION
        "This attribute counts the number of delayed Packet Data PDUs
         classified to this IATC Profile."
     ::= { docsQosCmtsIatcProfileStatsEntry 7 }


-- ---------------------------------------------------------------------
-- Aggregate Service Flow Table
-- ---------------------------------------------------------------------

docsQosAggregateServiceFlowTable OBJECT-TYPE
     SYNTAX      SEQUENCE OF DocsQosAggregateServiceFlowEntry
     MAX-ACCESS  not-accessible
     STATUS      current
     DESCRIPTION
        "This table describes the  attributes for an aggregate service 
		 Flow (ASF). It contains an entry for every active ASF in each MAC Domain."
     REFERENCE
        "DOCSIS 3.1 MAC and Upper Layer Protocols Interface
        Specification CM-SP-MULPIv3.1-I17, Common Upstream
        and Downstream Quality-of-Service Parameter Encodings."
     ::= { docsQosMibObjects 26}

docsQosAggregateServiceFlowEntry OBJECT-TYPE
     SYNTAX      DocsQosAggregateServiceFlowEntry
     MAX-ACCESS  not-accessible
     STATUS      current
     DESCRIPTION
        "The conceptual row of docsQosAggregateServiceFlowTable.
         The ifIndex key corresponds to the MAC Domain interface of the
         aggregate service flow."
     INDEX { ifIndex,
             docsQosAggregateServiceFlowId
           }
     ::= { docsQosAggregateServiceFlowTable 1 }

DocsQosAggregateServiceFlowEntry ::= SEQUENCE {
     docsQosAggregateServiceFlowId
                  Unsigned32,
     docsQosAggregateServiceFlowDirection
                  IfDirection,
     docsQosAggregateServiceFlowPriority
                  Unsigned32,
     docsQosAggregateServiceFlowMaxAggregateTrafficRate
                  BitRate,
     docsQosAggregateServiceFlowMaxTrafficBurst
                  Unsigned32,
     docsQosAggregateServiceFlowMinReservedRate
                  BitRate,
     docsQosAggregateServiceFlowMinReservedPkt
                  Unsigned32,
     docsQosAggregateServiceFlowPeakTrafficRate
                  BitRate,
     docsQosAggregateServiceFlowDataRateUnitSetting
                  DataRateUnitType,
     docsQosAggregateServiceFlowLowLatencyAsf
                  TruthValue,
     docsQosAggregateServiceFlowLowLatencySfId
                  Unsigned32,
     docsQosAggregateServiceFlowClassicSfScn
                  SnmpAdminString,
     docsQosAggregateServiceFlowLowLatencySfScn
                  SnmpAdminString,
     docsQosAggregateServiceFlowAqmCouplingFactor
                  Unsigned32,
     docsQosAggregateServiceFlowSchedulingWeight
                  Unsigned32,
     docsQosAggregateServiceFlowQpEnable
                  BITS,
     docsQosAggregateServiceFlowQpLatencyThreshold
                  Unsigned32,
     docsQosAggregateServiceFlowQpQueuingScoreThreshold
                  Unsigned32,
     docsQosAggregateServiceFlowQpDrainRateExponent
                  Unsigned32,
     docsQosAggregateServiceFlowHCMaxAggregateTrafficRate
                  CounterBasedGauge64,
     docsQosAggregateServiceFlowHCMinReservedRate
                  CounterBasedGauge64,
     docsQosAggregateServiceFlowHCPeakTrafficRate
                  CounterBasedGauge64        
     }

docsQosAggregateServiceFlowId OBJECT-TYPE
     SYNTAX      Unsigned32 (1..4294967295)
     MAX-ACCESS  not-accessible
     STATUS      current
     DESCRIPTION
        "This key represents an identifier assigned to an Aggregate Service
        Flow by the CMTS within a MAC Domain."
     ::= { docsQosAggregateServiceFlowEntry 1 }

docsQosAggregateServiceFlowDirection OBJECT-TYPE
     SYNTAX      IfDirection
     MAX-ACCESS  read-only
     STATUS      current
     DESCRIPTION
        "This attribute indicates the direction
        for the of the Aggregate Service Flow."
      ::= { docsQosAggregateServiceFlowEntry 2 }

docsQosAggregateServiceFlowPriority OBJECT-TYPE
     SYNTAX      Unsigned32 (0..7)
     MAX-ACCESS  read-only
     STATUS      current
     DESCRIPTION
        "This attribute indicates the relative priority of the 
		 Aggregate Service Flow. It represents the sum of the 
		 traffic rate for the Classic Service flow and Aggregate 
		 Service Flow."
     ::= { docsQosAggregateServiceFlowEntry 3 }

docsQosAggregateServiceFlowMaxAggregateTrafficRate OBJECT-TYPE
     SYNTAX      BitRate
     UNITS       "bps"
     MAX-ACCESS  read-only
     STATUS      current
     DESCRIPTION
        "This attribute represents the 4-byte value of the maximum
        sustained traffic rate in bits/sec allowed for this 
        Aggregate Service Flow. This attribute will also return 0
        if DataRateUnitSetting is set to a non-default value 
        (e.g., kbps, mbps or gbps) and the resulting value cannot
        be represented in 32 bits, in which case 
        HCMaxAggregateTrafficRate should be utilized."
     ::= { docsQosAggregateServiceFlowEntry 4 }

docsQosAggregateServiceFlowMaxTrafficBurst OBJECT-TYPE
     SYNTAX      Unsigned32
     MAX-ACCESS  read-only
     STATUS      current
     DESCRIPTION
        "This attribute represents the token bucket size in bytes for 
         this parameter set. The value is calculated from the byte 
         following the MAC header HCS to the end of the CRC. 
         This object is applied in conjunction with MaxTrafficRate to 
         calculate maximum sustained traffic rate the token bucket 
         size B (in bytes) for this Service Flow or an Aggregate Service Flow."
     ::= { docsQosAggregateServiceFlowEntry 5 }

docsQosAggregateServiceFlowMinReservedRate OBJECT-TYPE
     SYNTAX      BitRate
     MAX-ACCESS  read-only
     STATUS      current
     DESCRIPTION
        "This attribute represents the 4-byte value of  guaranteed minimum 
        rate in bits/sec allowed for this Aggregate Service Flow. 
        This attribute will also return 0 if DataRateUnitSetting is 
        set to a non-default value (e.g., kbps, mbps or gbps) and the
        resulting value cannot be represented in 32 bits, in which case
        HCMinReservedRate should be utilized."
     ::= { docsQosAggregateServiceFlowEntry 6}

docsQosAggregateServiceFlowMinReservedPkt OBJECT-TYPE
     SYNTAX      Unsigned32 (0..65535)
     UNITS       "bytes"
     MAX-ACCESS  read-only
     STATUS      current
     DESCRIPTION
        "This attribute represents Assumed Minimum Reserved 
          Rate Packet Size for the Aggregate Service Flow."
     ::= { docsQosAggregateServiceFlowEntry 7 }

docsQosAggregateServiceFlowPeakTrafficRate OBJECT-TYPE
     SYNTAX      BitRate
     UNITS       "bps"
     MAX-ACCESS  read-only
     STATUS      current
     DESCRIPTION
        "This attribute represents the 4-byte value of the Peak Traffic Rate
         allowed for this Aggregate Service Flow. 
         This attribute will also return 0 if DataRateUnitSetting is set
         to a non-default value (e.g., kbps, mbps or gbps) and the 
         resulting value cannot be represented in 32 bits, in which
         case HCPeakTrafficRate should be utilized."
     ::= { docsQosAggregateServiceFlowEntry 8 }

docsQosAggregateServiceFlowDataRateUnitSetting OBJECT-TYPE
     SYNTAX      DataRateUnitType
     MAX-ACCESS  read-only
     STATUS      current
     DESCRIPTION
        "This attribute indicates the base unit for the 
        AggregateServiceFlow traffic rate attributes Maximum
        Aggregate Traffic Rate (MaxAggregateTrafficRate), 
        Minimum Reserved Traffic Rate (MinReservedRate), 
        and Peak Traffic Rate (PeakTrafficeRate). The value
        of this attribute allows for their interpretation in
        units of bps, kbps, mbps or gbps. The default value 
        for DataRateUnitSetting is bits per second (0)."
     DEFVAL { 0 }
     ::= { docsQosAggregateServiceFlowEntry 9 }

docsQosAggregateServiceFlowLowLatencyAsf OBJECT-TYPE
     SYNTAX      TruthValue
     MAX-ACCESS  read-only
     STATUS      current
     DESCRIPTION
        "This attribute indicates whether this ASF is a Low Latency ASF.
		 This implies the ASF is describing a Dual Queue SF setup 
		 underneath the ASF"
     ::= { docsQosAggregateServiceFlowEntry 10 }


docsQosAggregateServiceFlowLowLatencySfId OBJECT-TYPE
     SYNTAX      Unsigned32
     MAX-ACCESS  read-only
     STATUS      current
     DESCRIPTION
        "This attribute represents which of the Individual Service Flows
         within this Aggregate Service Flow is the Low Latency Service 
         Flow. For an Aggregate Service Flow, the CM configuration file
         can indicate which of the constituent service flows will act as 
         the Low Latency queue the Service Class Name of the Low
         Latency Service flow in this ASF. "
     ::= { docsQosAggregateServiceFlowEntry 11 }


docsQosAggregateServiceFlowClassicSfScn OBJECT-TYPE
     SYNTAX      SnmpAdminString
     MAX-ACCESS  read-only
     STATUS      current
     DESCRIPTION
        "This attribute represents the Service Class Name that was 
         used to instantiate the Classic Service Flow by the CMTS.
         This attribute may not be known by the CM, and could report
         an empty string."
     ::= { docsQosAggregateServiceFlowEntry 12 }

docsQosAggregateServiceFlowLowLatencySfScn OBJECT-TYPE
     SYNTAX      SnmpAdminString
     MAX-ACCESS  read-only
     STATUS      current
     DESCRIPTION
        "This attribute represents the Service Class Name that was 
         used to instantiate the Low Latency Service Flow by the CMTS.
         This attribute may not be known by the CM, and could report
         an empty string."
     ::= { docsQosAggregateServiceFlowEntry 13 }

docsQosAggregateServiceFlowAqmCouplingFactor OBJECT-TYPE
     SYNTAX      Unsigned32 (1..255)
     MAX-ACCESS  read-only
     STATUS      current
     DESCRIPTION
        "This attribute represents the coupling factor for the AQMs 
         between the Classic Service Flow and the Low Latency Service Flow. "
     ::= { docsQosAggregateServiceFlowEntry 14 }

docsQosAggregateServiceFlowSchedulingWeight OBJECT-TYPE
     SYNTAX      Unsigned32 (1..255)
     MAX-ACCESS  read-only
     STATUS      current
     DESCRIPTION
        "This attribute indicates the amount of scheduling weight the
        CMTS assigns to the Low Latency Service Flow of the ASF out of
        a total weight of 256, whereas the rest is assigned to the
        Classic Service Flow, when Weighted Rounded Robin scheduling or
        Weighted scheduling is used between the two SFs."
     ::= { docsQosAggregateServiceFlowEntry 15 }

docsQosAggregateServiceFlowQpEnable OBJECT-TYPE
     SYNTAX      BITS {
                       queueProtectionEnabled(0),
                       queueProtectionPerFlow(1)
                      }
     MAX-ACCESS  read-only
     STATUS      current
     DESCRIPTION
        "This attribute indicates the configured Queue Protection status
        of this Aggregated Service Flow.
        Queue Protection is enabled if 'queueProtectionEnabled' bit set
        to '1'. If set to '0' Queue protection is disabled.
        Queue Protection mechanism is per flow if set to '1'.  If set
        to '0' Queue Protection is per packet."
     ::= { docsQosAggregateServiceFlowEntry 16 }

docsQosAggregateServiceFlowQpLatencyThreshold OBJECT-TYPE
     SYNTAX      Unsigned32 (0..65535)
     UNITS       "microseconds"
     MAX-ACCESS  read-only
     STATUS      current
     DESCRIPTION
        "This attribute indicates the latency threshold for the
        Queue Protection function in the Latency Queue."
     REFERENCE
        "DOCSIS 3.1 MAC and Upper Layer Protocols Interface
        Specification CM-SP-MULPIv3.1-I13-181213, Queue Protection
        Section."
	 DEFVAL {1000}
     ::= { docsQosAggregateServiceFlowEntry 17 }

docsQosAggregateServiceFlowQpQueuingScoreThreshold OBJECT-TYPE
     SYNTAX      Unsigned32 (0..65535)
     UNITS       "microseconds"
     MAX-ACCESS  read-only
     STATUS      current
     DESCRIPTION
        "This attribute represents Queuing Score Threshold for the
          Queue Protection function in the Latency Queue."
     REFERENCE
        "DOCSIS 3.1 MAC and Upper Layer Protocols Interface
        Specification CM-SP-MULPIv3.1-I13-181213, General Service Flow
        Encodings."
	 DEFVAL {2000}
     ::= { docsQosAggregateServiceFlowEntry 18 }

docsQosAggregateServiceFlowQpDrainRateExponent OBJECT-TYPE
     SYNTAX      Unsigned32 (0..255)
	 UNITS       "log2(bytes/second)"
     MAX-ACCESS  read-only
     STATUS      current
     DESCRIPTION
        "This attribute represents the drain rate exponent for the Queue
          Protection function in the Low Latency Service Flow.  The drain
          rate of the queuing score is expressed as an exponent of 2, in bytes/sec,
          e.g. a value of 17 means the Queue Protection function will use a value
          of  2^17 bytes/sec."
     REFERENCE
        "DOCSIS 3.1 MAC and Upper Layer Protocols Interface
        Specification CM-SP-MULPIv3.1-I13-181213, General Service Flow
        Encodings."
     ::= { docsQosAggregateServiceFlowEntry 19 }
     
docsQosAggregateServiceFlowHCMaxAggregateTrafficRate OBJECT-TYPE
     SYNTAX      CounterBasedGauge64
     UNITS       "bps"
     MAX-ACCESS  read-only
     STATUS      current
     DESCRIPTION
        "This attribute is a 64-bit representation of the maximum
        sustained traffic rate in bits/sec allowed for this Aggregate
        Service Flow. It represents the sum of the traffic rate for 
        the Classic Service flow and Aggregate Service Flow."
     REFERENCE
        "DOCSIS 3.1 MAC and Upper Layer Protocols Interface
        Specification CM-SP-MULPIv3.1-I13-181213, General Service Flow
        Encodings."
     ::= { docsQosAggregateServiceFlowEntry 20 }
     
docsQosAggregateServiceFlowHCMinReservedRate OBJECT-TYPE
     SYNTAX      CounterBasedGauge64
     UNITS       "bps"
     MAX-ACCESS  read-only
     STATUS      current
     DESCRIPTION
        "This attribute is a 64-bit representation of the 
        guaranteed minimum rate in bits/sec allowed for this
        Aggregate Service Flow."
     REFERENCE
        "DOCSIS 3.1 MAC and Upper Layer Protocols Interface
        Specification CM-SP-MULPIv3.1-I13-181213, General Service Flow
        Encodings."
     ::= { docsQosAggregateServiceFlowEntry 21 }
     
docsQosAggregateServiceFlowHCPeakTrafficRate OBJECT-TYPE
     SYNTAX      CounterBasedGauge64
     UNITS       "bps"
     MAX-ACCESS  read-only
     STATUS      current
     DESCRIPTION
        "This attribute is a 64-bit representation of the 
        Peak traffic Rate in bits/sec for this Aggregate 
        Service Flow. A value of 0 means the peak traffic
        rate is not limited."
     REFERENCE
        "DOCSIS 3.1 MAC and Upper Layer Protocols Interface
        Specification CM-SP-MULPIv3.1-I13-181213, General Service Flow
        Encodings."
     ::= { docsQosAggregateServiceFlowEntry 22 }
     
     

-- ---------------------------------------------------------------------
-- Aggregate Service Flow Stats Table
-- ---------------------------------------------------------------------

docsQosAggregateServiceFlowStatsTable OBJECT-TYPE
     SYNTAX      SEQUENCE OF DocsQosAggregateServiceFlowStatsEntry
     MAX-ACCESS  not-accessible
     STATUS      current
     DESCRIPTION
        "This object describes statistics associated with
        the Service Flows in a managed device. The CMTS MUST
		create an instance of AggregateServiceFlowStats for 
		every ASF instantiated in the MAC Domain."
     ::= { docsQosMibObjects 27}

docsQosAggregateServiceFlowStatsEntry OBJECT-TYPE
     SYNTAX      DocsQosAggregateServiceFlowStatsEntry
     MAX-ACCESS  not-accessible
     STATUS      current
     DESCRIPTION
        "The conceptual row of the docsQosAggregateServiceFlowStatsTable.
        The ifIndex key corresponds to the MAC Domain interface
        of the service flow."
     INDEX { ifIndex,
             docsQosAggregateServiceFlowId
           }
     ::= { docsQosAggregateServiceFlowStatsTable 1 }

DocsQosAggregateServiceFlowStatsEntry ::= SEQUENCE {
     docsQosAggregateServiceFlowStatsPkts
                  Counter64,
     docsQosAggregateServiceFlowStatsOctets
                  Counter64,
     docsQosAggregateServiceFlowStatsTimeCreated
                  TimeStamp,
     docsQosAggregateServiceFlowStatsTimeActive
                  Counter32
     }

docsQosAggregateServiceFlowStatsPkts OBJECT-TYPE
     SYNTAX      Counter64
     UNITS       "packets"
     MAX-ACCESS  read-only
     STATUS      current
     DESCRIPTION
        "This attribute provides the sum of the Packet Data PDUs forwarded
        on the Low Latency and Classic Service Flows aggregated within this
        ASF.

        This counter's last discontinuity is the
        ifCounterDiscontinuityTime for of the associated MAC Domain
        interface index."
     ::= { docsQosAggregateServiceFlowStatsEntry 1 }

docsQosAggregateServiceFlowStatsOctets OBJECT-TYPE
     SYNTAX      Counter64
     UNITS       "bytes"
     MAX-ACCESS  read-only
     STATUS      current
     DESCRIPTION
        "This attribute represents the sum of the number of octets for the
        Low Latency and Classic Service Flows aggregated within this ASF.
        For each packet, the count begins from the byte after the MAC header
        HCS to the end of the CRC"
     ::= { docsQosAggregateServiceFlowStatsEntry 2 }

docsQosAggregateServiceFlowStatsTimeCreated OBJECT-TYPE
     SYNTAX      TimeStamp
     MAX-ACCESS  read-only
     STATUS      current
     DESCRIPTION
        "This attribute indicates the value of sysUpTime when
        the aggregate service flow was created."
     ::= { docsQosAggregateServiceFlowStatsEntry 3 }

docsQosAggregateServiceFlowStatsTimeActive OBJECT-TYPE
     SYNTAX      Counter32
     UNITS       "seconds"
     MAX-ACCESS  read-only
     STATUS      current
     DESCRIPTION
        "This attribute indicates the number of seconds that
        the aggregate service flow has been active.

        This counter's last discontinuity is the
        ifCounterDiscontinuityTime for of the associated MAC Domain
        interface index."
     ::= { docsQosAggregateServiceFlowStatsEntry 4 }

-- ---------------------------------------------------------------------
-- Aggregate Service Flow QOS Profile (AQP) Table
-- ---------------------------------------------------------------------

docsQosAqpTable  OBJECT-TYPE
     SYNTAX      SEQUENCE OF DocsQosAqpEntry
     MAX-ACCESS  not-accessible
     STATUS      current
     DESCRIPTION
        "This object describes a provisioned ASF QoS Profile (AQP)for
        Aggregate Service Flows (ASF) on a CCAP. Each object instance
        defines a template for certain DOCSIS QoS Parameter Set values.
        When an Aggregate Service Flow is created, it may reference an
        AQP Name instead of providing explicit QoS Parameter Set values.
        In this case, the CCAP populates the QoS Parameter Set with the
        applicable corresponding values from the named AQP Name or Service
        Class Name. Subsequent changes to an AQP Name row do not affect
        the QoS Parameter Set values of any service flows already admitted.
        An AQP template applies to only a single direction, as indicated in
        the Direction attribute. An AsfQosProfile for ASF is an equivalent
        to a Service Class for a Service Flow."
     ::= { docsQosMibObjects 28}

docsQosAqpEntry OBJECT-TYPE
     SYNTAX      DocsQosAqpEntry
     MAX-ACCESS  not-accessible
     STATUS      current
     DESCRIPTION
        "The conceptual row of the docsQosAqpTable."
     INDEX { docsQosAqpName }
     ::= { docsQosAqpTable 1 }

DocsQosAqpEntry ::= SEQUENCE {
     docsQosAqpName
                  SnmpAdminString,
     docsQosAqpStatus
                  RowStatus,
     docsQosAqpDirection
                  IfDirection,
     docsQosAqpPriority
                  Unsigned32,
     docsQosAqpMaxAggregateTrafficRate
                  BitRate,
     docsQosAqpMaxTrafficBurst
                  Unsigned32,
     docsQosAqpPeakTrafficRate
                  BitRate,
     docsQosAqpMinReservedRate
                  BitRate,
     docsQosAqpMinReservedPkt
                  Unsigned32,
     docsQosAqpDataRateUnitSetting
                  DataRateUnitType,
     docsQosAqpLowLatencyAsf
                  TruthValue,
     docsQosAqpClassicSfScn
                  SnmpAdminString,
     docsQosAqpLatencySfScn
                  SnmpAdminString,
     docsQosAqpAqmCouplingFactor
                  Unsigned32,
     docsQosAqpSchedulingWeight
                  Unsigned32,
     docsQosAqpQpEnable
                  BITS,
     docsQosAqpQpLatencyThreshold
                  Unsigned32,
     docsQosAqpQpQueuingScoreThreshold
                  Unsigned32,
     docsQosAqpQpDrainRateExponent
                  Unsigned32,
     docsQosAqpLowLatencyClassifierList
                  OCTET STRING
     }

docsQosAqpName OBJECT-TYPE
     SYNTAX      SnmpAdminString (SIZE(0..16))
     MAX-ACCESS  not-accessible
     STATUS      current
     DESCRIPTION
        "This key indicates the ASF QoS Profile Name associated with this
        object instance. DOCSIS specifies that the maximum size is 16 ASCII
        characters including a terminating zero. The terminating zero is not
        represented in this SnmpAdminString syntax attribute."
     ::= { docsQosAqpEntry 1 }

docsQosAqpStatus OBJECT-TYPE
     SYNTAX      RowStatus
     MAX-ACCESS  read-create
     STATUS      current
     DESCRIPTION
        "The conceptual row status of this object."
     ::= { docsQosAqpEntry 2 }

docsQosAqpDirection OBJECT-TYPE
     SYNTAX      IfDirection
     MAX-ACCESS  read-create
     STATUS      current
     DESCRIPTION
        "This attribute is the template for the Direction attribute of
        the AsfQosProfile."
     ::= { docsQosAqpEntry 3 }

docsQosAqpPriority OBJECT-TYPE
     SYNTAX      Unsigned32
     MAX-ACCESS  read-create
     STATUS      current
     DESCRIPTION
        "This attribute is the template for the relative priority of an
        Aggregate Service Flow/ QoS Parameter Set."
      DEFVAL { 0 }
     ::= { docsQosAqpEntry 4 }

docsQosAqpMaxAggregateTrafficRate OBJECT-TYPE
     SYNTAX      BitRate
     UNITS       "bps,kpbs,mbps,or gbps"
     MAX-ACCESS  read-create
     STATUS      current
     DESCRIPTION
        "This attribute is the template for the Maximum Aggregate Traffic
        Rate attribute (maximum sustained traffic rate allowed) for 
        this ASF/Qos Parameter Set.
        This attribute represents the 4 byte value of the maximum 
        aggregate traffic rate allowed for this ASF. All MAC frame 
        data PDUs from the bytes following the MAC header HCS to 
        the end of the CRC are included in calculating the maximum 
        aggregate traffic rate. The number of bytes forwarded is 
        limited during any time interval. The value 0 indicates
        no maximum traffic rate is enforced. The rate is specified 
        in units of bps, kbps, mbps or gbps as specified by the 
        DataRateUnitSetting attribute. This attribute applies to
        both upstream and downstream ASFs. This attribute also 
        returns 0 if the referenced parameter is not present in 
        the corresponding DOCSIS QOS Parameter Set, or if the 
        parameter is not applicable."
      DEFVAL { 0 }
     ::= { docsQosAqpEntry 5 }

docsQosAqpMaxTrafficBurst OBJECT-TYPE
     SYNTAX      Unsigned32
     UNITS       "bytes"
     MAX-ACCESS  read-create
     STATUS      current
     DESCRIPTION
        "This attribute is the template for the MaxTrafficBurst attribute of
        the Aggregate Service Flow/ QoS Parameter Set. If this value is not
        set, the default value is 3044, or 4000 if support for extended packet
        size is enabled."
     ::= { docsQosAqpEntry 6 }

docsQosAqpPeakTrafficRate OBJECT-TYPE
     SYNTAX      BitRate
     UNITS       "bps,kpbs,mbps,or gbps"
     MAX-ACCESS  read-create
     STATUS      current
     DESCRIPTION
        "This attribute is the template for the Peak Traffic Rate allowed for
        this Aggregate Service Flow/QoS Parameter Set. 
        This attribute represents the 4 byte value of the rate parameter 
        'P' of a token-bucket-based peak rate limiter for packets of this
        ASF. A value of 0 means the downstream peak traffic rate is not 
        limited. The rate is specified in units of bps, kbps, mbps or gbps
        as specified by the DataRateUnitSetting attribute. This attribute
        also returns 0 if the referenced parameter is not present in the
        corresponding DOCSIS QOS Parameter Set, or if the parameter is 
        not applicable."
      DEFVAL {0}
     ::= { docsQosAqpEntry 7 }

docsQosAqpMinReservedRate OBJECT-TYPE
     SYNTAX      BitRate
     UNITS       "bps,kbps,mbps,or gbps"
     MAX-ACCESS  read-create
     STATUS      current
     DESCRIPTION
        "This attribute is the template for the MinReservedRate attribute of the
        Aggregate Service Flow/ QoS Parameter Set.
        This attribute represents the 4 byte value of the guaranteed minimum 
        rate allowed for this ASF. The value is calculated from the byte 
        following the MAC header HCS to the end of the CRC. The value 0 
        indicates that no bandwidth is reserved. The rate is specified in 
        units of bps, kbps, mbps or gbps as specified by the 
        DataRateUnitSetting attribute. This attribute also returns 0 if 
        the referenced parameter is not present in the corresponding
        DOCSIS QOS Parameter Set, or if the parameter is not applicable."
      DEFVAL {0}
     ::= { docsQosAqpEntry 8 }

docsQosAqpMinReservedPkt OBJECT-TYPE
     SYNTAX      Unsigned32
     UNITS          "bytes"
     MAX-ACCESS  read-create
     STATUS      current
     DESCRIPTION
        "This attribute is the template for the MinReservedPkt attribute of the
        Aggregate Service Flow/ QoS Parameter Set. The default value is CMTS
        vendor-dependent."
     ::= { docsQosAqpEntry 9 }

docsQosAqpDataRateUnitSetting OBJECT-TYPE
     SYNTAX      DataRateUnitType
     UNITS       "bps"
     MAX-ACCESS  read-create
     STATUS      current
     DESCRIPTION
        "This attribute indicates the base unit for the
        AsfQosProfile traffic rate configuration attributes
        Maximum Aggregate Traffic Rate (MaxAggregateTrafficRate),
        Minimum Reserved Traffic Rate (MinReservedRate), and Peak
        Traffic Rate (PeakTrafficeRate). The value of this attribute
        allows for their interpretation in units of Bps, Kbps, Mbps
        or Gbps. The default value for DataRateUnitSetting is 
        bits per second (bps)."
       DEFVAL { 0 }
     ::= { docsQosAqpEntry 10 }

docsQosAqpLowLatencyAsf OBJECT-TYPE
     SYNTAX      TruthValue
     MAX-ACCESS  read-create
     STATUS      current
     DESCRIPTION
        "This attribute indicates if the Aggregate Service Flow is being used for
        Low Latency services. This implies the ASF is describing a Dual Queue SF
        setup underneath the ASF."
      DEFVAL { true }
     ::= { docsQosAqpEntry 11 }

docsQosAqpClassicSfScn OBJECT-TYPE
     SYNTAX      SnmpAdminString
     MAX-ACCESS  read-create
     STATUS      current
     DESCRIPTION
        "This attribute represents the Service Class Name from which the parameter
        set values for the classic queue will be derived."
     ::= { docsQosAqpEntry 12 }

docsQosAqpLatencySfScn OBJECT-TYPE
     SYNTAX      SnmpAdminString
     MAX-ACCESS  read-create
     STATUS      current
     DESCRIPTION
        "This attribute represents the Service Class Name from which the parameter
        set values for the low latency queue will be derived."
     ::= { docsQosAqpEntry 13 }

docsQosAqpAqmCouplingFactor OBJECT-TYPE
     SYNTAX      Unsigned32 (0..255)
     MAX-ACCESS  read-create
     STATUS      current
     DESCRIPTION
        "This attribute represents the coupling factor for the AQMs
        between the Classic queue and the Latency Queue."
      DEFVAL { 1 }
     ::= { docsQosAqpEntry 14 }

docsQosAqpSchedulingWeight OBJECT-TYPE
     SYNTAX      Unsigned32 (0..255)
     MAX-ACCESS  read-create
     STATUS      current
     DESCRIPTION
        "This attribute represents the scheduling weight, as the implied ratio (out of
        256), for the Latency Queue/Service Flow (within the ASF)."
      DEFVAL { 230 }
     ::= { docsQosAqpEntry 15 }

docsQosAqpQpEnable OBJECT-TYPE
     SYNTAX      BITS {
                       queueProtection(0)
                      }
     MAX-ACCESS  read-create
     STATUS      current
     DESCRIPTION
        "This attribute (Bit 0) indicates if the Queue Protection(QP) functionality is
        enabled or disabled, for the Low Latency Service Flow."
     ::= { docsQosAqpEntry 16 }

docsQosAqpQpLatencyThreshold  OBJECT-TYPE
     SYNTAX      Unsigned32 (0..65535)
     UNITS         "microseconds"
     MAX-ACCESS  read-create
     STATUS      current
     DESCRIPTION
        "This attribute represents the latency threshold for the Queue
        Protection function in the Low Latency Service Flow."
     DEFVAL { 1000 }
     ::= { docsQosAqpEntry 17 }

docsQosAqpQpQueuingScoreThreshold OBJECT-TYPE
     SYNTAX      Unsigned32  (0..65535)
     UNITS         "microseconds"
     MAX-ACCESS  read-create
     STATUS      current
     DESCRIPTION
        "This attribute represents the Queuing Score Threshold for the
        Queue Protection function in the Low Latency Service Flow."
     DEFVAL { 2000 }
     ::= { docsQosAqpEntry 18 }

docsQosAqpQpDrainRateExponent OBJECT-TYPE
     SYNTAX      Unsigned32 (0..255)
     UNITS         "log2(bytes/sec)"
     MAX-ACCESS  read-create
     STATUS      current
     DESCRIPTION
        "This attribute represents the drain rate exponent for the Queue
        Protection function in the Low Latency Service Flow.  The drain
        rate of the queuing score is expressed as an exponent of 2, in
        bytes/sec., e.g., a value of 19 means the Queue Protection function
        will use a value of : 2^19 bytes/sec."
      DEFVAL  { 17 }
     ::= { docsQosAqpEntry 19 }

docsQosAqpLowLatencyClassifierList OBJECT-TYPE
     SYNTAX      OCTET STRING
     MAX-ACCESS  read-create
     STATUS      current
     DESCRIPTION
        "Packet classifiers assigned to the Low Latency service flow. Each
        classifier is encoded in hexBinary according to the TLV encoding.
        When multiple classifiers exist for the same Latency service flow,
        then they are encoded as the concatenated sequence of encodings for
        each classifier. See [MULPIv3.1] Quality-of-Service-Related Encodings
        (in Annex C). Because the TLV encoding for upstream classifiers is
        different than for downstream classifiers, the default value for this
        attribute depends on the value of the Direction attribute.

        This attribute is necessary to differentiate Low Latency Service
        Flow traffic from Classic Service Flow traffic. The minimum size of 
        this attribute is a zero-length octet string, which could occur if the 
        operator deletes the value. If this attribute is not populated, all traffic
        for this ASF would be mapped to the Classic Service Flow.
        No upper limit is defined for the length of this attribute."
     ::= { docsQosAqpEntry 20 }

-- ---------------------------------------------------------------------
-- docsQosSfLatencyHistObjects
-- ---------------------------------------------------------------------

docsQosSfLatencyHistObjects  OBJECT IDENTIFIER ::= { docsQosMibObjects 29 }

docsQosSfLatencyHistCfgTable OBJECT-TYPE
     SYNTAX      SEQUENCE OF DocsQosSfLatencyHistCfgEntry
     MAX-ACCESS  not-accessible
     STATUS      current
     DESCRIPTION
        "This table defines the latency histogram structure for each 
         upstream histogram enabled service flow. The CM/CMTS MUST create 
         an active instance of the SfLatencyHistCfg object for every service flow
		 for which histogram calculation is enabled via the Latency Histogram 
		 Encodings TLV. The activation of an instance of this object enables histogram
         calculation for the indexed service flow. The deactivation or deletion
         of an instance of this object disables histogram calculation for the indexed
         service flow.  The CM/CMTS MUST delete an instance of the SfLatencyHistCfg
		 object if the indexed service flow is deleted (e.g. because of a DSD operation)
		 or the histogram calculation is disabled via the Latency Histogram 
		 Encodings TLV(i.e. because of a DSC operation)."
     REFERENCE
        "DOCSIS 3.1 MAC and Upper Layer Protocols Interface
        Specification CM-SP-MULPIv3.1-I17-190116. Latency Histogram Calcuation
        Section."
     ::= { docsQosSfLatencyHistObjects 1}

docsQosSfLatencyHistCfgEntry OBJECT-TYPE
     SYNTAX      DocsQosSfLatencyHistCfgEntry
     MAX-ACCESS  not-accessible
     STATUS      current
     DESCRIPTION
        "The conceptual row of docsQosSfLatencyHistCfgTable.
         The ifIndex key corresponds to the MAC Domain interface
         of the aggregate service flow."
     INDEX { ifIndex,
             docsQosServiceFlowId
           }
     ::= { docsQosSfLatencyHistCfgTable 1 }

DocsQosSfLatencyHistCfgEntry ::= SEQUENCE {
     docsQosSfLatencyHistCfgStatus
                  RowStatus,
     docsQosSfLatencySfLabel
                  SnmpAdminString,
     docsQosSfLatencyBin1UpperEdge
                  Unsigned32,
     docsQosSfLatencyBin2UpperEdge
                  Unsigned32,
     docsQosSfLatencyBin3UpperEdge
                  Unsigned32,
     docsQosSfLatencyBin4UpperEdge
                  Unsigned32,
     docsQosSfLatencyBin5UpperEdge
                  Unsigned32,
     docsQosSfLatencyBin6UpperEdge
                  Unsigned32,
     docsQosSfLatencyBin7UpperEdge
                  Unsigned32,
     docsQosSfLatencyBin8UpperEdge
                  Unsigned32,
     docsQosSfLatencyBin9UpperEdge
                  Unsigned32,
     docsQosSfLatencyBin10UpperEdge
                  Unsigned32,
     docsQosSfLatencyBin11UpperEdge
                  Unsigned32,
     docsQosSfLatencyBin12UpperEdge
                  Unsigned32,
     docsQosSfLatencyBin13UpperEdge
                  Unsigned32,
     docsQosSfLatencyBin14UpperEdge
                  Unsigned32,
     docsQosSfLatencyBin15UpperEdge
                  Unsigned32,
     docsQosSfLatencyBinEdgeNum
                  Unsigned32
     }

docsQosSfLatencyHistCfgStatus OBJECT-TYPE
     SYNTAX      RowStatus
     MAX-ACCESS  read-create
     STATUS      current
     DESCRIPTION
        "The conceptual row status of this object."
     ::= { docsQosSfLatencyHistCfgEntry 1 }

docsQosSfLatencySfLabel OBJECT-TYPE
     SYNTAX      SnmpAdminString (SIZE(0..15))
     MAX-ACCESS  read-create
     STATUS      current
     DESCRIPTION
        "This attribute represents the Service Class Name or a Label 
        (configured by the operator) to be used in Service Flow Latency
         Performance Reporting. The CMTS SHOULD default this attribute 
		 to the SCN if it's known. If the SCN is not known, the CMTS MUST 
		 default the SfLabel to the value 'unknown'. The Operator can 
		 set this attribute to any string."
       DEFVAL { "unknown" }
     ::= { docsQosSfLatencyHistCfgEntry 2 }

docsQosSfLatencyBin1UpperEdge OBJECT-TYPE
     SYNTAX      Unsigned32
     UNITS       "microseconds"
     MAX-ACCESS  read-create
     STATUS      current
     DESCRIPTION
        "This attribute represents the upper edge of Bin 1.
        The lower edge of this bin is 0-microseconds."
      DEFVAL { 0 }
     ::= { docsQosSfLatencyHistCfgEntry 3 }

docsQosSfLatencyBin2UpperEdge OBJECT-TYPE
     SYNTAX      Unsigned32
     UNITS       "microseconds"
     MAX-ACCESS  read-create
     STATUS      current
     DESCRIPTION
        "This attribute represents the upper edge of Bin 2.
        The lower edge of this bin is the upper edge of the
        previous bin."
      DEFVAL { 0 }
     ::= { docsQosSfLatencyHistCfgEntry 4 }

docsQosSfLatencyBin3UpperEdge OBJECT-TYPE
     SYNTAX      Unsigned32
     UNITS       "microseconds"
     MAX-ACCESS  read-create
     STATUS      current
     DESCRIPTION
        "This attribute represents the upper edge of Bin 3.
        The lower edge of this bin is the upper edge of the
        previous bin."
      DEFVAL { 0 }
     ::= { docsQosSfLatencyHistCfgEntry 5 }

docsQosSfLatencyBin4UpperEdge OBJECT-TYPE
     SYNTAX      Unsigned32
     UNITS       "microseconds"
     MAX-ACCESS  read-create
     STATUS      current
     DESCRIPTION
        "This attribute represents the upper edge of Bin 4.
        The lower edge of this bin is the upper edge of the
        previous bin."
     DEFVAL { 0 }
     ::= { docsQosSfLatencyHistCfgEntry 6 }

docsQosSfLatencyBin5UpperEdge OBJECT-TYPE
     SYNTAX      Unsigned32
     UNITS       "microseconds"
     MAX-ACCESS  read-create
     STATUS      current
     DESCRIPTION
        "This attribute represents the upper edge of Bin 5.
        The lower edge of this bin is the upper edge of the
        previous bin."
      DEFVAL { 0 }
     ::= { docsQosSfLatencyHistCfgEntry 7 }

docsQosSfLatencyBin6UpperEdge OBJECT-TYPE
     SYNTAX      Unsigned32
     UNITS       "microseconds"
     MAX-ACCESS read-create
     STATUS      current
     DESCRIPTION
        "This attribute represents the upper edge of Bin 6.
        The lower edge of this bin is the upper edge of the
        previous bin."
     DEFVAL { 0 }
     ::= { docsQosSfLatencyHistCfgEntry 8 }

docsQosSfLatencyBin7UpperEdge OBJECT-TYPE
     SYNTAX      Unsigned32
     UNITS       "microseconds"
     MAX-ACCESS  read-create
     STATUS      current
     DESCRIPTION
        "This attribute represents the upper edge of Bin 7.
        The lower edge of this bin is the upper edge of the
        previous bin."
     DEFVAL { 0 }
     ::= { docsQosSfLatencyHistCfgEntry 9 }

docsQosSfLatencyBin8UpperEdge OBJECT-TYPE
     SYNTAX      Unsigned32
     UNITS       "microseconds"
     MAX-ACCESS read-create
     STATUS      current
     DESCRIPTION
        "This attribute represents the upper edge of Bin 8.
        The lower edge of this bin is the upper edge of the
        previous bin."
     DEFVAL { 0 }
     ::= { docsQosSfLatencyHistCfgEntry 10 }

docsQosSfLatencyBin9UpperEdge OBJECT-TYPE
     SYNTAX      Unsigned32
     UNITS       "microseconds"
     MAX-ACCESS  read-create
     STATUS      current
     DESCRIPTION
        "This attribute represents the upper edge of Bin 9.
        The lower edge of this bin is the upper edge of the
        previous bin."
     DEFVAL { 0 }
     ::= { docsQosSfLatencyHistCfgEntry 11 }

docsQosSfLatencyBin10UpperEdge OBJECT-TYPE
     SYNTAX      Unsigned32
     UNITS       "microseconds"
     MAX-ACCESS read-create
     STATUS      current
     DESCRIPTION
        "This attribute represents the upper edge of Bin 10.
        The lower edge of this bin is the upper edge of the
        previous bin."
     DEFVAL { 0 }
     ::= { docsQosSfLatencyHistCfgEntry 12 }

docsQosSfLatencyBin11UpperEdge OBJECT-TYPE
     SYNTAX      Unsigned32
     UNITS       "microseconds"
     MAX-ACCESS  read-create
     STATUS      current
     DESCRIPTION
        "This attribute represents the upper edge of Bin 11.
        The lower edge of this bin is the upper edge of the
        previous bin."
      DEFVAL { 0 }
     ::= { docsQosSfLatencyHistCfgEntry 13 }

docsQosSfLatencyBin12UpperEdge OBJECT-TYPE
     SYNTAX      Unsigned32
     UNITS       "microseconds"
     MAX-ACCESS read-create
     STATUS      current
     DESCRIPTION
        "This attribute represents the upper edge of Bin 12.
        The lower edge of this bin is the upper edge of the
        previous bin."
     DEFVAL { 0 }
     ::= { docsQosSfLatencyHistCfgEntry 14 }

docsQosSfLatencyBin13UpperEdge OBJECT-TYPE
     SYNTAX      Unsigned32
     UNITS       "microseconds"
     MAX-ACCESS read-create
     STATUS      current
     DESCRIPTION
        "This attribute represents the upper edge of Bin 13.
        The lower edge of this bin is the upper edge of the
        previous bin."
      DEFVAL { 0 }
     ::= { docsQosSfLatencyHistCfgEntry 15 }

docsQosSfLatencyBin14UpperEdge OBJECT-TYPE
     SYNTAX      Unsigned32
     UNITS       "microseconds"
     MAX-ACCESS  read-create
     STATUS      current
     DESCRIPTION
        "This attribute represents the upper edge of Bin 14.
        The lower edge of this bin is the upper edge of the
        previous bin."
     DEFVAL { 0 }
     ::= { docsQosSfLatencyHistCfgEntry 16 }

docsQosSfLatencyBin15UpperEdge OBJECT-TYPE
     SYNTAX      Unsigned32
     UNITS       "microseconds"
     MAX-ACCESS  read-create
     STATUS      current
     DESCRIPTION
        "This attribute represents the upper edge of Bin 15.
        The lower edge of this bin is the upper edge of the
        previous bin."
      DEFVAL { 0 }
     ::= { docsQosSfLatencyHistCfgEntry 17 }

docsQosSfLatencyBinEdgeNum OBJECT-TYPE
     SYNTAX      Unsigned32 (1..15)
     MAX-ACCESS  read-create
     STATUS      current
     DESCRIPTION
        "This attribute represents the number of consecutive 
          configured upper bin edges. The number of histogram bins 
          is then LatencyBinEdgeNum + 1. "
     ::= { docsQosSfLatencyHistCfgEntry 18 }

docsQosSfLatencyStatsTable OBJECT-TYPE
     SYNTAX      SEQUENCE OF DocsQosSfLatencyStatsEntry
     MAX-ACCESS  not-accessible
     STATUS      current
     DESCRIPTION
        "The SfLatencyStats object entry describes latency
        statistics such as histogram of latencies, Max Latency,
        Number of histogram updates at the CMTS for the down-
        stream service flow. The CMTS MUST create an instance
        of the SfLatencyStats object for every combination of 
		MAC Domain and ServiceFlowId on which latency histogram
		calculation is enabled. The CMTS MUST delete the instance
        of SfLatencyStats when latency histogram
        calculation is disabled for a service flow."
     REFERENCE
        "DOCSIS 3.1 MAC and Upper Layer Protocols Interface
        Specification CM-SP-MULPIv3.1-I17-190116."
     ::= { docsQosSfLatencyHistObjects 2}

docsQosSfLatencyStatsEntry OBJECT-TYPE
     SYNTAX      DocsQosSfLatencyStatsEntry
     MAX-ACCESS  not-accessible
     STATUS      current
     DESCRIPTION
        "The conceptual row of docsQosSfLatencyStatsTable.
         The ifIndex key corresponds to the MAC Domain interface
         of the aggregate service flow."
     INDEX { ifIndex,
             docsQosServiceFlowId
           }
     ::= { docsQosSfLatencyStatsTable 1 }

DocsQosSfLatencyStatsEntry ::= SEQUENCE {
     docsQosSfLatencyMaxLatency
                  Unsigned32,
     docsQosSfLatencyNumHistUpdates
                  Counter64,
     docsQosSfLatencyBin1Pkts
                  Counter64,
     docsQosSfLatencyBin2Pkts
                  Counter64,
     docsQosSfLatencyBin3Pkts
                  Counter64,
     docsQosSfLatencyBin4Pkts
                  Counter64,
     docsQosSfLatencyBin5Pkts
                  Counter64,
     docsQosSfLatencyBin6Pkts
                  Counter64,
     docsQosSfLatencyBin7Pkts
                  Counter64,
     docsQosSfLatencyBin8Pkts
                  Counter64,
     docsQosSfLatencyBin9Pkts
                  Counter64,
     docsQosSfLatencyBin10Pkts
                  Counter64,
     docsQosSfLatencyBin11Pkts
                  Counter64,
     docsQosSfLatencyBin12Pkts
                  Counter64,
     docsQosSfLatencyBin13Pkts
                  Counter64,
     docsQosSfLatencyBin14Pkts
                  Counter64,
     docsQosSfLatencyBin15Pkts
                  Counter64,
     docsQosSfLatencyBin16Pkts
                  Counter64
     }
docsQosSfLatencyMaxLatency OBJECT-TYPE
     SYNTAX      Unsigned32
     UNITS       "microseconds"
     MAX-ACCESS  read-only
     STATUS      current
     DESCRIPTION
        "This attribute represents the maximum latency observed."
     ::= { docsQosSfLatencyStatsEntry 1 }
docsQosSfLatencyNumHistUpdates OBJECT-TYPE
     SYNTAX      Counter64
     MAX-ACCESS  read-only
     STATUS      current
     DESCRIPTION
        "This attribute represents count of updates to the queue latency
         histogram. In cases where a latency estimate is not generated
         for every packet (e.g., subsampling in the case of Low Latency
         Service Flow or estimates every update interval in the case of
         Classic Service Flow) this attribute provides information
         regarding the fidelity of the histogram bin counts"
     ::= { docsQosSfLatencyStatsEntry 2 }

docsQosSfLatencyBin1Pkts OBJECT-TYPE
     SYNTAX      Counter64
     UNITS       "packets"
     MAX-ACCESS  read-only
     STATUS      current
     DESCRIPTION
        "This attribute represents the count of packets with latency that
        fall within this histogram bin."
     ::= { docsQosSfLatencyStatsEntry 3 }

docsQosSfLatencyBin2Pkts OBJECT-TYPE
     SYNTAX      Counter64
     UNITS       "packets"
     MAX-ACCESS  read-only
     STATUS      current
     DESCRIPTION
        "This attribute represents the count of packets with latency that
        fall within this histogram bin."
     ::= { docsQosSfLatencyStatsEntry 4 }

docsQosSfLatencyBin3Pkts OBJECT-TYPE
     SYNTAX      Counter64
     UNITS       "packets"
     MAX-ACCESS  read-only
     STATUS      current
     DESCRIPTION
        "This attribute represents the count of packets with latency that
        fall within this histogram bin."
     ::= { docsQosSfLatencyStatsEntry 5 }

docsQosSfLatencyBin4Pkts OBJECT-TYPE
     SYNTAX      Counter64
     UNITS       "packets"
     MAX-ACCESS  read-only
     STATUS      current
     DESCRIPTION
        "This attribute represents the count of packets with latency that
        fall within this histogram bin."
     ::= { docsQosSfLatencyStatsEntry 6 }

docsQosSfLatencyBin5Pkts OBJECT-TYPE
     SYNTAX      Counter64
     UNITS       "packets"
     MAX-ACCESS  read-only
     STATUS      current
     DESCRIPTION
        "This attribute represents the count of packets with latency that
        fall within this histogram bin."
     ::= { docsQosSfLatencyStatsEntry 7 }

docsQosSfLatencyBin6Pkts OBJECT-TYPE
     SYNTAX      Counter64
     UNITS       "packets"
     MAX-ACCESS  read-only
     STATUS      current
     DESCRIPTION
        "This attribute represents the count of packets with latency that
        fall within this histogram bin."
     ::= { docsQosSfLatencyStatsEntry 8 }

docsQosSfLatencyBin7Pkts OBJECT-TYPE
     SYNTAX      Counter64
     UNITS       "packets"
     MAX-ACCESS  read-only
     STATUS      current
     DESCRIPTION
        "This attribute represents the count of packets with latency that
        fall within this histogram bin."
     ::= { docsQosSfLatencyStatsEntry 9 }

docsQosSfLatencyBin8Pkts OBJECT-TYPE
     SYNTAX      Counter64
     UNITS       "packets"
     MAX-ACCESS  read-only
     STATUS      current
     DESCRIPTION
        "This attribute represents the count of packets with latency that
        fall within this histogram bin."
     ::= { docsQosSfLatencyStatsEntry 10 }

docsQosSfLatencyBin9Pkts OBJECT-TYPE
     SYNTAX      Counter64
     UNITS       "packets"
     MAX-ACCESS  read-only
     STATUS      current
     DESCRIPTION
        "This attribute represents the count of packets with latency that
        fall within this histogram bin."
     ::= { docsQosSfLatencyStatsEntry 11 }

docsQosSfLatencyBin10Pkts OBJECT-TYPE
     SYNTAX      Counter64
     UNITS       "packets"
     MAX-ACCESS  read-only
     STATUS      current
     DESCRIPTION
        "This attribute represents the count of packets with latency that
        fall within this histogram bin."
     ::= { docsQosSfLatencyStatsEntry 12 }

docsQosSfLatencyBin11Pkts OBJECT-TYPE
     SYNTAX      Counter64
     UNITS       "packets"
     MAX-ACCESS  read-only
     STATUS      current
     DESCRIPTION
        "This attribute represents the count of packets with latency that
        fall within this histogram bin."
     ::= { docsQosSfLatencyStatsEntry 13 }

docsQosSfLatencyBin12Pkts OBJECT-TYPE
     SYNTAX      Counter64
     UNITS       "packets"
     MAX-ACCESS  read-only
     STATUS      current
     DESCRIPTION
        "This attribute represents the count of packets with latency that
        fall within this histogram bin."
     ::= { docsQosSfLatencyStatsEntry 14 }

docsQosSfLatencyBin13Pkts OBJECT-TYPE
     SYNTAX      Counter64
     UNITS       "packets"
     MAX-ACCESS  read-only
     STATUS      current
     DESCRIPTION
        "This attribute represents the count of packets with latency that
        fall within this histogram bin."
     ::= { docsQosSfLatencyStatsEntry 15 }

docsQosSfLatencyBin14Pkts OBJECT-TYPE
     SYNTAX      Counter64
     UNITS       "packets"
     MAX-ACCESS  read-only
     STATUS      current
     DESCRIPTION
        "This attribute represents the count of packets with latency that
        fall within this histogram bin."
     ::= { docsQosSfLatencyStatsEntry 16 }

docsQosSfLatencyBin15Pkts OBJECT-TYPE
     SYNTAX      Counter64
     UNITS       "packets"
     MAX-ACCESS  read-only
     STATUS      current
     DESCRIPTION
        "This attribute represents the count of packets with latency that
        fall within this histogram bin."
     ::= { docsQosSfLatencyStatsEntry 17 }

docsQosSfLatencyBin16Pkts OBJECT-TYPE
     SYNTAX      Counter64
     UNITS       "packets"
     MAX-ACCESS  read-only
     STATUS      current
     DESCRIPTION
        "This attribute represents the count of packets with latency that
        fall within this histogram bin."
     ::= { docsQosSfLatencyStatsEntry 18 }

docsQosMibConformance OBJECT IDENTIFIER ::= { docsQosMib 2 }
docsQosMibCompliances OBJECT IDENTIFIER ::= { docsQosMibConformance 1 }
docsQosMibGroups         OBJECT IDENTIFIER ::= { docsQosMibConformance 2 }

docsQosCompliance MODULE-COMPLIANCE
STATUS      current
DESCRIPTION
        "The compliance statement of managed objects common for Cable Modem
        Termination Systems (CMTS) and Cable Modems (CM)."

    MODULE -- this MODULE
    MANDATORY-GROUPS {
     docsQosBaseGroup
     }

    GROUP docsQosCmtsGroup
    DESCRIPTION
        "This group is mandatory for Cable Modem Termination
         Systems (CMTS) and is not implemented for Cable Modems
         (CM)."

    GROUP docsQosCmGroup
    DESCRIPTION
        "This group is mandatory for Cable Modems (CM)TS) and is
         not implemented for Cable Modems Termination Systems (CMTS)."
::= { docsQosMibCompliances 1 }


docsQosDeprecatedCompliance MODULE-COMPLIANCE
   STATUS      deprecated
   DESCRIPTION
        "The compliance statement for deprecated objects."

    MODULE -- this MODULE
    GROUP docsQosDeprecatedGroup
    DESCRIPTION
        "This group contains objects which are deprecated
         from the MIB as of the current release."
::= { docsQosMibCompliances 2 }

docsQosBaseGroup OBJECT-GROUP
    OBJECTS {
     docsQosPktClassDirection,
     docsQosPktClassPriority,
     docsQosPktClassIpTosLow,
     docsQosPktClassIpTosHigh,
     docsQosPktClassIpTosMask,
     docsQosPktClassIpProtocol,
     docsQosPktClassIpSourceAddr,
     docsQosPktClassIpSourceMask,
     docsQosPktClassIpDestAddr,
     docsQosPktClassIpDestMask,
     docsQosPktClassSourcePortStart,
     docsQosPktClassSourcePortEnd,
     docsQosPktClassDestPortStart,
     docsQosPktClassDestPortEnd,
     docsQosPktClassDestMacAddr,
     docsQosPktClassDestMacMask,
     docsQosPktClassSourceMacAddr,
     docsQosPktClassEnetProtocolType,
     docsQosPktClassEnetProtocol,
     docsQosPktClassUserPriLow,
     docsQosPktClassUserPriHigh,
     docsQosPktClassVlanId,
     docsQosPktClassState,
     docsQosPktClassPkts,
     docsQosPktClassBitMap,
     docsQosPktClassIpAddrType,
     docsQosPktClassFlowLabel,
     docsQosPktClassCmInterfaceMask,
     docsQosPktClassIcmpTypeLow,
     docsQosPktClassIcmpTypeHigh,
     docsQosParamSetServiceClassName,
     docsQosParamSetPriority,
     docsQosParamSetMaxTrafficRate,
     docsQosParamSetMaxTrafficBurst,
     docsQosParamSetMinReservedRate,
     docsQosParamSetMinReservedPkt,
     docsQosParamSetActiveTimeout,
     docsQosParamSetAdmittedTimeout,
     docsQosParamSetMaxConcatBurst,
     docsQosParamSetSchedulingType,
     docsQosParamSetNomPollInterval,
     docsQosParamSetTolPollJitter,
     docsQosParamSetUnsolicitGrantSize,
     docsQosParamSetNomGrantInterval,
     docsQosParamSetTolGrantJitter,
     docsQosParamSetGrantsPerInterval,
     docsQosParamSetTosAndMask,
     docsQosParamSetTosOrMask,
     docsQosParamSetMaxLatency,
     docsQosParamSetRequestPolicyOct,
     docsQosParamSetRequiredAttrMask,
     docsQosParamSetForbiddenAttrMask,
     docsQosParamSetAttrAggrRuleMask,
     docsQosParamSetAppId,
     docsQosParamSetMultiplierContentionReqWindow,
     docsQosParamSetMultiplierBytesReq,
     docsQosParamSetPeakTrafficRate,
     docsQosParamSetDsResequencing,
     docsQosParamSetBitMap,
     docsQosParamSetMinimumBuffer,
     docsQosParamSetTargetBuffer,
     docsQosParamSetMaximumBuffer,
     docsQosParamSetAqmDisabled,
     docsQosParamSetAqmLatencyTarget,
     docsQosParamSetHCMaxTrafficRate,
     docsQosParamSetHCMinReservedRate,
     docsQosParamSetHCPeakTrafficRate,
     docsQosParamSetAqmAlgInUse,
     docsQosParamSetGuaranteedGrantInterval,
     docsQosParamSetGuaranteedGrantRate,
     docsQosParamSetGuaranteedRequestInterval,
     docsQosParamSetImmedAqmMaxThreshold,
     docsQosParamSetImmedAqmRangeExponentRampFunc,
     docsQosServiceFlowSID,
     docsQosServiceFlowDirection,
     docsQosServiceFlowPrimary,
     docsQosServiceFlowParamSetTypeStatus,
     docsQosServiceFlowChSetId,
     docsQosServiceFlowAttrAssignSuccess,
     docsQosServiceFlowDsid,
     docsQosServiceFlowMaxReqPerSidCluster,
     docsQosServiceFlowMaxOutstandingBytesPerSidCluster,
     docsQosServiceFlowMaxTotBytesReqPerSidCluster,
     docsQosServiceFlowMaxTimeInSidCluster,
     docsQosServiceFlowBufferSize,
     docsQosServiceFlowPkts,
     docsQosServiceFlowOctets,
     docsQosServiceFlowTimeCreated,
     docsQosServiceFlowTimeActive,
     docsQosServiceFlowPHSUnknowns,
     docsQosServiceFlowPolicedDropPkts,
     docsQosServiceFlowAqmDroppedPkts,
     docsQosServiceFlowSanctionedPkts,
     docsQosServiceFlowPolicedDelayPkts,
     docsQosDSAReqs,
     docsQosDSARsps,
     docsQosDSAAcks,
     docsQosDSCReqs,
     docsQosDSCRsps,
     docsQosDSCAcks,
     docsQosDSDReqs,
     docsQosDSDRsps,
     docsQosDynamicAdds,
     docsQosDynamicAddFails,
     docsQosDynamicChanges,
     docsQosDynamicChangeFails,
     docsQosDynamicDeletes,
     docsQosDynamicDeleteFails,
     docsQosDCCReqs,
     docsQosDCCRsps,
     docsQosDCCAcks,
     docsQosDCCs,
     docsQosDCCFails,
     docsQosDCCRspDeparts,
     docsQosDCCRspArrives,
     docsQosDCCRspDeparts,
     docsQosDCCRspArrives,
     docsQosDbcReqs,
     docsQosDbcRsps,
     docsQosDbcAcks,
     docsQosDbcSuccesses,
     docsQosDbcFails,
     docsQosDbcPartial,
     docsQosServiceFlowSidClusterSid,
     docsQosAggregateServiceFlowDirection,
     docsQosAggregateServiceFlowPriority,
     docsQosAggregateServiceFlowMaxAggregateTrafficRate,
     docsQosAggregateServiceFlowMaxTrafficBurst,
     docsQosAggregateServiceFlowMinReservedRate,
     docsQosAggregateServiceFlowMinReservedPkt,
     docsQosAggregateServiceFlowPeakTrafficRate,
     docsQosAggregateServiceFlowDataRateUnitSetting,
     docsQosAggregateServiceFlowLowLatencyAsf,
     docsQosAggregateServiceFlowLowLatencySfId,
     docsQosAggregateServiceFlowClassicSfScn,
     docsQosAggregateServiceFlowLowLatencySfScn,
     docsQosAggregateServiceFlowAqmCouplingFactor,
     docsQosAggregateServiceFlowSchedulingWeight,
     docsQosAggregateServiceFlowQpEnable,
     docsQosAggregateServiceFlowQpLatencyThreshold,
     docsQosAggregateServiceFlowQpQueuingScoreThreshold,
     docsQosAggregateServiceFlowQpDrainRateExponent,
     docsQosAggregateServiceFlowHCMaxAggregateTrafficRate,
     docsQosAggregateServiceFlowHCMinReservedRate,
     docsQosAggregateServiceFlowHCPeakTrafficRate,
     docsQosAggregateServiceFlowStatsPkts,
     docsQosAggregateServiceFlowStatsOctets,
     docsQosAggregateServiceFlowStatsTimeCreated,
     docsQosAggregateServiceFlowStatsTimeActive,
     docsQosSfLatencyHistCfgStatus,
     docsQosSfLatencySfLabel,
     docsQosSfLatencyBin1UpperEdge,
     docsQosSfLatencyBin2UpperEdge,
     docsQosSfLatencyBin3UpperEdge,
     docsQosSfLatencyBin4UpperEdge,
     docsQosSfLatencyBin5UpperEdge,
     docsQosSfLatencyBin6UpperEdge,
     docsQosSfLatencyBin7UpperEdge,
     docsQosSfLatencyBin8UpperEdge,
     docsQosSfLatencyBin9UpperEdge,
     docsQosSfLatencyBin10UpperEdge,
     docsQosSfLatencyBin11UpperEdge,
     docsQosSfLatencyBin12UpperEdge,
     docsQosSfLatencyBin13UpperEdge,
     docsQosSfLatencyBin14UpperEdge,
     docsQosSfLatencyBin15UpperEdge,
     docsQosSfLatencyBinEdgeNum,
     docsQosSfLatencyMaxLatency,
     docsQosSfLatencyNumHistUpdates,
     docsQosSfLatencyBin1Pkts,
     docsQosSfLatencyBin2Pkts,
     docsQosSfLatencyBin3Pkts,
     docsQosSfLatencyBin4Pkts,
     docsQosSfLatencyBin5Pkts,
     docsQosSfLatencyBin6Pkts,
     docsQosSfLatencyBin7Pkts,
     docsQosSfLatencyBin8Pkts,
     docsQosSfLatencyBin9Pkts,
     docsQosSfLatencyBin10Pkts,
     docsQosSfLatencyBin11Pkts,
     docsQosSfLatencyBin12Pkts,
     docsQosSfLatencyBin13Pkts,
     docsQosSfLatencyBin14Pkts,
     docsQosSfLatencyBin15Pkts,
     docsQosSfLatencyBin16Pkts
     }
    STATUS      current
    DESCRIPTION
       "Group of objects implemented in both CM and CMTS."
    ::= { docsQosMibGroups 1 }

docsQosCmtsGroup OBJECT-GROUP
    OBJECTS {
     docsQosUpstreamFragments,
     docsQosUpstreamFragDiscards,
     docsQosUpstreamConcatBursts,
     docsQosServiceFlowIatcProfileName,
     docsQosServiceFlowAggregateServiceFlowId,
     docsQosServiceFlowLogIfIndex,
     docsQosServiceFlowLogSFID,
     docsQosServiceFlowLogCmMac,
     docsQosServiceFlowLogPkts,
     docsQosServiceFlowLogOctets,
     docsQosServiceFlowLogTimeDeleted,
     docsQosServiceFlowLogTimeCreated,
     docsQosServiceFlowLogTimeActive,
     docsQosServiceFlowLogDirection,
     docsQosServiceFlowLogPrimary,
     docsQosServiceFlowLogServiceClassName,
     docsQosServiceFlowLogPolicedDropPkts,
     docsQosServiceFlowLogPolicedDelayPkts,
     docsQosServiceFlowLogControl,
     docsQosServiceClassStatus,
     docsQosServiceClassPriority,
     docsQosServiceClassMaxTrafficRate,
     docsQosServiceClassMaxTrafficBurst,
     docsQosServiceClassMinReservedRate,
     docsQosServiceClassMinReservedPkt,
     docsQosServiceClassMaxConcatBurst,
     docsQosServiceClassNomPollInterval,
     docsQosServiceClassTolPollJitter,
     docsQosServiceClassUnsolicitGrantSize,
     docsQosServiceClassNomGrantInterval,
     docsQosServiceClassTolGrantJitter,
     docsQosServiceClassGrantsPerInterval,
     docsQosServiceClassMaxLatency,
     docsQosServiceClassActiveTimeout,
     docsQosServiceClassAdmittedTimeout,
     docsQosServiceClassSchedulingType,
     docsQosServiceClassRequestPolicy,
     docsQosServiceClassTosAndMask,
     docsQosServiceClassTosOrMask,
     docsQosServiceClassDirection,
     docsQosServiceClassStorageType,
     docsQosServiceClassDSCPOverwrite,
     docsQosServiceClassRequiredAttrMask,
     docsQosServiceClassForbiddenAttrMask,
     docsQosServiceClassAttrAggrRuleMask,
     docsQosServiceClassAppId,
     docsQosServiceClassMultiplierContentionReqWindow,
     docsQosServiceClassMultiplierBytesReq,
     docsQosServiceClassPeakTrafficRate,
     docsQosServiceClassDsResequencing,
     docsQosServiceClassMinimumBuffer,
     docsQosServiceClassTargetBuffer,
     docsQosServiceClassMaximumBuffer,
     docsQosServiceClassAqmDisabled,
     docsQosServiceClassAqmLatencyTarget,
     docsQosServiceClassGuaranteedGrantInterval,
     docsQosServiceClassGuaranteedGrantRate,
     docsQosServiceClassGuaranteedRequestInterval,
     docsQosServiceClassAqmAlgorithm,
     docsQosServiceClassImmedAqmMaxThreshold,
     docsQosServiceClassImmedAqmRangeExponentRampFunc,
     docsQosServiceClassLatencyHistBinEdges,
     docsQosServiceClassDataRateUnitSetting,
     docsQosCmtsIfIndex,
     docsQosGrpServiceFlowIsDef,
     docsQosGrpServiceFlowQosConfigId,
     docsQosGrpServiceFlowNumSess,
     docsQosGrpServiceFlowSrcAddr,
     docsQosGrpServiceFlowGrpAddr,
     docsQosGrpServiceFlowAddrType,
     docsQosGrpPktClassGrpConfigId,
     docsQosUpChCounterExtSgmtValids,
     docsQosUpChCounterExtSgmtDiscards,
     docsQosServiceFlowCcfStatsSgmtValids,
     docsQosServiceFlowCcfStatsSgmtLost,
     docsQosCmtsDsidUsage,
     docsQosCmtsDsidDsChSet,
     docsQosCmtsDsidReseqWaitTime,
     docsQosCmtsDsidReseqWarnThrshld,
     docsQosCmtsDsidStatusHldoffTimerSeqOutOfRng,
     docsQosCmtsDsidCurrentSeqNum,
     docsQosCmtsDebugDsidRowStatus,
     docsQosCmtsDebugDsidStatsDsidPackets,
     docsQosCmtsDebugDsidStatsDsidOctets,
     docsQosCmtsIatcProfileStatsIfIndex,
     docsQosCmtsIatcProfileStatsDirection,
     docsQosCmtsIatcProfileStatsPkts,
     docsQosCmtsIatcProfileStatsOctets,
     docsQosCmtsIatcProfileStatsPolicedDropPkts,
     docsQosCmtsIatcProfileStatsPolicedDelayPkts,
     docsQosAqpStatus,
     docsQosAqpDirection,
     docsQosAqpPriority,
     docsQosAqpMaxAggregateTrafficRate,
     docsQosAqpMaxTrafficBurst,
     docsQosAqpPeakTrafficRate,
     docsQosAqpMinReservedRate,
     docsQosAqpMinReservedPkt,
     docsQosAqpDataRateUnitSetting,
     docsQosAqpLowLatencyAsf,
     docsQosAqpClassicSfScn,
     docsQosAqpLatencySfScn,
     docsQosAqpAqmCouplingFactor,
     docsQosAqpSchedulingWeight,
     docsQosAqpQpEnable,
     docsQosAqpQpLatencyThreshold,
     docsQosAqpQpQueuingScoreThreshold,
     docsQosAqpQpDrainRateExponent,
     docsQosAqpLowLatencyClassifierList
     }
   STATUS      current
    DESCRIPTION
       "Group of objects implemented in the CMTS only."
    ::= { docsQosMibGroups 2 }

docsQosCmGroup OBJECT-GROUP
    OBJECTS {
     docsQosCmServiceUsStatsTxSlotsImmed,
     docsQosCmServiceUsStatsTxSlotsDed,
     docsQosCmServiceUsStatsTxRetries,
     docsQosCmServiceUsStatsTxExceededs,
     docsQosCmServiceUsStatsRqRetries,
     docsQosCmServiceUsStatsRqExceededs,
     docsQosCmServiceUsStatsSgmts,
     docsQosCmDsidUsage,
     docsQosCmDsidNumReseqChs,
     docsQosCmDsidReseqChList,
     docsQosCmDsidReseqWaitTime,
     docsQosCmDsidReseqWarnThrshld,
     docsQosCmDsidStatusHldoffTimerSeqOutOfRng,
     docsQosCmDsidOutOfRangeDiscards,
     docsQosCmDsidNextExpectedSeqNum,
     docsQosCmDsidCmInterfaceMask,
     docsQosCmDsidFwdCmInterfaceMask,
     docsQosCmDsidStatsSeqNumMissing,
     docsQosCmDsidStatsSkewThreshExceeds,
     docsQosCmDsidStatsOutOfRangePackets,
     docsQosCmDsidStatsNumPackets,
     docsQosCmDsidClientClientMacAddr,
     docsQosCmSystemCfgStateAqmUsEnable,
     docsQosCmSystemCfgStateDefaultUsTargetBuffer
     }
   STATUS      current
    DESCRIPTION
       "Group of objects implemented in the CM only."
    ::= { docsQosMibGroups 3 }

docsQosDeprecatedGroup OBJECT-GROUP
    OBJECTS {
            docsQosParamSetMaxReqPerSidCluster,
            docsQosParamSetMaxOutstandingBytesPerSidCluster,
            docsQosParamSetMaxTotBytesReqPerSidCluster,
            docsQosParamSetMaxTimeInSidCluster,
            docsQosServiceClassMaxReqPerSidCluster,
            docsQosServiceClassMaxOutstandingBytesPerSidCluster,
            docsQosServiceClassMaxTotBytesReqPerSidCluster,
            docsQosServiceClassMaxTimeInSidCluster
            }
   STATUS      deprecated
    DESCRIPTION
       "Group of deprecated objects no longer required to be
       supported by conformant devices as they have been replaced
       by other objects."
    ::= { docsQosMibGroups 4 }

docsQosObsoleteGroup OBJECT-GROUP
    OBJECTS {
            docsQosPHSField,
            docsQosPHSMask,
            docsQosPHSSize,
            docsQosPHSVerify,
            docsQosPHSIndex,
            docsQosServiceClassHCMaxTrafficRate,
            docsQosServiceClassHCMinReservedRate,
            docsQosServiceClassHCPeakTrafficRate
            }
   STATUS      obsolete
    DESCRIPTION
       "Group of obsolete objects no longer required to be
       supported by conformant devices."
    ::= { docsQosMibGroups 5 }

END
