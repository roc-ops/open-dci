DOCS-RPHY-MIB DEFINITIONS ::= BEGIN
IMPORTS
    MODULE-IDENTITY, 
    OBJECT-TYPE, 
    Unsigned32,
    Gauge32,
    Counter32,
    Counter64,
    Integer32
        FROM SNMPv2-SMI         -- RFC 2578
    TruthValue, 
    MacAddress,
    TimeStamp,
    DateAndTime,
    PhysAddress,
    TEXTUAL-CONVENTION
        FROM SNMPv2-TC 
    OBJECT-GROUP, 
    MODULE-COMPLIANCE 
        FROM SNMPv2-CONF
    SnmpAdminString
        FROM SNMP-FRAMEWORK-MIB -- RFC 3411
    InetAddressType,
    InetAddress,
    InetPortNumber,
    InetVersion,
    InetAddressPrefixLength
        FROM INET-ADDRESS-MIB   -- RFC 4001
    UUIDorZero
        FROM UUID-TC-MIB        -- RFC 6933
    IANAPhysicalClass
        FROM IANA-ENTITY-MIB    -- RFC 6933
    IANAifType                       
        FROM IANAifType-MIB
    PhysicalIndex,
    PhysicalIndexOrZero
        FROM ENTITY-MIB         -- RFC 6933
    EntitySensorDataType,
    EntitySensorDataScale,
    EntitySensorPrecision,
    EntitySensorValue,
    EntitySensorStatus
        FROM ENTITY-SENSOR-MIB  -- RFC 3433
    IpAddressOriginTC,
    IpAddressStatusTC,
    Ipv6AddressIfIdentifierTC
        FROM IP-MIB             -- RFC 4293
    TenthdB,
    TenthdBmV
        FROM DOCS-IF-MIB        -- RFC 4546
    InterfaceIndex,
    ifIndex
        FROM IF-MIB             -- RFC2863
    IfDirection,
    docsIf3CmtsCmRegStatusId
        FROM DOCS-IF3-MIB
    clabProjDocsis
        FROM CLAB-DEF-MIB;


docsRphyMib MODULE-IDENTITY 
    LAST-UPDATED    "202401180000Z" -- January 18, 2024
    ORGANIZATION    "Cable Television Laboratories, Inc" 
    CONTACT-INFO 
         "
         Postal: Cable Television Laboratories, Inc. 
         400 Centennial Parkway 
         Louisville, Colorado 80027-1266 
         U.S.A. 
         Phone: +1 303-661-9100 
         Fax: +1 303-661-9199 
         E-mail: mibs@cablelabs.com" 
    DESCRIPTION 
        "This MIB module contains the management objects for
         the Remote PHY Device (RPD) management.
         Copyright 2016-2024 Cable Television Laboratories, Inc.
         All rights reserved."
    REVISION "202401180000Z" -- January 18, 2024
    DESCRIPTION 
        "Revised version includes ECN DOCS-RPHY-MIB-N-23.2359-1."
    REVISION "202310120000Z" -- October 12, 2023
    DESCRIPTION 
        "Revised version includes ECN DOCS-RPHY-MIB-N-23.2340-1."
    REVISION "202212010000Z" -- December 1, 2022
    DESCRIPTION 
        "Revised version includes ECN DOCS-RPHY-MIB-N-22.2291-1."
    REVISION "202206300000Z" -- June 30, 2022
    DESCRIPTION 
        "Revised version includes ECN DOCS-RPHY-MIB-N-22.2261-1."
    REVISION "202203310000Z" -- March 31, 2022
    DESCRIPTION 
        "Revised version includes ECN DOCS-RPHY-MIB-N-22.2240-1."
    REVISION "202201200000Z" -- January 20, 2022
    DESCRIPTION 
        "Revised version includes ECN DOCS-RPHY-MIB-N-21.2224-1."
    REVISION "202110210000Z" -- October 21, 2021
    DESCRIPTION 
        "Revised version includes ECN DOCS-RPHY-MIB-N-21.2196-1."
    REVISION "202103110000Z" -- March 11, 2021
    DESCRIPTION 
        "Revised version includes ECN DOCS-RPHY-MIB-N-21.2149-2."
    REVISION "202010010000Z" -- October 1, 2020
    DESCRIPTION 
        "Revised version includes ECN DOCS-RPHY-MIB-N-20.2115-1."
    REVISION "202005210000Z" -- May 21, 2020
    DESCRIPTION 
        "Revised Version includes ECN DOCS-RPHY-MIB-N-20.2097-1."
    REVISION "202001090000Z" -- January 9, 2020
    DESCRIPTION 
        "Revised Version includes ECN DOCS-RPHY-MIB-N-19.2068-1."
    REVISION "201908230000Z" -- August 23, 2019
    DESCRIPTION 
        "Revised Version includes ECN DOCS-RPHY-MIB-N-19.2051-2."
    REVISION "201906130000Z" -- June 13, 2019
    DESCRIPTION 
        "Revised Version includes ECN
         DOCS-RPHY-MIB-N-19.2027-1."
    REVISION "201901240000Z" -- January 24, 2019
    DESCRIPTION 
        "Revised Version includes ECN
         DOCS-RPHY-MIB-N-18.1987-1."
    REVISION "201810180000Z" -- October 18, 2018
    DESCRIPTION 
        "Revised Version includes ECN
         DOCS-RPHY-MIB-N-18.1959-1."
    REVISION "201807260000Z" -- July 26, 2018
    DESCRIPTION 
        "Revised Version includes ECN
         DOCS-RPHY-MIB-N-18.1938-2."
    REVISION "201804120000Z" -- April 12, 2018
    DESCRIPTION 
        "Revised Version includes ECN
         DOCS-RPHY-MIB-N-18.1910-2."
    REVISION "201711160000Z" -- November 16, 2017
    DESCRIPTION 
        "Revised Version includes ECN
         DOCS-RPHY-MIB-N-17.1812-4."
    REVISION "201708100000Z" -- August 10, 2017
    DESCRIPTION 
        "Revised Version includes ECN
         DOCS-RPHY-MIB-N-17.1780-3." 
    REVISION "201704130000Z" -- April 13, 2017
    DESCRIPTION 
        "Revised Version includes ECN
         DOCS-RPHY-MIB-N-17.1711-4."
    REVISION "201612150000Z" -- December 15, 2016
    DESCRIPTION 
        "Revised Version includes ECN
         DOCS-RPHY-MIB-N-16.1680-2."
    REVISION "201609290000Z" -- September 29, 2016
    DESCRIPTION 
        "Revised Version includes ECN
         DOCS-RPHY-MIB-N-16.1561-4."
    REVISION "201604210000Z" -- April 21, 2016
    DESCRIPTION 
        "Initial version, created by R-OSSI-N-16.1461-3."
::= { clabProjDocsis 30 }


-- ---------------------------------------------------------
-- Textual Conventions
-- ---------------------------------------------------------

OperStatusType ::= TEXTUAL-CONVENTION
     STATUS      current
     DESCRIPTION
         "This data type represents the status of the 
          pseudowire from the point of view of the specific 
          reporting entity.
          
          Values are as follows:
         'other' 
             indicates a vendor-specific operational status.
         'up'         
             indicates that the pseudowire is ready to pass packets.
         'down' 
             indicates that pseudowire signaling is not yet finished, 
             or indications available at the service level indicate 
             that the pseudowire is not passing packets.
         'testing' 
             indicates that AdminStatus at the pseudowire level is 
             set to test.
         'dormant' 
             indicates that the pseudowire is not in a condition to 
             pass packets but is in a 'pending' state, waiting for 
             some external event.
         'notPresent' 
             indicates that some component is missing to accomplish 
             the setup of the pseudowire.  It can be a configuration 
             error, incomplete configuration, or a missing H/W 
             component.
         'lowerLayerDown' 
             indicates one or more of the lower-layer 
             interfaces responsible for running the underlying PSN
             is not in OperStatus 'up' state."

     SYNTAX      INTEGER {
                          other(0),
                          up(1),
                          down(2),
                          testing(3),
                          dormant(4),
                          notPresent(5),
                          lowerLayerDown(6)
                         }


RphyChannelType ::= TEXTUAL-CONVENTION
     STATUS      current
     DESCRIPTION
         "This data type indicates the type of RPHY channel."
     REFERENCE
        "DOCSIS DCA MHAv2 Remote PHY Specification
         CM-SP-R-PHY-I04-160512, RfChannelType TLV Section."
     SYNTAX      INTEGER {
                          other(0),
                          dsScQam(1),
                          dsOfdm(2),
                          ndf(3),
                          scte551Fwd(4),
                          usAtdma(5),
                          usOfdma(6),
                          reserved(7),
                          ndr(8),
                          scte551Ret(9),
                          dsScte55d2(10),
                          usScte55d2(11)                        
                         }

EvPriorityType ::= TEXTUAL-CONVENTION
     STATUS      current
     DESCRIPTION
         "This data type defines an event priority level.  These are 
           ordered from most (emergency) to least (debug) critical.  
           Each event has a particular priority level associated with 
           it (as defined by the vendor)."
     REFERENCE
        "DOCSIS DCA MHAv2 Remote PHY OSS Interface Specification
         CM-SP-R-OSSI-I04-160923, Section 9."
     SYNTAX      INTEGER {
                          emergency(1),
                          alert(2),
                          critical(3),
                          error(4),
                          warning(5),
                          notice(6),
                          information(7),
                          debug(8)                                                                                  
                         }

SyncEQLType ::= TEXTUAL-CONVENTION
     STATUS      current
     DESCRIPTION
         "This data type defines the SyncE EQL Type."
     REFERENCE
        "Synchronization Techniques for DOCSIS Technology Specification,
          CM-SP-SYNC-D01-18073  Annex C"
     SYNTAX      INTEGER {
                          other(1),
                          prc(2),
                          ssuA(3),
                          ssuB(4),
                          eec1(5),
                          dnu(6),
                          prs(7),
                          stu(9),
                          st2(10),
                          tnc(11),
                          st3e(12),
                          eec2(13),
                          dus(14)                                                                          
                         }
                         
RfmStatusType ::= TEXTUAL-CONVENTION
     STATUS      current
     DESCRIPTION
         "This data type defines the Rfm Status Type"
     REFERENCE 
        "DOCSIS DCA MHAv2 Remote PHY OSS Interface Specification
         CM-SP-R-OSSI, DataType Definitions."
     SYNTAX      INTEGER {
                          other(1),
                          gcpCfg(2),
                          localCfgNvRam(3),
                          localCfgDefault(4),
                          unknown(5)                                                                   
                         }
                     
-- ---------------------------------------------------------------------
-- Main Groups
-- ---------------------------------------------------------------------
docsRphyNotifications        OBJECT IDENTIFIER ::= { docsRphyMib 0}
docsRphyObjects              OBJECT IDENTIFIER ::= { docsRphyMib 1}
docsRphyConformance          OBJECT IDENTIFIER ::= { docsRphyMib 2}

docsRphyRpdDevMibObjects     OBJECT IDENTIFIER ::= { docsRphyObjects 1}
docsRphyRpdIfMibObjects      OBJECT IDENTIFIER ::= { docsRphyObjects 2}

docsRphyRpdIpMibObjects      OBJECT IDENTIFIER ::= { docsRphyObjects 3}
docsRphyCcapMibObjects       OBJECT IDENTIFIER ::= { docsRphyObjects 4}

docsRphyCcapSecMibObjects    OBJECT IDENTIFIER ::= { docsRphyObjects 5} -- Deprecated (objects moved to DOCS-RPHY-SEC-MIB)

docsRphyCmtsCmStatMibObjects OBJECT IDENTIFIER ::= { docsRphyObjects 6}


docsRphyRpdIpIcmpMibObjects  OBJECT IDENTIFIER ::= { docsRphyRpdIpMibObjects 9 }

docsRphyCompliances          OBJECT IDENTIFIER ::= { docsRphyConformance 1 } 
docsRphyGroups               OBJECT IDENTIFIER ::= { docsRphyConformance 2 } 



-- ---------------------------------------------------------------------
-- Notification Objects
-- ---------------------------------------------------------------------

-- ---------------------------------------------------------------------
-- RPD Group Objects
-- ---------------------------------------------------------------------
           
-- ---------------------------------------------------------------------
-- RPD Info Table
-- ---------------------------------------------------------------------

docsRphyRpdDevInfoTable OBJECT-TYPE
    SYNTAX      SEQUENCE OF DocsRphyRpdDevInfoEntry
    MAX-ACCESS  not-accessible
    STATUS      current
    DESCRIPTION
        "This table identifies the RPD for which the details
         and statistics are being provided.
         The RpdInfo object is read from the GCP complex TLV Type 100.
         The attributes defined in the RpdInfo object are read from 
         the GCP complex TLV Type 100.1."
    REFERENCE 
        "Information Model Mapping: CM-SP-R-OSSI 
         RpdInfo"
    ::= { docsRphyRpdDevMibObjects 1 }


docsRphyRpdDevInfoEntry OBJECT-TYPE
    SYNTAX     DocsRphyRpdDevInfoEntry
    MAX-ACCESS not-accessible
    STATUS     current
    DESCRIPTION
        "The conceptual row of docsRphyRpdDevInfoTable."
    INDEX { docsRphyRpdDevInfoUniqueId }
    ::= { docsRphyRpdDevInfoTable 1 }


DocsRphyRpdDevInfoEntry ::= SEQUENCE
    {
    docsRphyRpdDevInfoUniqueId              MacAddress,
    docsRphyRpdDevInfoSysUpTime             TimeStamp,
    docsRphyRpdDevInfoNumCrashFilesAvail    Unsigned32,
    docsRphyRpdDevInfoPrincipalCoreStatus   INTEGER
    }
        
docsRphyRpdDevInfoUniqueId OBJECT-TYPE
    SYNTAX      MacAddress
    MAX-ACCESS  not-accessible 
    STATUS      current 
    DESCRIPTION 
        "This attribute specifies a globally unique 6-byte 
         identifier for the RPD.  By convention, an RPD SHOULD use 
         the MAC address of the lowest numbered Ethernet port 
         facing the CIN."
    REFERENCE 
        "Information Model Mapping: CM-SP-R-OSSI 
         RpdInfo::RpdUniqueId"
    ::= { docsRphyRpdDevInfoEntry 1 }


docsRphyRpdDevInfoSysUpTime OBJECT-TYPE
    SYNTAX      TimeStamp
    MAX-ACCESS  read-only
    STATUS      current
    DESCRIPTION 
        "This attribute is the time (in hundredths of a second) 
         since the RPD was last re-initialized. This value is 
         reported by the RPD."
    REFERENCE 
        "Information Model Mapping: CM-SP-R-OSSI 
         RpdInfo::RpdSysUpTime"
    ::= { docsRphyRpdDevInfoEntry 2 }

docsRphyRpdDevInfoNumCrashFilesAvail OBJECT-TYPE
    SYNTAX      Unsigned32
    MAX-ACCESS  read-only
    STATUS      current
    DESCRIPTION 
        "This attribute provides the number of crash files."
    REFERENCE 
        "Information Model Mapping: CM-SP-R-OSSI 
         RpdInfo::NumCrashFilesAvail"
    ::= { docsRphyRpdDevInfoEntry 3 }

docsRphyRpdDevInfoPrincipalCoreStatus OBJECT-TYPE
    SYNTAX      INTEGER {
                          connected(1),
                          waitOperational(2),
                          operational(3)
                         }
    MAX-ACCESS  read-only
    STATUS      current
    DESCRIPTION 
        "This attribute reports the RPD status with respect    
          to the Principal Core initialization.

         connected: The RPD is connected to the Principal Core
         and in the process of being configured.
         
         waitOperational: The Principal Core has set 
         'configuration complete' to true, 
         but has not made the RPD operational.

         operational: The Principal Core has made
         the RPD operational.

         The reported values correspond to values 5..7 of the RCP/GCP
         attribute TopLevelRpdstate (TLV 87.1) for the index assigned
         by the RPD to the Principal CCAP Core." 
    REFERENCE 
        "Information Model Mapping: CM-SP-R-OSSI 
         RpdInfo::PrincipalCoreStatus"
    ::= { docsRphyRpdDevInfoEntry 4 }


-- ---------------------------------------------------------------------
-- RPD Identification Table
-- ---------------------------------------------------------------------

docsRphyRpdDevIdentificationTable OBJECT-TYPE
    SYNTAX      SEQUENCE OF DocsRphyRpdDevIdentificationEntry
    MAX-ACCESS  not-accessible
    STATUS      current
    DESCRIPTION
        "This table provides data that uniquely identifies the RPD.
         The Identification TLV Type is 50.19."
    REFERENCE 
        "Information Model Mapping: CM-SP-R-OSSI 
         Identification"
    ::= { docsRphyRpdDevMibObjects 2 }


docsRphyRpdDevIdentificationEntry OBJECT-TYPE
    SYNTAX     DocsRphyRpdDevIdentificationEntry
    MAX-ACCESS not-accessible
    STATUS     current
    DESCRIPTION
        "The conceptual row of docsRphyRpdDevIdentificationTable."
    INDEX { docsRphyRpdDevInfoUniqueId }
    ::= { docsRphyRpdDevIdentificationTable 1 }


DocsRphyRpdDevIdentificationEntry ::= SEQUENCE
    {
    docsRphyRpdDevIdVendorName               SnmpAdminString,
    docsRphyRpdDevIdVendorId                 Unsigned32,
    docsRphyRpdDevIdModelNum                 SnmpAdminString,
    docsRphyRpdDevIdSerialNum                SnmpAdminString,
    docsRphyRpdDevIdDeviceAlias              SnmpAdminString,
    docsRphyRpdDevIdDeviceDescr              SnmpAdminString,
    docsRphyRpdDevIdHwRev                    SnmpAdminString,
    docsRphyRpdDevIdCurrSwVer                SnmpAdminString,
    docsRphyRpdDevIdBootRomVer               SnmpAdminString,
    docsRphyRpdDevIdUsBurstRcvrVendorId      Unsigned32,
    docsRphyRpdDevIdUsBurstRcvrModelNum      SnmpAdminString,
    docsRphyRpdDevIdUsBurstRcvrDrivVer       SnmpAdminString,
    docsRphyRpdDevIdUsBurstRcvrSerialNum     SnmpAdminString,
    docsRphyRpdDevIdRcpProtocolVer           SnmpAdminString,
    docsRphyRpdDevIdRcpSchemaVer             SnmpAdminString,
    docsRphyRpdDevIdCurrSwImageLastUpdate    DateAndTime,          
    docsRphyRpdDevIdCurrSwImageName          SnmpAdminString,
    docsRphyRpdDevIdCurrSwImageServerType    InetAddressType,
    docsRphyRpdDevIdCurrSwImageServerAddress InetAddress,
    docsRphyRpdDevIdCurrSwImageIndex         Unsigned32,
    docsRphyRpdDevIdVspSelector              SnmpAdminString
    }
        
docsRphyRpdDevIdVendorName OBJECT-TYPE
    SYNTAX      SnmpAdminString
    MAX-ACCESS  read-only 
    STATUS      current 
    DESCRIPTION 
        "This attribute identifies the RPD manufacturer. 
         The format is vendor proprietary."
    REFERENCE 
        "Information Model Mapping: CM-SP-R-OSSI 
         Identification::VendorName"
    ::= { docsRphyRpdDevIdentificationEntry 1 }


docsRphyRpdDevIdVendorId OBJECT-TYPE
    SYNTAX      Unsigned32 (0..65535)
    MAX-ACCESS  read-only
    STATUS      current
    DESCRIPTION 
        "This attribute is the IANA-assigned SMI Network Management 
         Private Enterprise Code of the vendor, as specified in
         RFC 5612."
    REFERENCE 
        "Information Model Mapping: CM-SP-R-OSSI 
         Identification::VendorId"
    ::= { docsRphyRpdDevIdentificationEntry 2 }

docsRphyRpdDevIdModelNum OBJECT-TYPE
    SYNTAX      SnmpAdminString
    MAX-ACCESS  read-only 
    STATUS      current 
    DESCRIPTION 
        "This attribute is the model name and number used by the 
         vendor to identify the RPD. The format is vendor 
         proprietary."
    REFERENCE 
        "Information Model Mapping: CM-SP-R-OSSI 
         Identification::ModelNumber"
    ::= { docsRphyRpdDevIdentificationEntry 3 }

docsRphyRpdDevIdSerialNum OBJECT-TYPE
    SYNTAX      SnmpAdminString (SIZE(0..16))
    MAX-ACCESS  read-only 
    STATUS      current 
    DESCRIPTION 
        "This attribute is the serial number of the RPD. 
         The format is vendor proprietary."
    REFERENCE 
        "Information Model Mapping: CM-SP-R-OSSI 
         Identification::SerialNumber"
    ::= { docsRphyRpdDevIdentificationEntry 4 }
        
docsRphyRpdDevIdDeviceAlias OBJECT-TYPE
    SYNTAX      SnmpAdminString
    MAX-ACCESS  read-only 
    STATUS      current 
    DESCRIPTION 
        "This attribute reports the device name assigned by the 
         operator and represents a 'handle' for the RPD."
    REFERENCE 
        "Information Model Mapping: CM-SP-R-OSSI 
         Identification::DeviceAlias"
    ::= { docsRphyRpdDevIdentificationEntry 5 }
        
docsRphyRpdDevIdDeviceDescr OBJECT-TYPE
    SYNTAX      SnmpAdminString
    MAX-ACCESS  read-only 
    STATUS      current 
    DESCRIPTION 
        "This attribute is a short text description of the RPD
         provided by the RPD manufacturer."
    REFERENCE 
        "Information Model Mapping: CM-SP-R-OSSI 
         Identification::DeviceDescription"
    ::= { docsRphyRpdDevIdentificationEntry 6 }
        
docsRphyRpdDevIdHwRev OBJECT-TYPE
    SYNTAX      SnmpAdminString
    MAX-ACCESS  read-only 
    STATUS      current 
    DESCRIPTION 
        "This attribute is the revision number of the hardware 
         of the RPD. The format is vendor proprietary."
    REFERENCE 
        "Information Model Mapping: CM-SP-R-OSSI 
         Identification::HwRevision"
    ::= { docsRphyRpdDevIdentificationEntry 7 }
        
docsRphyRpdDevIdCurrSwVer OBJECT-TYPE
    SYNTAX      SnmpAdminString
    MAX-ACCESS  read-only 
    STATUS      current 
    DESCRIPTION 
        "This attribute is the version number of the software 
         currently running on the RPD. The format is vendor 
         proprietary."
    REFERENCE 
        "Information Model Mapping: CM-SP-R-OSSI 
         Identification::CurrentSwVersion"
    ::= { docsRphyRpdDevIdentificationEntry 8 }
        
docsRphyRpdDevIdBootRomVer OBJECT-TYPE
    SYNTAX      SnmpAdminString
    MAX-ACCESS  read-only 
    STATUS      current 
    DESCRIPTION 
        "This attribute reports the version number of the boot 
         ROM currently installed on the RPD. The format is 
         vendor proprietary."
    REFERENCE 
        "Information Model Mapping: CM-SP-R-OSSI 
         Identification::BootRomVersion"
    ::= { docsRphyRpdDevIdentificationEntry 9 }
        
docsRphyRpdDevIdUsBurstRcvrVendorId OBJECT-TYPE
    SYNTAX      Unsigned32 (0..65535)
    MAX-ACCESS  read-only 
    STATUS      current 
    DESCRIPTION 
        "This attribute reports the IANA-assigned SMI Network 
         Management Private Enterprise Code of the RPD's US burst 
         receiver manufacturer, as specified in RFC 5612."
    REFERENCE 
        "Information Model Mapping: CM-SP-R-OSSI 
         Identification::UsBurstReceiverVendorId"
    ::= { docsRphyRpdDevIdentificationEntry 10 }
        
docsRphyRpdDevIdUsBurstRcvrModelNum OBJECT-TYPE
    SYNTAX      SnmpAdminString (SIZE(3..16))
    MAX-ACCESS  read-only 
    STATUS      current 
    DESCRIPTION 
        "This attribute reports the model number used by the vendor 
         to identify the RPD's US burst receiver. The format is 
         vendor proprietary."
    REFERENCE 
        "Information Model Mapping: CM-SP-R-OSSI 
         Identification::UsBurstReceiverModelNumber"
    ::= { docsRphyRpdDevIdentificationEntry 11 }
        
docsRphyRpdDevIdUsBurstRcvrDrivVer OBJECT-TYPE
    SYNTAX      SnmpAdminString (SIZE(3..16))
    MAX-ACCESS  read-only 
    STATUS      current 
    DESCRIPTION 
        "This attribute reports the driver version of the RPD's 
         US burst receiver. The format is vendor proprietary."
    REFERENCE 
        "Information Model Mapping: CM-SP-R-OSSI 
         Identification::UsBurstReceiverDriverVersion"
    ::= { docsRphyRpdDevIdentificationEntry 12 }
        
docsRphyRpdDevIdUsBurstRcvrSerialNum OBJECT-TYPE
    SYNTAX      SnmpAdminString (SIZE(5..16))
    MAX-ACCESS  read-only 
    STATUS      current 
    DESCRIPTION 
        "This attribute reports the serial number of the RPD's 
         US burst receiver. The format is vendor proprietary."
    REFERENCE 
        "Information Model Mapping: CM-SP-R-OSSI 
         Identification::UsBurstReceiverSerialNumber"
    ::= { docsRphyRpdDevIdentificationEntry 13 }
        
docsRphyRpdDevIdRcpProtocolVer OBJECT-TYPE
    SYNTAX      SnmpAdminString (SIZE(3..32))
    MAX-ACCESS  read-only 
    STATUS      current 
    DESCRIPTION 
        "This attribute reports the version of the RCP protocol 
         supported by the RPD."
    REFERENCE 
        "Information Model Mapping: CM-SP-R-OSSI 
         Identification::RdpRcpProtocolVersion"
    ::= { docsRphyRpdDevIdentificationEntry 14 }
        
docsRphyRpdDevIdRcpSchemaVer OBJECT-TYPE
    SYNTAX      SnmpAdminString (SIZE(5..32))
    MAX-ACCESS  read-only 
    STATUS      current 
    DESCRIPTION 
        "This attribute reports the version of the RCP schema 
         supported by the RPD."
    REFERENCE 
        "Information Model Mapping: CM-SP-R-OSSI 
         Identification::RdpRcpSchemaVersion"
    ::= { docsRphyRpdDevIdentificationEntry 15 }

docsRphyRpdDevIdCurrSwImageLastUpdate OBJECT-TYPE
    SYNTAX      DateAndTime          
    MAX-ACCESS  read-only 
    STATUS      current 
    DESCRIPTION 
        "This attribute reports the most recent date and time the 
         software image currently running on the RPD was updated. 
         The RPD preserves the value of this attribute across reboots
         for a given software image."
    REFERENCE 
        "Information Model Mapping: CM-SP-R-OSSI 
         Identification::CurrentSwImageLastUpdate"
    ::= { docsRphyRpdDevIdentificationEntry 16 }


docsRphyRpdDevIdCurrSwImageName OBJECT-TYPE
    SYNTAX      SnmpAdminString
    MAX-ACCESS  read-only 
    STATUS      current 
    DESCRIPTION 
        "This attribute reports the name of the software image currently
         running on the RPD. The RPD preserves the value of this 
         attribute across reboots for a given software image."
    REFERENCE 
        "Information Model Mapping: CM-SP-R-OSSI 
         Identification::CurrentSwImageName"
    ::= { docsRphyRpdDevIdentificationEntry 17 }

docsRphyRpdDevIdCurrSwImageServerType OBJECT-TYPE
    SYNTAX      InetAddressType  
    MAX-ACCESS  read-only 
    STATUS      current 
    DESCRIPTION 
        "This attribute reports the server internet address type of 
         the software image currently running on the RPD. The RPD
         preserves the value of this attribute across reboots
         for a given software image."
    REFERENCE 
        "Information Model Mapping: CM-SP-R-OSSI 
         Identification::CurrentSwImageServerType"
    ::= { docsRphyRpdDevIdentificationEntry 18 }

docsRphyRpdDevIdCurrSwImageServerAddress OBJECT-TYPE
    SYNTAX      InetAddress  (SIZE(4|16))
    MAX-ACCESS  read-only 
    STATUS      current 
    DESCRIPTION 
        "This attribute reports the Internet address of the server 
         from which the software image currently running on the RPD 
         was downloaded. The RPD preserves the value of this 
         attribute across reboots."
    REFERENCE 
        "Information Model Mapping: CM-SP-R-OSSI 
         Identification::CurrentSwImageServerAddress"
    ::= { docsRphyRpdDevIdentificationEntry 19 }

docsRphyRpdDevIdCurrSwImageIndex OBJECT-TYPE
    SYNTAX      Unsigned32 (0..3)
    MAX-ACCESS  read-only 
    STATUS      current 
    DESCRIPTION 
        "This attribute reports which software image is
         currently running on the RPD."
    REFERENCE 
        "Information Model Mapping: CM-SP-R-OSSI 
         Identification::CurrentSwImageIndex"
     ::= { docsRphyRpdDevIdentificationEntry 20 }

docsRphyRpdDevIdVspSelector OBJECT-TYPE
    SYNTAX      SnmpAdminString (SIZE(0..16))
    MAX-ACCESS  read-only 
    STATUS      current 
    DESCRIPTION 
        "This attribute contains the Vendor-Specific 
         Pre-configuration (VSP) Selector advertised by the RPD, 
         defined as a human-readable string. This attribute is used 
         by the Principal CCAP Core to match the RPD to VSP configuration 
         maintained on the CCAP Core and to deliver VSP configuration 
         to the RPD during initialization. If the RPD does not support VSP, 
         the RPD communicates VSP as a zero-length string."
    REFERENCE 
        "Information Model Mapping: CM-SP-R-OSSI 
         Identification::VspSelector"
    ::= { docsRphyRpdDevIdentificationEntry 21 }


-- ---------------------------------------------------------------------
-- RPD Location Table
-- ---------------------------------------------------------------------

docsRphyRpdDevLocationTable OBJECT-TYPE
    SYNTAX      SEQUENCE OF DocsRphyRpdDevLocationEntry
    MAX-ACCESS  not-accessible
    STATUS      current
    DESCRIPTION
        "This table provides location details for the RPD. The 
         values are populated via a management interface or other 
         automatic mechanisms (e.g. GPS)."
    ::= { docsRphyRpdDevMibObjects 3 }


docsRphyRpdDevLocationEntry OBJECT-TYPE
    SYNTAX     DocsRphyRpdDevLocationEntry
    MAX-ACCESS not-accessible
    STATUS     current
    DESCRIPTION
        "The conceptual row of docsRphyRpdDevLocationTable."
    INDEX { docsRphyRpdDevInfoUniqueId }
    ::= { docsRphyRpdDevLocationTable 1 }


DocsRphyRpdDevLocationEntry ::= SEQUENCE
    {
    docsRphyRpdDevLocationDescr              SnmpAdminString,
    docsRphyRpdDevLocationLatitude           SnmpAdminString,
    docsRphyRpdDevLocationLongitude          SnmpAdminString
    }
        
docsRphyRpdDevLocationDescr OBJECT-TYPE
    SYNTAX      SnmpAdminString (SIZE(0..255))
    MAX-ACCESS  read-only 
    STATUS      current 
    DESCRIPTION 
        "This attribute is short text description of where the RPD
         has been installed, such as a street address. The format 
         is specific to the operator."
    ::= { docsRphyRpdDevLocationEntry 1 }


docsRphyRpdDevLocationLatitude OBJECT-TYPE
    SYNTAX      SnmpAdminString (SIZE(9))
    MAX-ACCESS  read-only
    STATUS      current
    DESCRIPTION 
        "This attribute is the latitudinal coordinate of the RPD 
         location, expressed as a 6-byte long string as described
         in ISO 6709-2008 (6 digit degrees, minutes, 
         seconds: +/-DDMMSS.S). For  example: -750015.1"
    ::= { docsRphyRpdDevLocationEntry 2 }
        
docsRphyRpdDevLocationLongitude OBJECT-TYPE
    SYNTAX      SnmpAdminString (SIZE(10))
    MAX-ACCESS  read-only
    STATUS      current
    DESCRIPTION 
        "This attribute is the longitudinal coordinate of the RPD 
         location, expressed as a 7-byte long string as described 
         in ISO 6709-2008 (7 digits degrees, minutes, 
         seconds: +/-DDDMMSS.S).  For example: -0750015.1"
    ::= { docsRphyRpdDevLocationEntry 3 }
        
-- ---------------------------------------------------------------------
-- RPD Cores Connected Table
-- ---------------------------------------------------------------------

docsRphyRpdDevCoresConnectedTable OBJECT-TYPE
    SYNTAX      SEQUENCE OF DocsRphyRpdDevCoresConnectedEntry
    MAX-ACCESS  not-accessible
    STATUS      current
    DESCRIPTION
        "This table provides a list of CCAP-Cores to which the RPD
         is authenticated, including the CCAP-Core on which the MIB 
         is polled. For each CCAP-Core instance, the RPD indicates if 
         that CCAP-Core is the principal Core. These values are 
         provided by the CCAP-Core on initialization.
         The CoresConnected TLV Type is 60."
    REFERENCE 
        "Information Model Mapping: CM-SP-R-OSSI 
         CoresConnected"
    ::= { docsRphyRpdDevMibObjects 4 }


docsRphyRpdDevCoresConnectedEntry OBJECT-TYPE
    SYNTAX     DocsRphyRpdDevCoresConnectedEntry
    MAX-ACCESS not-accessible
    STATUS     current
    DESCRIPTION
        "The conceptual row of docsRphyRpdDevCoresConnectedTable."
    INDEX { docsRphyRpdDevInfoUniqueId, docsRphyRpdDevCoresConnectedIndex }
    ::= { docsRphyRpdDevCoresConnectedTable 1 }


DocsRphyRpdDevCoresConnectedEntry ::= SEQUENCE
    {
    docsRphyRpdDevCoresConnectedIndex                         Unsigned32,
    docsRphyRpdDevCoresConnectedCoreId                        OCTET STRING,
    docsRphyRpdDevCoresConnectedAddressType                   InetAddressType,
    docsRphyRpdDevCoresConnectedAddress                       InetAddress,
    docsRphyRpdDevCoresConnectedIsPrincipal                   TruthValue,
    docsRphyRpdDevCoresConnectedName                          SnmpAdminString,
    docsRphyRpdDevCoresConnectedVendorId                      Unsigned32,
    docsRphyRpdDevCoresConnectedCoreMode                      INTEGER,
    docsRphyRpdDevCoresConnectedInitConfigComplete            TruthValue,
    docsRphyRpdDevCoresConnectedCoreFunction                  BITS,
    docsRphyRpdDevCoresConnectedAuxCoreGcpConnectionStatus    INTEGER,
    docsRphyRpdDevCoresConnectedAuxCoreRpdState               INTEGER,
    docsRphyRpdDevCoresConnectedResourceSetIndex              Unsigned32,
    docsRphyRpdDevCoresConnectedGcpBackupConnectionConfig     TruthValue,
    docsRphyRpdDevCoresConnectedGcpConnectionStatus           INTEGER,
    docsRphyRpdDevCoresConnectedGcpBackupCoreStatus           INTEGER,
    docsRphyRpdDevCoresConnectedAuthenticationStatus          INTEGER
    }

docsRphyRpdDevCoresConnectedIndex OBJECT-TYPE
    SYNTAX      Unsigned32 (0..255) 
    MAX-ACCESS  not-accessible
    STATUS      current
    DESCRIPTION 
        "This key attribute uniquely identifies an instance of
         a row in the CoresConnected table."
    ::= { docsRphyRpdDevCoresConnectedEntry 1 }
        
docsRphyRpdDevCoresConnectedCoreId OBJECT-TYPE
    SYNTAX      OCTET STRING (SIZE (6))
    MAX-ACCESS  read-only 
    STATUS      current 
    DESCRIPTION 
        "This attribute reports the unique identifier, 
         for example a MAC address, of the CCAP Core identified
         in the row entry."
    ::= { docsRphyRpdDevCoresConnectedEntry 2 }


docsRphyRpdDevCoresConnectedAddressType OBJECT-TYPE
    SYNTAX      InetAddressType   
    MAX-ACCESS  read-only
    STATUS      current
    DESCRIPTION 
        "This attribute represents the IP address type of 
         the CCAP Core. This value is of type InetAddressType, 
         which is defined by [RFC 4001]."
    ::= { docsRphyRpdDevCoresConnectedEntry 3 }
        
docsRphyRpdDevCoresConnectedAddress OBJECT-TYPE
    SYNTAX      InetAddress (SIZE (4|16))
    MAX-ACCESS  read-only
    STATUS      current
    DESCRIPTION 
        "This attribute provides the IPv4 or IPv6 address 
         of the CCAP-Core."
    ::= { docsRphyRpdDevCoresConnectedEntry 4 }
        
docsRphyRpdDevCoresConnectedIsPrincipal OBJECT-TYPE
    SYNTAX      TruthValue
    MAX-ACCESS  read-only
    STATUS      current
    DESCRIPTION 
        "This attribute indicates if the CCAP-Core is the
         principal core. If true, this attribute indicates 
         that this CCAP-Core is the principal core."
    ::= { docsRphyRpdDevCoresConnectedEntry 5 }
        
docsRphyRpdDevCoresConnectedName OBJECT-TYPE
    SYNTAX      SnmpAdminString
    MAX-ACCESS  read-only
    STATUS      current
    DESCRIPTION 
        "This attribute provides the name of the CCAP-Core 
         as conveyed to the RPD."
    ::= { docsRphyRpdDevCoresConnectedEntry 6 }
        
docsRphyRpdDevCoresConnectedVendorId OBJECT-TYPE
    SYNTAX      Unsigned32 (0..65535)
    MAX-ACCESS  read-only
    STATUS      current
    DESCRIPTION 
        "This attribute provides the IANA-assigned SMI Network 
         Management Private Enterprise Code of the vendor, as 
         specified in RFC 1700."
    ::= { docsRphyRpdDevCoresConnectedEntry 7 }

docsRphyRpdDevCoresConnectedCoreMode OBJECT-TYPE
    SYNTAX      INTEGER {
                         active(1),
                         backup(2),
                         notActing(3),
                         decisionPending(4),
                         outOfService(5),
                         contactPending(6),     
                         deprecated(7),
                         redirect(8)
                        }
    MAX-ACCESS  read-only
    STATUS      current
    DESCRIPTION 
        "This attribute indicates the role in which the CCAP
         core is currently acting for the RPD. It also identifies two 
         intermediate states ('decisionPending' and 'contactPending') 
         in which the role of the CCAP Core is still to be determined.
         
         active: The CCAP Core is actively providing service(s)
         to the RPD as a Principal or Auxiliary Core.

         backup: The CCAP Core is configured to provide 
         backup service for an Active CCAP Core.

         notActing: The CCAP Core is not prepared to act 
         as an Active or Backup CCAP Core.

         decisionPending: The CCAP Core requires further 
         information to make a decision on acting for the 
         RPD or redirecting the RPD.

         outOfService: An error occurred during the 
         initialization process with the CCAP Core or 
         the RPD has been instructed to place the CCAP 
         Core in Out-Of-Service mode.

         contactPending: The initial state after configuring
         the CCAP Core. The CCAP Core has not yet been 
         contacted by the RPD.

         deprecated: Reserved.
  
         redirect: A CCAP Core wishing to redirect an RPD does this by 
         sending an IRA message with the CoreMode set to 'redirect'. 
         This is the mode for the CCAP Core after it has instructed the 
         RPD to redirect to an alternate CCAP Core."
      ::= { docsRphyRpdDevCoresConnectedEntry 8 }

docsRphyRpdDevCoresConnectedInitConfigComplete OBJECT-TYPE
    SYNTAX      TruthValue
    MAX-ACCESS  read-only
    STATUS      current
    DESCRIPTION 
        "This attribute reports whether the Core has indicated
         that its initial configuration of the RPD is complete."
    ::= { docsRphyRpdDevCoresConnectedEntry 9 }

docsRphyRpdDevCoresConnectedCoreFunction OBJECT-TYPE
    SYNTAX      BITS {
                      principal(0),
                      docsis(1),
                      broadcastVideo(2),
                      narrowcastVideo(3), 
                      scte55d1Oob(4), 
                      scte55d2Oob(5), 
                      ndf(6), 
                      ndr(7),
                      monitoring(8)
                     }
    MAX-ACCESS  read-only
    STATUS      current
    DESCRIPTION 
        "This attribute reports the operational functions
         that this Core provides.

         principal: Core operates as a Principal Core 

         docsis: Core provides DOCSIS services
 
         broadcastVideo: Core provides broadcast video services
 
         narrowcastVideo: Core provides narrowcast video services
 
         scte55d1Oob: Core provides SCTE 55-1 OOB services
 
         scte55d2Oob: Core provides SCTE 55-2 OOB services
 
         ndf: Core provides narrowband digital forward services
 
         ndr: Core provides narrowband digital return services
         
         monitoring: Core provides monitoring functions"
    ::= { docsRphyRpdDevCoresConnectedEntry 10 }
        
docsRphyRpdDevCoresConnectedAuxCoreGcpConnectionStatus OBJECT-TYPE
    SYNTAX      INTEGER {
                         notConnected(0),
                         connected(1),
                         reconnecting(2)
                        }
    MAX-ACCESS  read-only
    STATUS      deprecated
    DESCRIPTION 
        "This attribute reports the status of the GCP connection to the 
         Auxiliary CCAP Core. If the attribute IsPrincipal contains a value
         of true, this attribute has no meaning since it only applies to 
         Auxiliary Cores."
      ::= { docsRphyRpdDevCoresConnectedEntry 11 }

docsRphyRpdDevCoresConnectedAuxCoreRpdState OBJECT-TYPE
    SYNTAX      INTEGER {
                         other(0),
                         authenticateToCore(1),
                         gcpConfig(2),
                         waitForRcpIraReq(3),
                         waitForConfigRexReq(4),
                         waitOperationalAuxCore(5),
                         operationalAuxCore(6),
                         outOfService(7)
                        }
    MAX-ACCESS  read-only
    STATUS      current
    DESCRIPTION 
        "This attribute identifies the current operational 
         status with this Auxiliary CCAP Core. If the attribute
         IsPrincipal contains a value of 'true', this attribute 
         has no meaning since it only applies to Auxiliary Cores.
         
         other: This value is reported in cases not defined below

         authenticateToCore: The RPD is in the process of authenticating
         to the Auxiliary Core.

         gcpConfig: The RPD is in the process of being configured
         by the Auxiliary Core.

         waitForRcpIraReq: The RPD is waiting for the IRA message
         from the Auxiliary Core.

         waitForConfigRexReq: The RPD is waiting for the first 
         REX message from the Auxiliary Core.

         waitOperationalAuxCore: The RPD is waiting for the Auxiliary
         Core to make it operational.

         operationalAuxCore: The RPD is operational with this Auxiliary Core.

         outOfService: The Auxiliary Core has reported to the RPD that 
         it is out of service.

         Note that the indexing of the RPD's AuxCoreState table (TLV 87.4) 
         and the CoresConected object can differ. To correctly report the 
         AuxCoreRpdState the CCAP Core needs to read the AuxCoreState table
         and match the obtained results to the CoreConnected object entries
         by comparing the AuxCoreId (TLV 87.4.2) to the CoreId attribute." 
     ::= { docsRphyRpdDevCoresConnectedEntry 12 }

docsRphyRpdDevCoresConnectedResourceSetIndex OBJECT-TYPE
    SYNTAX      Unsigned32 (0..255)
    MAX-ACCESS  read-only
    STATUS      current
    DESCRIPTION 
        "This attribute reports the resource set 
         index used by the core."
    ::= { docsRphyRpdDevCoresConnectedEntry 13 }

docsRphyRpdDevCoresConnectedGcpBackupConnectionConfig OBJECT-TYPE
    SYNTAX      TruthValue
    MAX-ACCESS  read-only
    STATUS      current
    DESCRIPTION 
        "This attribute reports whether a GCP control connection
         is maintained to the Core when it is acting as a Backup Core."
    ::= { docsRphyRpdDevCoresConnectedEntry 14 }

docsRphyRpdDevCoresConnectedGcpConnectionStatus OBJECT-TYPE
    SYNTAX      INTEGER {
                         inactive(1),
                         connecting(2),
                         connected(3),
                         reconnecting(4)
                        }
    MAX-ACCESS  read-only
    STATUS      current
    DESCRIPTION 
        "This attribute reports the status of the GCP connection to the Core
         as seen by the RPD."
     ::= { docsRphyRpdDevCoresConnectedEntry 15 }

docsRphyRpdDevCoresConnectedGcpBackupCoreStatus OBJECT-TYPE
    SYNTAX      INTEGER {
                         waitForCoreMode(1),
                         active(2),
                         backup(3),
                         coreNotActing(4),
                         handover(5)
                        }
    MAX-ACCESS  read-only
    STATUS      current
    DESCRIPTION 
        "This attribute reports the operating mode of the Core
         as seen by the RPD."
     ::= { docsRphyRpdDevCoresConnectedEntry 16 }
     
docsRphyRpdDevCoresConnectedAuthenticationStatus OBJECT-TYPE
    SYNTAX      INTEGER {
                         other(0),
                         authenticated(1),
                         authFailed(2),
                         authNotPerformed(3)
                        }
    MAX-ACCESS  read-only
    STATUS      current
    DESCRIPTION 
        "This attribute reports the authentication status of the 
         selected CCAP Core.
         other: This value is reported in cases not defined below.
         authenticated: The RPD is authenticated with the selected CCAP Core.
         authFailed: RPD authentication with the selected CCAP Core has failed.
         authNotPerformed:RPD authentication with the selected CCAP Core 
         has not been performed."
     ::= { docsRphyRpdDevCoresConnectedEntry 17 }

        
-- ---------------------------------------------------------------------
-- RPD Capabilities Table
-- ---------------------------------------------------------------------

docsRphyRpdDevCapabilitiesTable OBJECT-TYPE
    SYNTAX      SEQUENCE OF DocsRphyRpdDevCapabilitiesEntry
    MAX-ACCESS  not-accessible
    STATUS      current
    DESCRIPTION
        "This table provides information about the principal 
         capabilities and constraints of the RPD."
    ::= { docsRphyRpdDevMibObjects 5 }


docsRphyRpdDevCapabilitiesEntry OBJECT-TYPE
    SYNTAX     DocsRphyRpdDevCapabilitiesEntry
    MAX-ACCESS not-accessible
    STATUS     current
    DESCRIPTION
        "The conceptual row of docsRphyRpdDevCapabilitiesTable."
    INDEX { docsRphyRpdDevInfoUniqueId }
    ::= { docsRphyRpdDevCapabilitiesTable 1 }


DocsRphyRpdDevCapabilitiesEntry ::= SEQUENCE
    {
    docsRphyRpdDevCapabNumDsPorts                 Unsigned32,
    docsRphyRpdDevCapabNumUsPorts                 Unsigned32,
    docsRphyRpdDevCapabNumTenGeNsPorts            Unsigned32,
    docsRphyRpdDevCapabNumOneGeNsPorts            Unsigned32,
    docsRphyRpdDevCapabNumDsScQamChans            Unsigned32,
    docsRphyRpdDevCapabNumDsOfdmChans             Unsigned32,
    docsRphyRpdDevCapabNumUsScQamChans            Unsigned32,
    docsRphyRpdDevCapabNumUsOfdmaChans            Unsigned32,
    docsRphyRpdDevCapabNumDsOob55d1Chans          Unsigned32,
    docsRphyRpdDevCapabNumUsOob55d1Chans          Unsigned32,
    docsRphyRpdDevCapabNumDsOob55d2Modules        Unsigned32,
    docsRphyRpdDevCapabNumUsOob55d2Demods         Unsigned32,
    docsRphyRpdDevCapabNumNdfChans                Unsigned32,
    docsRphyRpdDevCapabNumNdrChans                Unsigned32,
    docsRphyRpdDevCapabNumDsPspFlowsPerChan       Unsigned32,
    docsRphyRpdDevCapabNumUsPspFlowsPerChan       Unsigned32,
    docsRphyRpdDevCapabNumAsynchVideoChans        Unsigned32,
    docsRphyRpdDevCapabNumCwToneGens              Unsigned32,
    docsRphyRpdDevCapabLowestCwToneFreq           Unsigned32,
    docsRphyRpdDevCapabHighestCwToneFreq          Unsigned32,
    docsRphyRpdDevCapabMaxPwrDedCwTone            TenthdB,
    docsRphyRpdDevCapabQamAsPilot                 TruthValue,
    docsRphyRpdDevCapabSupportsUdpEncap           TruthValue,
    docsRphyRpdDevCapabSupportsFlowTags           TruthValue,
    docsRphyRpdDevCapabSupportsFreqTilt           TruthValue,
    docsRphyRpdDevCapabMaxTiltValue               TenthdB,
    docsRphyRpdDevCapabBufferDepthMonAlertSupp    BITS,
    docsRphyRpdDevCapabBufferDepthCfgSupp         BITS,
    docsRphyRpdDevCapabRpdUcdProcTime             Unsigned32,
    docsRphyRpdDevCapabRpdUcdChgNullGrtTime       Unsigned32,
    docsRphyRpdDevCapabMultiSectionTimingMerRep   INTEGER,
    docsRphyRpdDevCapabMinPwrDedCwTone            TenthdB,
    docsRphyRpdDevCapabMaxPwrQamCwTone            TenthdB,
    docsRphyRpdDevCapabMinPwrQamCwTone            TenthdB,
    docsRphyRpdDevCapabSupportsOpticalNodeRf      TruthValue,
    docsRphyRpdDevCapabMaxDsFrequency             Unsigned32,
    docsRphyRpdDevCapabMinDsFrequency             Unsigned32,
    docsRphyRpdDevCapabMaxBasePwr                 TenthdBmV, 
    docsRphyRpdDevCapabMinTiltValue               TenthdB,
    docsRphyRpdDevCapabMinPwrAdjustScQam          TenthdB,
    docsRphyRpdDevCapabMaxPwrAdjustScQam          TenthdB,
    docsRphyRpdDevCapabMinPwrAdjustOfdm           TenthdB,
    docsRphyRpdDevCapabMaxPwrAdjustOfdm           TenthdB,
    docsRphyRpdDevCapabVspSelector                SnmpAdminString,
    docsRphyRpdDevCapabMinBaseUsPowerTarLevel     TenthdBmV,
    docsRphyRpdDevCapabMaxBaseUsPowerTarLevel     TenthdBmV,
    docsRphyRpdDevCapabMinTarRxPowerAdjustScqam   TenthdB,
    docsRphyRpdDevCapabMaxTarRxPowerAdjustScqam   TenthdB,
    docsRphyRpdDevCapabMinTarRxPowerAdjustOfdma   TenthdB,
    docsRphyRpdDevCapabMaxTarRxPowerAdjustOfdma   TenthdB,
    docsRphyRpdDevCapabMinTarRxPowerAdjustNdr     TenthdB,
    docsRphyRpdDevCapabMaxTarRxPowerAdjustNdr     TenthdB, 
    docsRphyRpdDevCapabMaxDsPspSegCount           Unsigned32,
    docsRphyRpdDevCapabDirectDsFlowQueueMapping   TruthValue,
    docsRphyRpdDevCapabDsSchedulerPhbIdList       OCTET STRING,
    docsRphyRpdDevCapabRpdPendingEvRepQueueSize   Unsigned32,
    docsRphyRpdDevCapabRpdLocalEventLogSize       Unsigned32,
    docsRphyRpdDevCapabSupportsUsProfileQuery     TruthValue,
    docsRphyRpdDevCapabSupportsFlowTagIncrement   TruthValue,
    docsRphyRpdDevCapabMinBasePwr                 TenthdB,
    docsRphyRpdDevCapabNumCoresSupported          Unsigned32,
    docsRphyRpdDevCapabMaxDsOob55d1Frequency      Unsigned32,
    docsRphyRpdDevCapabSupportsDsOob55d2SecFreq   TruthValue,
    docsRphyRpdDevCapabMaxDsOob55d2Frequency      Unsigned32,
    docsRphyRpdDevCapabReportsOfdmConfigChangeCounts TruthValue
    }

docsRphyRpdDevCapabNumDsPorts OBJECT-TYPE
    SYNTAX      Unsigned32 (0..65535)
    MAX-ACCESS  read-only
    STATUS      current
    DESCRIPTION 
        "This attribute reports the number of Full Spectrum
         downstream unidirectional RF ports available on a
         non-Partial Spectrum-capable RPD. A Partial
         Spectrum-capable RPD can report a value greater
         than the actual number of implemented downstream RF
         ports. An RPD reports NumDsRfPorts as the maximum
         supported downstream RfPortIndex (TLV 12.1) plus one."
    REFERENCE 
        "Information Model Mapping: CM-SP-R-OSSI 
         DsCapabilities::NumDsRfPorts"
    ::= { docsRphyRpdDevCapabilitiesEntry 1 }
        
docsRphyRpdDevCapabNumUsPorts OBJECT-TYPE
    SYNTAX      Unsigned32 (0..65535)
    MAX-ACCESS  read-only
    STATUS      current
    DESCRIPTION 
        "This attribute reports the number of Full Spectrum
         upstream unidirectional RF ports available on a
         non-Partial Spectrum-capable RPD. A Partial
         Spectrum-capable RPD can report a value greater
         than the actual number of implemented upstream RF
         ports. An RPD reports NumUsRfPorts as the maximum
         supported upstream RfPortIndex (TLV 12.1) plus one."
    REFERENCE 
        "Information Model Mapping: CM-SP-R-OSSI 
         UsCapabilities::NumUsRfPorts"
    ::= { docsRphyRpdDevCapabilitiesEntry 2 }
        
docsRphyRpdDevCapabNumTenGeNsPorts OBJECT-TYPE
    SYNTAX      Unsigned32 (0..65535)
    MAX-ACCESS  read-only
    STATUS      current
    DESCRIPTION 
        "This attribute provides the number of 10 Gigabit 
         Ethernet ports supported by the RPD."
    REFERENCE 
        "Information Model Mapping: CM-SP-R-OSSI 
         NetworkingCapabilities::NumTenGeNsPorts"
    ::= { docsRphyRpdDevCapabilitiesEntry 3 }
        
docsRphyRpdDevCapabNumOneGeNsPorts OBJECT-TYPE
    SYNTAX      Unsigned32 (0..65535)
    MAX-ACCESS  read-only
    STATUS      current
    DESCRIPTION 
        "This attribute provides the number 1 Gigabit 
         Ethernet ports supported by the RPD."
    REFERENCE 
        "Information Model Mapping: CM-SP-R-OSSI 
         NetworkingCapabilities::NumOneGeNsPorts"
    ::= { docsRphyRpdDevCapabilitiesEntry 4 }
        
docsRphyRpdDevCapabNumDsScQamChans OBJECT-TYPE
    SYNTAX      Unsigned32 (0..65535)
    MAX-ACCESS  read-only
    STATUS      current
    DESCRIPTION 
        "On a non-Partial Spectrum-capable RPD, this attribute
         reports the number of downstream SC-QAM channels
         supported per downstream RF port. 
         On a Partial Spectrum-capable RPD, this attribute
         reports the maximum number of downstream SC-QAM
         channels supported on any downstream RF port of the
         RPD."
    REFERENCE 
        "Information Model Mapping: CM-SP-R-OSSI 
         DsCapabilities::NumDsScQamChannels"
    ::= { docsRphyRpdDevCapabilitiesEntry 5 }
        
docsRphyRpdDevCapabNumDsOfdmChans OBJECT-TYPE
    SYNTAX      Unsigned32 (0..65535)
    MAX-ACCESS  read-only
    STATUS      current
    DESCRIPTION 
        "On a non-Partial Spectrum-capable RPD, this attribute
         reports the number of downstream OFDM channels
         supported per downstream RF port. 
	     On a Partial Spectrum-capable RPD, this attribute reports
         the maximum number of downstream OFDM channels supported
         on any downstream RF port of the RPD."
    REFERENCE 
        "Information Model Mapping: CM-SP-R-OSSI 
         DsCapabilities::NumDsOfdmChannels"
    ::= { docsRphyRpdDevCapabilitiesEntry 6 }
        
docsRphyRpdDevCapabNumUsScQamChans OBJECT-TYPE
    SYNTAX      Unsigned32 (0..65535)
    MAX-ACCESS  read-only
    STATUS      current
    DESCRIPTION 
        "On a non-Partial Spectrum-capable RPD, this
         attribute reports the number of upstream SC-QAM
         channels supported per upstream RF port.
         On a Partial Spectrum-capable RPD, this attribute
         reports the maximum number of upstream SC-QAM channels
         supported on any upstream RF port of the RPD. 
"
    REFERENCE 
        "Information Model Mapping: CM-SP-R-OSSI 
         UsCapabilities::NumUsSqQamChannels"
    ::= { docsRphyRpdDevCapabilitiesEntry 7 }
        
docsRphyRpdDevCapabNumUsOfdmaChans OBJECT-TYPE
    SYNTAX      Unsigned32 (0..65535)
    MAX-ACCESS  read-only
    STATUS      current
    DESCRIPTION 
        "On a non-Partial Spectrum-capable RPD, this
         attribute reports the number of upstream OFDMA
         channels supported per upstream RF port. 
	     On a Partial Spectrum-capable RPD, this attribute
         reports the maximum number of upstream OFDMA channels
         supported on any upstream RF port of the RPD."
    REFERENCE 
        "Information Model Mapping: CM-SP-R-OSSI 
         UsCapabilities::NumUsOfdmaChannels"
    ::= { docsRphyRpdDevCapabilitiesEntry 8 }
        
docsRphyRpdDevCapabNumDsOob55d1Chans OBJECT-TYPE
    SYNTAX      Unsigned32 (0..65535)
    MAX-ACCESS  read-only
    STATUS      current
    DESCRIPTION 
        "This attribute represents the number of SCTE-55-1 forward
         (downstream) channels supported on any DS RF port of the RPD. 
         The RPD must report a value of 1 when it supports a single 
         SCTE 55-1 forward channel per DS RF port. The RPD must report 
         a value of 2 when it supports two SCTE 55-1 forward channels 
         per DS RF port."
    REFERENCE 
        "Information Model Mapping: CM-SP-R-OSSI 
         DsCapabilities::NumDsOob55d1Channels"
    ::= { docsRphyRpdDevCapabilitiesEntry 9 }
        
docsRphyRpdDevCapabNumUsOob55d1Chans OBJECT-TYPE
    SYNTAX      Unsigned32 (0..65535)
    MAX-ACCESS  read-only
    STATUS      current
    DESCRIPTION 
        "On a non-Partial Spectrum-capable RPD, this attribute reports
         the number of upstream SCTE 55-1 channels supported per
         upstream RF port.
         On a Partial Spectrum-capable RPD, this attribute reports the
         maximum number of upstream SCTE 55-1 channels supported on
         any upstream RF port of the RPD."
    REFERENCE 
        "Information Model Mapping: CM-SP-R-OSSI 
         UsCapabilities::NumUsOob55d1Channels"
    ::= { docsRphyRpdDevCapabilitiesEntry 10 }
        
docsRphyRpdDevCapabNumDsOob55d2Modules OBJECT-TYPE
    SYNTAX      Unsigned32 (0..65535)
    MAX-ACCESS  read-only
    STATUS      current
    DESCRIPTION 
        "This attribute provides the number of SCTE 55-2 modules 
         supported."
    REFERENCE 
        "Information Model Mapping: CM-SP-R-OSSI 
         DsCapabilities::NumDsOob55d2Modules"
    ::= { docsRphyRpdDevCapabilitiesEntry 11 }
        
docsRphyRpdDevCapabNumUsOob55d2Demods OBJECT-TYPE
    SYNTAX      Unsigned32 (0..65535)
    MAX-ACCESS  read-only
    STATUS      current
    DESCRIPTION 
        "This attribute provides the number of upstream demodulators 
         per SCTE 55-2 modules supported."
    REFERENCE 
        "Information Model Mapping: CM-SP-R-OSSI 
         UsCapabilities::NumUsOob55d2Demods"
    ::= { docsRphyRpdDevCapabilitiesEntry 12 }
        
docsRphyRpdDevCapabNumNdfChans OBJECT-TYPE
    SYNTAX      Unsigned32 (0..65535)
    MAX-ACCESS  read-only
    STATUS      current
    DESCRIPTION 
        "On a non-Partial Spectrum-capable RPD, this attribute
         reports the number of Narrowband Digital Forward (NDF)
         channels supported per downstream RF port.
         On a Partial Spectrum-capable RPD, this attribute
         reports the maximum number of Narrowband Digital
         Forward (NDF) channels supported on any upstream RF
         port of the RPD."
    REFERENCE 
        "Information Model Mapping: CM-SP-R-OSSI 
         DsCapabilities::NumNdfChannels"
    ::= { docsRphyRpdDevCapabilitiesEntry 13 }
        
docsRphyRpdDevCapabNumNdrChans OBJECT-TYPE
    SYNTAX      Unsigned32 (0..65535)
    MAX-ACCESS  read-only
    STATUS      current
    DESCRIPTION 
        "On a non-Partial Spectrum-capable RPD, this attribute
         reports the number of Narrowband Digital Return (NDR)
         channels supported per upstream RF port.
         On a Partial Spectrum-capable RPD, this attribute
         reports the maximum number of Narrowband Digital Return
         (NDR) channels supported on any upstream RF port of the
         RPD."
    REFERENCE 
        "Information Model Mapping: CM-SP-R-OSSI 
         UsCapabilities::NumNdrChannels"
    ::= { docsRphyRpdDevCapabilitiesEntry 14 }
          
docsRphyRpdDevCapabNumDsPspFlowsPerChan OBJECT-TYPE
    SYNTAX      Unsigned32 (0..255)
    MAX-ACCESS  read-only
    STATUS      current
    DESCRIPTION 
        "This attribute provides the number of distinct PSP flows
         supported by the RPD on downstream data pseudowires."
    REFERENCE 
        "Information Model Mapping: CM-SP-R-OSSI 
         DsCapabilities::NumDsPspFlowsPerChan"
    ::= { docsRphyRpdDevCapabilitiesEntry 15 }
        
docsRphyRpdDevCapabNumUsPspFlowsPerChan OBJECT-TYPE
    SYNTAX      Unsigned32 (0..255)
    MAX-ACCESS  read-only
    STATUS      current
    DESCRIPTION 
        "This attribute provides the number of distinct PSP flows
         supported by the RPD on upstream data pseudowires."
    REFERENCE 
        "Information Model Mapping: CM-SP-R-OSSI 
         UsCapabilities::NumUsPspFlowsPerChan"
    ::= { docsRphyRpdDevCapabilitiesEntry 16 }
        
docsRphyRpdDevCapabNumAsynchVideoChans OBJECT-TYPE
    SYNTAX      Unsigned32 (0..255)
    MAX-ACCESS  read-only
    STATUS      current
    DESCRIPTION 
        "This attribute provides the number of asynchronous 
         MPEG video channels supported per downstream RF port."
    REFERENCE 
        "Information Model Mapping: CM-SP-R-OSSI 
         DsCapabilities::NumAsynchVideoChannels"
    ::= { docsRphyRpdDevCapabilitiesEntry 17 }
        
docsRphyRpdDevCapabNumCwToneGens OBJECT-TYPE
    SYNTAX      Unsigned32 (0..255)
    MAX-ACCESS  read-only
    STATUS      current
    DESCRIPTION 
        "This attribute provides the number of CW tone generators
         supported per downstream RF port."
    REFERENCE 
        "Information Model Mapping: CM-SP-R-OSSI 
         ToneCapabilities::NumCwToneGenerators"
    ::= { docsRphyRpdDevCapabilitiesEntry 18 }
        
docsRphyRpdDevCapabLowestCwToneFreq OBJECT-TYPE
    SYNTAX      Unsigned32
    UNITS       "Hz"
    MAX-ACCESS  read-only
    STATUS      current
    DESCRIPTION 
        "This attribute provides the lowest frequency supported
         by the CW tone generators."
    REFERENCE 
        "Information Model Mapping: CM-SP-R-OSSI 
         ToneCapabilities::LowestCwToneFreq"
    ::= { docsRphyRpdDevCapabilitiesEntry 19 }
        
docsRphyRpdDevCapabHighestCwToneFreq OBJECT-TYPE
    SYNTAX      Unsigned32
        UNITS       "Hz"
    MAX-ACCESS  read-only
    STATUS      current
    DESCRIPTION 
        "This attribute provides the highest frequency supported
         by the CW tone generators."
    REFERENCE 
        "Information Model Mapping: CM-SP-R-OSSI 
         ToneCapabilities::HighestCwToneFreq"
    ::= { docsRphyRpdDevCapabilitiesEntry 20 }
        
docsRphyRpdDevCapabMaxPwrDedCwTone OBJECT-TYPE
    SYNTAX      TenthdB (0..65535)
    UNITS       "dB"
    MAX-ACCESS  read-only
    STATUS      current
    DESCRIPTION 
        "The attribute allows the RPD to inform the CCAP Core what 
         is the maximum power level relative to the RF Port's BasePower 
         that is supported by its dedicated CW tone generators."
    REFERENCE 
        "Information Model Mapping: CM-SP-R-OSSI 
         ToneCapabilities::MaxPwrDedCwTone"
    ::= { docsRphyRpdDevCapabilitiesEntry 21 }
        
docsRphyRpdDevCapabQamAsPilot OBJECT-TYPE
    SYNTAX      TruthValue
    MAX-ACCESS  read-only
    STATUS      current
    DESCRIPTION 
        "This attribute indicates if a QAM channel can be configured
         as a CW tone. A value of true indicates a QAM channel can 
         be configured as a CW tone. A value of false indicates a 
         QAM channel cannot be configured as a CW tone."
    REFERENCE 
        "Information Model Mapping: CM-SP-R-OSSI 
         ToneCapabilities::QamAsPilot"
    ::= { docsRphyRpdDevCapabilitiesEntry 22 }
        
docsRphyRpdDevCapabSupportsUdpEncap OBJECT-TYPE
    SYNTAX      TruthValue
    MAX-ACCESS  read-only
    STATUS      current
    DESCRIPTION 
        "This attribute reports whether the RPD supports UDP 
         encapsulation on L2TPv3 pseudowires. A value of true 
         indicates the RPD supports UDP encapsulation on L2TPv3 
         pseudowires. A value of false indicates the RPD does not 
         support UDP encapsulation on L2TPv3 pseudowires."
    REFERENCE 
        "Information Model Mapping: CM-SP-R-OSSI 
         NetworkingCapabilities::SupportsUdpEncap"
    ::= { docsRphyRpdDevCapabilitiesEntry 23 }

docsRphyRpdDevCapabSupportsFlowTags OBJECT-TYPE
    SYNTAX      TruthValue
    MAX-ACCESS  read-only
    STATUS      current
    DESCRIPTION 
        "This attribute indicates Flow Tags support capability. If 
         the attribute returns a value of true, the RPD supports 
         Flow Tags on OFDMA channels. A Flow Tag is a 32-bit 
         identifier of a MAC hardware resource (typically a Service 
         Flow). The Flow Tag can be assigned to the scheduled SID by 
         the CCAP Core. The RPD provides Flow Tags in UEPI headers 
         for OFDMA channels. If the attribute returns a value of 
         false, the RPD does not support Flow Tags."
    REFERENCE 
        "Information Model Mapping: CM-SP-R-OSSI 
         UsCapabilities::SupportsFlowTags"
    ::= { docsRphyRpdDevCapabilitiesEntry 24 }
        
docsRphyRpdDevCapabSupportsFreqTilt OBJECT-TYPE
    SYNTAX      TruthValue
    MAX-ACCESS  read-only
    STATUS      current
    DESCRIPTION 
        "This attribute indicates Frequency Tilt support capability. 
         If the attribute returns a value of true, the RPD supports 
         Frequency Tilt settings on DS RF Ports. If the attribute 
         returns a value of false, the RPD does not support 
         Frequency Tilt settings."
    REFERENCE 
        "Information Model Mapping: CM-SP-R-OSSI 
         DsPowerCapabilities::SupportsFrequencyTilt"
    ::= { docsRphyRpdDevCapabilitiesEntry 25 }
        
docsRphyRpdDevCapabMaxTiltValue OBJECT-TYPE
    SYNTAX      TenthdB (0..65535)
    UNITS       "dB"
    MAX-ACCESS  read-only
    STATUS      current
    DESCRIPTION 
        "This attribute indicates the maximum value of tilt settings that 
         the RPD supports."
    REFERENCE 
        "Information Model Mapping: CM-SP-R-OSSI 
         DsPowerCapabilities::MaxTiltValue"
    ::= { docsRphyRpdDevCapabilitiesEntry 26 }
        
docsRphyRpdDevCapabBufferDepthMonAlertSupp OBJECT-TYPE
    SYNTAX       BITS {
                       ofdmChannels(0),
                       scQamDocsisChannels(1),
                       scQamVideoChannels(2),
                       ndfChannels(3),
                       scte551Channels(4),
                       scte552Channels(5)
                      }
    MAX-ACCESS  read-only
    STATUS      current
    DESCRIPTION 
        "This attribute indicates buffer depth monitoring alert 
         supported by the RPD.  For each bit set to 1, the RPD 
         is capable of monitoring buffer depth on the corresponding 
         types of downstream channels."
    REFERENCE 
        "Information Model Mapping: CM-SP-R-OSSI 
         BufferMonitoringCapabilities::BufferDepthMonitorAlertSupport"
    ::= { docsRphyRpdDevCapabilitiesEntry 27 }
        
docsRphyRpdDevCapabBufferDepthCfgSupp OBJECT-TYPE
    SYNTAX      BITS {
                      ofdmChannels(0),
                      scQamDocsisChannels(1)
                     }
    MAX-ACCESS  read-only
    STATUS      current
    DESCRIPTION 
        "This attribute indicates configuration of the output buffer 
         depth supported by the RPD.  This capability is only 
         applicable to DOCSIS downstream channels. For each bit set 
         to 1, the RPD is capable of configuring output buffer depth 
         of the corresponding types of downstream channels."
    REFERENCE 
        "Information Model Mapping: CM-SP-R-OSSI 
         BufferMonitoringCapabilities::BufferDepthConfigurationSupport"
    ::= { docsRphyRpdDevCapabilitiesEntry 28 }
        
docsRphyRpdDevCapabRpdUcdProcTime OBJECT-TYPE
    SYNTAX      Unsigned32 (0..65535)
    MAX-ACCESS  read-only
    STATUS      current
    DESCRIPTION 
        "This attribute indicates the minimum interval needed by the 
         RPD to process a UCD message received via GCP. This 
         interval is equivalent to CM UCD processing time defined in 
         MULPIv4.0 but its duration can be longer. The maximum value 
         of the RPD UCD Processing time is 50000 usec. The minimum 
         value RPD UCD Processing time is equal to CM UCD processing 
         time (1500 usec for each changed SC-QAM channel or 2000 usec 
         for each changed upstream OFDMA channel) defined in 
         MULPIv4.0."
    REFERENCE 
        "Information Model Mapping: CM-SP-R-OSSI 
         UsCapabilities::RpdUcdProcessingTime"
    ::= { docsRphyRpdDevCapabilitiesEntry 29 }
        
docsRphyRpdDevCapabRpdUcdChgNullGrtTime OBJECT-TYPE
    SYNTAX      Unsigned32 (0..65535)
    MAX-ACCESS  read-only
    STATUS      current
    DESCRIPTION 
        "This attribute indicates the minimum Null grant interval 
         needed by the RPD in the first MAP with incremented UCD 
         change count. The RPD uses the Null grant in the first 
         MAP Message to programs registers of its burst receiver 
         during this interval. The maximum value of the RPD UCD 
         Change Null Grant Time is 4000 usec for each changed channel.
         The minimum value of the RPD UCD Change Null Grant Time is 
         defined in MULPIv4.0."
    REFERENCE 
        "Information Model Mapping: CM-SP-R-OSSI 
         UsCapabilities::RpdUcdChgNullGrtTime"
    ::= { docsRphyRpdDevCapabilitiesEntry 30 }
        
docsRphyRpdDevCapabMultiSectionTimingMerRep OBJECT-TYPE
    SYNTAX      INTEGER {
                         doesNotSupport(0),
                         equallySpacedNonOverlapping(1),
                         fullyFlexible(2)
                        }
    MAX-ACCESS  read-only
    STATUS      current
    DESCRIPTION 
        "This attribute indicates whether the RPD supports 
         Multi-Section Timing and MER reporting as opposed to just 
         reporting a single average Timing and MER.  More detail 
         is documented in the UEPI Probe Pseudowire format of 
         R-UEPI.
         Valid values are listed below:
         
         doesNotSupport(0) The RPD does not support Multi-Section Timing 
         and MER Reporting
         
         equallySpacedNonOverlapping(1) The RPD supports equally spaced 
         non-overlapping sections
         
         fullyFlexible(2) The RPD supports fully flexible sections and 
         spacing of non-overlapping sections."
    REFERENCE 
        "Information Model Mapping: CM-SP-R-OSSI 
         UsCapabilities::MultiSectionTimingMerReporting"
    ::= { docsRphyRpdDevCapabilitiesEntry 31 }

docsRphyRpdDevCapabMinPwrDedCwTone OBJECT-TYPE
    SYNTAX      TenthdB (-32768..32767)
    UNITS       "dB"
    MAX-ACCESS  read-only
    STATUS      current
    DESCRIPTION
        "The object allows the RPD to inform the CCAP Core what is
         the minimum power level relative to the RF Port's BasePower
         that is supported by its dedicated CW tone generators."
    REFERENCE 
        "Information Model Mapping: CM-SP-R-OSSI 
         ToneCapabilities::MinPwrDedCwTone"
    ::= { docsRphyRpdDevCapabilitiesEntry 32 }

docsRphyRpdDevCapabMaxPwrQamCwTone OBJECT-TYPE
    SYNTAX      TenthdB (0..65535)
    UNITS       "dB"
    MAX-ACCESS  read-only
    STATUS      current
    DESCRIPTION
        "The object allows the RPD to inform the CCAP Core what is
         the maximum power level setting relative to the RF Port's
         BasePower that is supported by its QAM channels operating
         as CW tone generators."
    REFERENCE 
        "Information Model Mapping: CM-SP-R-OSSI 
         ToneCapabilities::MaxPwrQamCwTone"
    ::= { docsRphyRpdDevCapabilitiesEntry 33 }


docsRphyRpdDevCapabMinPwrQamCwTone OBJECT-TYPE
    SYNTAX      TenthdB (-32768..32767)
    UNITS       "dB"
    MAX-ACCESS  read-only
    STATUS      current
    DESCRIPTION
        "The object allows the RPD to inform the CCAP Core what is
         the minimum power level setting relative to the RF Port's
         BasePower that is supported by its QAM channels operating
         as CW tone generators."
    REFERENCE 
        "Information Model Mapping: CM-SP-R-OSSI 
         ToneCapabilities::MinPwrQamCwTone"
    ::= { docsRphyRpdDevCapabilitiesEntry 34 }
     
docsRphyRpdDevCapabSupportsOpticalNodeRf OBJECT-TYPE
    SYNTAX      TruthValue
    MAX-ACCESS  read-only
    STATUS      current
    DESCRIPTION
        "This attribute reports whether the RPD supports the RF 
         technology for an optical node.

         The RPD reports 'false' if it complies with the main section of 
         the [DRFI] specification and the main section of the [PHYv4.0]
         specification. In this case the RPD does not support optical node 
         technology (i.e., RPD is a Remote PHY Shelf).

         The RPD reports 'true' if it complies with Annex E and Annex F of
         [R-PHY] and [DRFI] specification Annex D. In this case the RPD supports
         optical node RF technology (i.e., RPD is a Remote PHY Node)."
    REFERENCE 
        "Information Model Mapping: CM-SP-R-OSSI 
         MiscellaneousCapabilities::SupportsOpticalNodeRf"
    ::= {docsRphyRpdDevCapabilitiesEntry 35 } 
     
docsRphyRpdDevCapabMaxDsFrequency OBJECT-TYPE
    SYNTAX      Unsigned32
    UNITS       "Hz"
    MAX-ACCESS  read-only
    STATUS      current
    DESCRIPTION
        "This attribute reports the maximum frequency of any downstream
         signal that the RPD supports on its DS RF port. This attribute
         defines the highest frequency of the encompassed spectrum of the
         highest frequency downstream channel or OOB signal."
    REFERENCE 
        "Information Model Mapping: CM-SP-R-OSSI 
         DsCapabilities::MaxDsFrequency"
    ::= { docsRphyRpdDevCapabilitiesEntry 36 }

docsRphyRpdDevCapabMinDsFrequency OBJECT-TYPE
    SYNTAX      Unsigned32
    UNITS       "Hz"
    MAX-ACCESS  read-only
    STATUS      current
    DESCRIPTION
        "This attribute reports the minimum frequency of any downstream
         signal that the RPD supports on its DS RF port. . This attribute
         defines the lowest frequency of the encompassed spectrum of the
         lowest frequency downstream channel or OOB signal."
     REFERENCE 
        "Information Model Mapping: CM-SP-R-OSSI 
         DsCapabilities::MinDsFrequency"
    ::= { docsRphyRpdDevCapabilitiesEntry 37 }

docsRphyRpdDevCapabMaxBasePwr OBJECT-TYPE
    SYNTAX      TenthdBmV (0..65535)
    UNITS       "dBmV/6MHz"
    MAX-ACCESS  read-only
    STATUS      current
    DESCRIPTION
        "This attribute reports the maximum power level setting that the
         RPD supports for downstream RF port."
    REFERENCE 
        "Information Model Mapping: CM-SP-R-OSSI 
         DsPowerCapabilities::MaxBasePower"
    ::= { docsRphyRpdDevCapabilitiesEntry 38  }
  
     
docsRphyRpdDevCapabMinTiltValue OBJECT-TYPE
    SYNTAX      TenthdB (-32768..32767)
    UNITS       "dB"
    MAX-ACCESS  read-only
    STATUS      current
    DESCRIPTION
        "This attribute reports the minimum value of the tilt setting that
         the RPD supports. Note that the RPD can report this value as a
         negative number."
    REFERENCE 
        "Information Model Mapping: CM-SP-R-OSSI 
         DsPowerCapabilities::MinTiltValue"
    ::= {  docsRphyRpdDevCapabilitiesEntry 39 }


docsRphyRpdDevCapabMinPwrAdjustScQam OBJECT-TYPE
    SYNTAX      TenthdB (-32768..32767)
    UNITS       "dB"
    MAX-ACCESS  read-only
    STATUS      current
    DESCRIPTION
        "This attribute reports the minimum power adjustment value that the
         RPD supports for downstream SC-QAM channels."
    REFERENCE 
        "Information Model Mapping: CM-SP-R-OSSI 
         DsPowerCapabilities::MinPowerAdjustScQam"
    ::= { docsRphyRpdDevCapabilitiesEntry 40 }

docsRphyRpdDevCapabMaxPwrAdjustScQam OBJECT-TYPE
    SYNTAX      TenthdB (0..65535)
    UNITS       "dB"
    MAX-ACCESS  read-only
    STATUS      current
    DESCRIPTION
        "This attribute reports the maximum power adjustment that the RPD
         supports for downstream SC-QAM channel."
    REFERENCE 
        "Information Model Mapping: CM-SP-R-OSSI 
         DsPowerCapabilities::MaxPowerAdjustScQam"
    ::= { docsRphyRpdDevCapabilitiesEntry 41 }


docsRphyRpdDevCapabMinPwrAdjustOfdm OBJECT-TYPE
    SYNTAX      TenthdB  (-32768..32767)
    UNITS       "dB"
    MAX-ACCESS  read-only
    STATUS      current
    DESCRIPTION
        "This attribute reports the minimum power adjustment value that the
         RPD supports for downstream OFDM channels."
    REFERENCE 
        "Information Model Mapping: CM-SP-R-OSSI 
         DsPowerCapabilities::MinPowerAdjustOfdm"
    ::= { docsRphyRpdDevCapabilitiesEntry 42 }

     
docsRphyRpdDevCapabMaxPwrAdjustOfdm OBJECT-TYPE
    SYNTAX      TenthdB (0..65535)
    UNITS       "dB"
    MAX-ACCESS  read-only
    STATUS      current
    DESCRIPTION
        "This attribute reports the maximum power adjustment that the RPD
         supports for downstream OFDM channels."
    REFERENCE 
        "Information Model Mapping: CM-SP-R-OSSI 
         DsPowerCapabilities::MaxPowerAdjustOfdm"
    ::= {  docsRphyRpdDevCapabilitiesEntry 43 }

docsRphyRpdDevCapabVspSelector OBJECT-TYPE
    SYNTAX      SnmpAdminString
    MAX-ACCESS  read-only
    STATUS      deprecated
    DESCRIPTION
        "This attribute contains the Vendor-Specific Pre-configuration 
         (VSP) Selector advertised by the RPD, defined as a human 
         readable string. This attribute is used by the Principal 
         CCAP Core to match the RPD to VSP configuration maintained 
         on the CCAP Core and to deliver VSP configuration to the RPD 
         during initialization. If the RPD does not support VSP the 
         RPD communicates VSP as a zero-length string."
    ::= {  docsRphyRpdDevCapabilitiesEntry 44 }


docsRphyRpdDevCapabMinBaseUsPowerTarLevel OBJECT-TYPE
    SYNTAX      TenthdBmV (-32768..32767)  
    UNITS       "dBmV/1.6MHz"
    MAX-ACCESS  read-only
    STATUS      current
    DESCRIPTION
        "This attribute reports the minimum value of the base target power 
         reference level for upstream signals received on all upstream channels
         on an RF port that the RPD supports with a precision of 0.1 dBmV per 1.6MHz."
    REFERENCE 
        "Information Model Mapping: CM-SP-R-OSSI 
         UsPowerCapabilities::MinBaseUsPowerTargetLevel"
    ::= { docsRphyRpdDevCapabilitiesEntry 45 }

docsRphyRpdDevCapabMaxBaseUsPowerTarLevel OBJECT-TYPE
    SYNTAX      TenthdBmV (-32768..32767)  
    UNITS       "dBmV/1.6MHz"
    MAX-ACCESS  read-only
    STATUS      current
    DESCRIPTION
        "This attribute reports the maximum value of the base target power
         reference level for upstream signals received on all upstream channels
         on an RF port that the RPD supports with a precision of 0.1 dBmV per 1.6Mhz."
    REFERENCE 
        "Information Model Mapping: CM-SP-R-OSSI 
         UsPowerCapabilities::MaxBaseUsPowerTargetLevel"
    ::= { docsRphyRpdDevCapabilitiesEntry 46 }

docsRphyRpdDevCapabMinTarRxPowerAdjustScqam OBJECT-TYPE
    SYNTAX      TenthdB (-32768..32767)  
    UNITS       "dB"
    MAX-ACCESS  read-only
    STATUS      current
    DESCRIPTION
        "This attribute reports the minimum power adjustment
         to the base target power level that the RPD supports
         for SC-QAM channels."
    REFERENCE 
        "Information Model Mapping: CM-SP-R-OSSI 
         UsPowerCapabilities::MinTargetRxPowerAdjustScqam"
    ::= { docsRphyRpdDevCapabilitiesEntry 47 }

docsRphyRpdDevCapabMaxTarRxPowerAdjustScqam OBJECT-TYPE
    SYNTAX      TenthdB (-32768..32767)  
    UNITS       "dB"
    MAX-ACCESS  read-only
    STATUS      current
    DESCRIPTION
        "This attribute reports the maximum power adjustment
         to the base target power level that the RPD supports
         for SC-QAM channels."
    REFERENCE 
        "Information Model Mapping: CM-SP-R-OSSI 
         UsPowerCapabilities::MaxTargetRxPowerAdjustScqam"
    ::= { docsRphyRpdDevCapabilitiesEntry 48 }

docsRphyRpdDevCapabMinTarRxPowerAdjustOfdma OBJECT-TYPE
    SYNTAX      TenthdB (-32768..32767)  
    UNITS       "dB"
    MAX-ACCESS  read-only
    STATUS      current
    DESCRIPTION
        "This attribute reports the minimum power adjustment
         to the base target power level that the RPD supports
         for OFDMA channels."
    REFERENCE 
        "Information Model Mapping: CM-SP-R-OSSI 
         UsPowerCapabilities::MinTargetRxPowerAdjustOfdma"
    ::= { docsRphyRpdDevCapabilitiesEntry 49 }

docsRphyRpdDevCapabMaxTarRxPowerAdjustOfdma OBJECT-TYPE
    SYNTAX      TenthdB (-32768..32767)  
    UNITS       "dB"
    MAX-ACCESS  read-only
    STATUS      current
    DESCRIPTION
        "This attribute reports the maximum power adjustment
         to the base target power level that the RPD supports
         for OFDMA channels."
    REFERENCE 
        "Information Model Mapping: CM-SP-R-OSSI 
         UsPowerCapabilities::MaxTargetRxPowerAdjustOfdma"
    ::= { docsRphyRpdDevCapabilitiesEntry 50 }

docsRphyRpdDevCapabMinTarRxPowerAdjustNdr OBJECT-TYPE
    SYNTAX      TenthdB (-32768..32767)  
    UNITS       "dB"
    MAX-ACCESS  read-only
    STATUS      current
    DESCRIPTION
        "This attribute reports the minimum power adjustment
         to the base target power level that the RPD supports
         for NDR channels."
    REFERENCE 
        "Information Model Mapping: CM-SP-R-OSSI 
         UsPowerCapabilities::MinTargetRxPowerAdjustNdr"
    ::= { docsRphyRpdDevCapabilitiesEntry 51 }

docsRphyRpdDevCapabMaxTarRxPowerAdjustNdr OBJECT-TYPE
    SYNTAX      TenthdB (-32768..32767)  
    UNITS       "dB"
    MAX-ACCESS  read-only
    STATUS      current
    DESCRIPTION
        "This attribute reports the maximum power adjustment
         to the base target power level that the RPD supports
         for NDR channels."
    REFERENCE 
        "Information Model Mapping: CM-SP-R-OSSI 
         UsPowerCapabilities::MaxTargetRxPowerAdjustNdr"
    ::= { docsRphyRpdDevCapabilitiesEntry 52 }

docsRphyRpdDevCapabMaxDsPspSegCount OBJECT-TYPE
    SYNTAX      Unsigned32 (10..255)
    MAX-ACCESS  read-only
    STATUS      current
    DESCRIPTION
        "This attribute reports how many PSP segments the RPD 
         can support in a packet received on downstream PSP pseudowires."
    REFERENCE 
        "Information Model Mapping: CM-SP-R-OSSI 
         NetworkingCapabilities::MaxDsPspSegCount"
    ::= {  docsRphyRpdDevCapabilitiesEntry 53 }

docsRphyRpdDevCapabDirectDsFlowQueueMapping OBJECT-TYPE
    SYNTAX      TruthValue  
    MAX-ACCESS  read-only
    STATUS      current
    DESCRIPTION
        "This attribute reports whether the RPD supports direct mapping
         of downstream PSP flows to strict priority queues. [R-DEPI] 
         provides more detailed information about direct mapping 
         of downstream PSP flows to strict priority queues.The RPD reports a 
         value of false(0) when it does not support direct mapping of 
         downstream PSP flows to strict priority queues.The RPD reports a 
         value of true(1) when it supports direct mapping of downstream 
         PSP flows to strict priority queues."
    REFERENCE 
        "Information Model Mapping: CM-SP-R-OSSI 
         NetworkingCapabilities::DirectDsFlowQueueMapping"
    ::= {  docsRphyRpdDevCapabilitiesEntry 54 }

docsRphyRpdDevCapabDsSchedulerPhbIdList OBJECT-TYPE
    SYNTAX      OCTET STRING 
    MAX-ACCESS  read-only
    STATUS      current
    DESCRIPTION
        "This attribute reports the list of PHB-IDs supported
         by the RPDs downstream scheduler. [R-DEPI] provides 
         more detailed information about PHB-IDs for the RPDs 
         downstream scheduler. The value of this attribute is a 
         hexadecimal string in which six LSBs of each byte contain 
         a single PHB-ID that is supported by the RPDs scheduler."
    REFERENCE 
        "Information Model Mapping: CM-SP-R-OSSI 
         NetworkingCapabilities::DsSchedulerPhbIdList"
    ::= {  docsRphyRpdDevCapabilitiesEntry 55 }

docsRphyRpdDevCapabRpdPendingEvRepQueueSize OBJECT-TYPE
    SYNTAX      Unsigned32
    MAX-ACCESS  read-only
    STATUS      current
    DESCRIPTION
        "This attribute reports the size of the RPDs 
         Pending Event Report Queue."
    REFERENCE 
        "Information Model Mapping: CM-SP-R-OSSI 
         LogCapabilities::RpdPendingEvQueueSize"
    ::= {  docsRphyRpdDevCapabilitiesEntry 56 }

docsRphyRpdDevCapabRpdLocalEventLogSize OBJECT-TYPE
    SYNTAX      Unsigned32
    MAX-ACCESS  read-only
    STATUS      current
    DESCRIPTION
        "This attribute reports the size of the 
         RPDs Local Event Log."
    REFERENCE 
        "Information Model Mapping: CM-SP-R-OSSI 
         LogCapabilities::RpdLocalEventLogSize"
    ::= {  docsRphyRpdDevCapabilitiesEntry 57 }

docsRphyRpdDevCapabSupportsUsProfileQuery OBJECT-TYPE
    SYNTAX      TruthValue
    MAX-ACCESS  read-only
    STATUS      current
    DESCRIPTION
        "This attribute reports whether the RPD supports 
         UsScQamProfileQuery (TLV 150) and UsOfdmaConfigQuery 
         (TLV 151) via  UsScQamProfileResponse (TLV 152) and 
         UsOfdmaConfigResponse (TLV 153). These TLVs allow the 
         RPD to report various unique upstream burst receiver 
         parameters to the CCAP Core. The RPD reports a value of 
         false(0) when it does not support the upstream profile 
         query TLVs."
    REFERENCE 
        "Information Model Mapping: CM-SP-R-OSSI 
         UsCapabilities::SupportsUsProfileQuery"
    ::= {  docsRphyRpdDevCapabilitiesEntry 58 }
    
docsRphyRpdDevCapabSupportsFlowTagIncrement OBJECT-TYPE
    SYNTAX      TruthValue
    MAX-ACCESS  read-only
    STATUS      current
    DESCRIPTION
        "This attribute reports whether the RPD supports the 
         FlowTagIncrement TLV.
         
         The RPD reports a value of 'false' when it does not 
         support the FlowTagIncrement TLV and will
         always set the flow tag of all SIDs in a SidQos 
         TLV to the same value.

         The RPD reports a value of 'true' when it supports
         the FlowTagIncrement TLV."
    REFERENCE 
        "Information Model Mapping: CM-SP-R-OSSI 
         UsCapabilities::SupportsFlowTagIncrement"
    ::= {  docsRphyRpdDevCapabilitiesEntry 59 }
    
docsRphyRpdDevCapabMinBasePwr OBJECT-TYPE
    SYNTAX      TenthdB (0..65535)
    UNITS       "dBmV/6MHz"
    MAX-ACCESS  read-only
    STATUS      current
    DESCRIPTION
        "This attribute reports the minimum power level setting that
         the RPD supports for a downstream RF port."
    REFERENCE 
        "Information Model Mapping: CM-SP-R-OSSI 
         DsPowerCapabilities::MinBasePower"
    ::= { docsRphyRpdDevCapabilitiesEntry 60  }
    
docsRphyRpdDevCapabNumCoresSupported OBJECT-TYPE
    SYNTAX      Unsigned32 (10..255)
    MAX-ACCESS  read-only
    STATUS      current
    DESCRIPTION
        "This attribute reports the number of Cores 
         supported by the RPD."
    REFERENCE 
        "Information Model Mapping: CM-SP-R-OSSI 
         MiscellaneousCapabilities::NumCoresSupported"
    ::= {  docsRphyRpdDevCapabilitiesEntry 61 }
    
docsRphyRpdDevCapabMaxDsOob55d1Frequency OBJECT-TYPE
    SYNTAX      Unsigned32
    UNITS       "Hertz"
    MAX-ACCESS  read-only
    STATUS      current
    DESCRIPTION
        "This attribute reports the highest center frequency on 
         which an SCTE 55-1 forward channel can be modulated in
         Hertz."
    REFERENCE 
        "Information Model Mapping: CM-SP-R-OSSI 
         DsCapabilities::MaxDsOob55d1Frequency"
    ::= {  docsRphyRpdDevCapabilitiesEntry 62 }
    
docsRphyRpdDevCapabSupportsDsOob55d2SecFreq OBJECT-TYPE
    SYNTAX      TruthValue
    MAX-ACCESS  read-only
    STATUS      current
    DESCRIPTION
        "This attribute indicates whether the RPD supports modulating 
         the SCTE-55-2 forward (downstream) channel on two frequencies 
         per DS RF port.
         
         The RPD reports a value of 'false' when it does not support modulating
         an SCTE 55-2 forward channel on two frequencies.
         
         The RPD reports a value of 'true' when it supports modulating an 
         SCTE 55-2 forward channels on two frequencies."
    REFERENCE 
        "Information Model Mapping: CM-SP-R-OSSI 
         DsCapabilities::SupportsDsOob55d2SecFreq"
    ::= {  docsRphyRpdDevCapabilitiesEntry 63 }

docsRphyRpdDevCapabMaxDsOob55d2Frequency OBJECT-TYPE
    SYNTAX      Unsigned32
    UNITS       "Hertz"
    MAX-ACCESS  read-only
    STATUS      current
    DESCRIPTION
        "This attribute reports the highest center frequency on 
         which an SCTE 55-2 forward channel can be modulated in
         Hertz."
    REFERENCE 
        "Information Model Mapping: CM-SP-R-OSSI 
         DsCapabilities::MaxDsOob55d2Frequency"
    ::= {  docsRphyRpdDevCapabilitiesEntry 64 }
    
docsRphyRpdDevCapabReportsOfdmConfigChangeCounts OBJECT-TYPE
    SYNTAX      TruthValue
    MAX-ACCESS  read-only
    STATUS      current
    DESCRIPTION
        "This attribute reports the implementation of TLVs to report the 
         configuration change counts of OFDM channels, namely OcdConfigChangeCount 
         and DpdConfigChangeCount.  It is intended for CCAP Cores to recognize RPDs 
         conforming to RPHY specification versions before these objects were defined. 
         
         The value 'true' reported for this attribute indicates the RPD reports 
         OcdConfigChangeCount and DpdConfigChangeCount. 
         
         If this attribute is not present, or if the value 'false' is reported for 
         this attribute, the RPD does not report OcdConfigChangeCount or 
         DpdConfigChangeCount."
    REFERENCE 
        "Information Model Mapping: CM-SP-R-OSSI 
         DsCapabilities::ReportsOfdmConfigChangeCounts"
    ::= {  docsRphyRpdDevCapabilitiesEntry 65 }
       
-- ---------------------------------------------------------------------
-- RPD Channel Reachability Table
-- ---------------------------------------------------------------------

docsRphyRpdDevChanReachabilityTable OBJECT-TYPE
    SYNTAX      SEQUENCE OF DocsRphyRpdDevChanReachabilityEntry
    MAX-ACCESS  not-accessible
    STATUS      current
    DESCRIPTION
        "This table provides RPD channel reachability constraints. 
         In some RPD implementations, an Ethernet interface might 
         not have connectivity to all channels on a port of the RPD.
         This table is only populated if reachability constraints 
         exist on the RPD.
         The ChannelReachability TLV Type is 50.20."
    REFERENCE 
        "Information Model Mapping: CM-SP-R-OSSI 
         ChannelReachability"
    ::= { docsRphyRpdDevMibObjects 6 }


docsRphyRpdDevChanReachabilityEntry OBJECT-TYPE
    SYNTAX     DocsRphyRpdDevChanReachabilityEntry
    MAX-ACCESS not-accessible
    STATUS     current
    DESCRIPTION
        "The conceptual row of docsRphyRpdDevChanReachabilityTable."
    INDEX { docsRphyRpdDevInfoUniqueId,
            docsRphyRpdDevChanReachabilityEnetPortIndex,
            docsRphyRpdDevChanReachabilityRfPortIndex,
            docsRphyRpdDevChanReachabilityChanType,
            docsRphyRpdDevChanReachabilityStartChanIndex }
    ::= { docsRphyRpdDevChanReachabilityTable 1 }


DocsRphyRpdDevChanReachabilityEntry ::= SEQUENCE
    {
    docsRphyRpdDevChanReachabilityEnetPortIndex       Unsigned32,
    docsRphyRpdDevChanReachabilityRfPortIndex         Unsigned32,
    docsRphyRpdDevChanReachabilityChanType            RphyChannelType,
    docsRphyRpdDevChanReachabilityStartChanIndex      Unsigned32,
    docsRphyRpdDevChanReachabilityEndChanIndex        Unsigned32
}
        
docsRphyRpdDevChanReachabilityEnetPortIndex OBJECT-TYPE
    SYNTAX      Unsigned32 (0..255)
    MAX-ACCESS  not-accessible 
    STATUS      current 
    DESCRIPTION 
        "This attribute identifies the Ethernet port on the RPD
         that has the connectivity constraint."
    REFERENCE 
        "Information Model Mapping: CM-SP-R-OSSI 
         ChannelReachability::EnetPortIndex"
    ::= { docsRphyRpdDevChanReachabilityEntry 1 }


docsRphyRpdDevChanReachabilityRfPortIndex OBJECT-TYPE
    SYNTAX      Unsigned32 (0..255)
    MAX-ACCESS  not-accessible
    STATUS      current
    DESCRIPTION 
        "This attribute identifies the RF port with which the 
         Ethernet port has a connectivity constraint."
    REFERENCE 
        "Information Model Mapping: CM-SP-R-OSSI 
         ChannelReachability::RfPortIndex"
    ::= { docsRphyRpdDevChanReachabilityEntry 2 }
        
docsRphyRpdDevChanReachabilityChanType OBJECT-TYPE
    SYNTAX      RphyChannelType
    MAX-ACCESS  not-accessible
    STATUS      current
    DESCRIPTION 
        "This attribute identifies the type of channel that is supported
         within the specified channel index range on this RF port from the 
         specified Ethernet interface. A row entry will be created for each 
         channel type with a constraint. Absence of a row for a channel type 
         means there is no constraint for that channel type."
    REFERENCE 
        "Information Model Mapping: CM-SP-R-OSSI 
         ChannelReachability::ChannelType"
    ::= { docsRphyRpdDevChanReachabilityEntry 3 }
        
docsRphyRpdDevChanReachabilityStartChanIndex OBJECT-TYPE
    SYNTAX      Unsigned32 (0..255)
    MAX-ACCESS  not-accessible
    STATUS      current
    DESCRIPTION 
        "This attribute identifies the first channel of the 
         specified channel type in the range of channels that 
         does not have connectivity to the specified Ethernet port."
    REFERENCE 
        "Information Model Mapping: CM-SP-R-OSSI 
         ChannelReachability::StartChanIndex"
    ::= { docsRphyRpdDevChanReachabilityEntry 4 }
        
docsRphyRpdDevChanReachabilityEndChanIndex OBJECT-TYPE
    SYNTAX      Unsigned32 (0..255)
    MAX-ACCESS  read-only
    STATUS      current
    DESCRIPTION 
        "This attribute identifies the last channel of the 
         specified channel type in the range of channels that 
         does not have connectivity to the specified Ethernet port."
    REFERENCE 
        "Information Model Mapping: CM-SP-R-OSSI 
         ChannelReachability::EndChanIndex"
    ::= { docsRphyRpdDevChanReachabilityEntry 5 }
        
        
-- ---------------------------------------------------------------------
-- RPD DS/US RF Port Allocation Table
-- ---------------------------------------------------------------------

docsRphyRpdDevDsUsRfPortAllocTable OBJECT-TYPE
    SYNTAX      SEQUENCE OF DocsRphyRpdDevDsUsRfPortAllocEntry
    MAX-ACCESS  not-accessible
    STATUS      current
    DESCRIPTION
        "This table provides the allocation status for the 
         downstream channel resources on the RPD on a per DS RF port 
         basis as well as for the upstream channel resources on a 
         per US RF port basis. The DsUsRfPortAlloc TLV Type is 50.22
         Downstream and 50.23 Upstream."
    REFERENCE 
        "Information Model Mapping: CM-SP-R-OSSI 
         DsUsRfPortAlloc"
    ::= { docsRphyRpdDevMibObjects 7 }


docsRphyRpdDevDsUsRfPortAllocEntry OBJECT-TYPE
    SYNTAX     DocsRphyRpdDevDsUsRfPortAllocEntry
    MAX-ACCESS not-accessible
    STATUS     current
    DESCRIPTION
        "The conceptual row of docsRphyRpdDevDsUsRfPortAllocTable."
    INDEX { docsRphyRpdDevInfoUniqueId, 
            docsRphyRpdDevDsUsRfPortAllocIndex, 
            docsRphyRpdDevDsUsRfPortAllocDirection }
    ::= { docsRphyRpdDevDsUsRfPortAllocTable 1 }


DocsRphyRpdDevDsUsRfPortAllocEntry ::= SEQUENCE
    {
    docsRphyRpdDevDsUsRfPortAllocIndex              Unsigned32,
    docsRphyRpdDevDsUsRfPortAllocDirection          IfDirection,
    docsRphyRpdDevDsUsRfPortAllocScQamChans         Unsigned32,
    docsRphyRpdDevDsUsRfPortAllocOfdmChans          Unsigned32,
    docsRphyRpdDevDsUsRfPortAllocOob551Chans        Unsigned32,
    docsRphyRpdDevDsUsRfPortAllocNdChans            Unsigned32,
    docsRphyRpdDevDsUsRfPortAllocBdrs               Unsigned32,
    docsRphyRpdDevDsUsRfPortAllocConfiguredBcgs     Unsigned32
    }
        
docsRphyRpdDevDsUsRfPortAllocIndex OBJECT-TYPE
    SYNTAX      Unsigned32 (0..255)
    MAX-ACCESS  not-accessible 
    STATUS      current 
    DESCRIPTION 
        "This attribute provides the index of the downstream or
         upstream RF port for which resource allocation is being 
         reported."
    REFERENCE 
        "Information Model Mapping: CM-SP-R-OSSI 
         DsUsRfPortAlloc::RfPortIndex"
    ::= { docsRphyRpdDevDsUsRfPortAllocEntry 1 }
        
docsRphyRpdDevDsUsRfPortAllocDirection OBJECT-TYPE
    SYNTAX      IfDirection
    MAX-ACCESS  not-accessible 
    STATUS      current 
    DESCRIPTION 
        "This attribute indicates whether the allocation
         applies to the upstream or downstream RF Port."
    REFERENCE 
        "Information Model Mapping: CM-SP-R-OSSI 
         DsUsRfPortAlloc::Direction"
    ::= { docsRphyRpdDevDsUsRfPortAllocEntry 2 }

docsRphyRpdDevDsUsRfPortAllocScQamChans OBJECT-TYPE
    SYNTAX      Unsigned32 (0..65535)
    MAX-ACCESS  read-only
    STATUS      current
    DESCRIPTION 
        "This attribute provides the number of allocated SC-QAM
         channels on this RF port."
    REFERENCE 
        "Information Model Mapping: CM-SP-R-OSSI 
         DsUsRfPortAlloc::AllocScQamChannels"
    ::= { docsRphyRpdDevDsUsRfPortAllocEntry 3 }
        
docsRphyRpdDevDsUsRfPortAllocOfdmChans OBJECT-TYPE
    SYNTAX      Unsigned32 (0..65535)
    MAX-ACCESS  read-only
    STATUS      current
    DESCRIPTION 
        "This attribute provides the number of allocated DOCSIS 3.1
         channels on this RF port."
    REFERENCE 
        "Information Model Mapping: CM-SP-R-OSSI 
         DsUsRfPortAlloc::AllocOfdmChannels"
    ::= { docsRphyRpdDevDsUsRfPortAllocEntry 4 }
        
docsRphyRpdDevDsUsRfPortAllocOob551Chans OBJECT-TYPE
    SYNTAX      Unsigned32 (0..65535)
    MAX-ACCESS  read-only
    STATUS      current
    DESCRIPTION 
        "This attribute provides the number of allocated SCTE 55-1
         channels on this RF port."
    REFERENCE 
        "Information Model Mapping: CM-SP-R-OSSI 
         DsUsRfPortAlloc::AllocOob551Channels"
    ::= { docsRphyRpdDevDsUsRfPortAllocEntry 5 }
        
docsRphyRpdDevDsUsRfPortAllocNdChans OBJECT-TYPE
    SYNTAX      Unsigned32 (0..65535)
    MAX-ACCESS  read-only
    STATUS      current
    DESCRIPTION 
        "This attribute provides the number of allocated narrowband
         digital forward channels (for DS RF Ports) or narrowband
         digital return channels (for US RF Ports) on this RF port."
    REFERENCE 
        "Information Model Mapping: CM-SP-R-OSSI 
         DsUsRfPortAlloc::AllocNdChannels"
    ::= { docsRphyRpdDevDsUsRfPortAllocEntry 6 }
    
docsRphyRpdDevDsUsRfPortAllocBdrs OBJECT-TYPE
    SYNTAX      Unsigned32 (0..65535)
    MAX-ACCESS  read-only
    STATUS      current
    DESCRIPTION 
        "This attribute reports how many BDRs have been allocated
         on the RPD. This attribute is not applicable for US 
         channels and always reports zero."
    REFERENCE 
        "Information Model Mapping: CM-SP-R-OSSI 
         DsUsRfPortAlloc::AllocBdrs"
    ::= { docsRphyRpdDevDsUsRfPortAllocEntry 7 }
    
docsRphyRpdDevDsUsRfPortAllocConfiguredBcgs OBJECT-TYPE
    SYNTAX      Unsigned32 (0..65535)
    MAX-ACCESS  read-only
    STATUS      current
    DESCRIPTION 
        "This attribute reports how many BCGs have been configured
         on the RPD. This attribute is not applicable for US 
         channels and always reports zero."
    REFERENCE 
        "Information Model Mapping: CM-SP-R-OSSI 
         DsUsRfPortAlloc::ConfiguredBcgs"
    ::= { docsRphyRpdDevDsUsRfPortAllocEntry 8 }
  
-- ---------------------------------------------------------
-- RPD L2TP Session Info Table 
-- ---------------------------------------------------------
             
docsRphyRpdDevL2tpSessionInfoTable OBJECT-TYPE
    SYNTAX      SEQUENCE OF DocsRphyRpdDevL2tpSessionInfoEntry
    MAX-ACCESS  not-accessible
    STATUS      current
    DESCRIPTION
        "This table provides details about each tunnel 
         session between the RPD and each CCAP Core with which the 
         RPD is associated from the RPD's point of view.
         
         It is based on the docsIfMCmtsDepiSessionInfo object defined 
         in the DOCS-IF-M-CMTS-MIB and the PW3 MIB definition in [RFC 5601]. 
         It has been extended for Remote PHY.
         
         The attributes in this table are used to create an entry 
         for each L2TPv3 tunnel (session) terminated at an R-PHY 
         entity (RPD).
         
         Note: The SessionInfo TLV, applicable to the RpdL2tpSessionInfo 
         object, is 100.2."
    REFERENCE 
        "Information Model Mapping: CM-SP-R-OSSI 
         SessionInfo"
    ::= { docsRphyRpdDevMibObjects 8 }

docsRphyRpdDevL2tpSessionInfoEntry OBJECT-TYPE
    SYNTAX      DocsRphyRpdDevL2tpSessionInfoEntry
    MAX-ACCESS  not-accessible
    STATUS      current
    DESCRIPTION
        "The conceptual row of docsRphyRpdDevL2tpSessionInfoTable.
         A row entry is created for every session the RPD 
         terminates and there may be entries for sessions with 
         different CCAP-Cores if the RPD is connected with one 
         or more auxiliary cores."
    INDEX { docsRphyRpdDevInfoUniqueId,
            docsRphyRpdDevL2tpSessionInfoSessionIpAddrType,
            docsRphyRpdDevL2tpSessionInfoCcapLcceIpAddr,
            docsRphyRpdDevL2tpSessionInfoRpdLcceIpAddr,
            docsRphyRpdDevL2tpSessionInfoDirection,
            docsRphyRpdDevL2tpSessionInfoL2tpSessionId }
    ::= { docsRphyRpdDevL2tpSessionInfoTable 1 }

DocsRphyRpdDevL2tpSessionInfoEntry ::= SEQUENCE
    {
    docsRphyRpdDevL2tpSessionInfoSessionIpAddrType     InetAddressType,
    docsRphyRpdDevL2tpSessionInfoCcapLcceIpAddr        InetAddress,
    docsRphyRpdDevL2tpSessionInfoRpdLcceIpAddr         InetAddress,
    docsRphyRpdDevL2tpSessionInfoDirection             INTEGER,
    docsRphyRpdDevL2tpSessionInfoL2tpSessionId         Unsigned32,
    docsRphyRpdDevL2tpSessionInfoCoreId                OCTET STRING,
    docsRphyRpdDevL2tpSessionInfoConnCtrlID            Unsigned32,
    docsRphyRpdDevL2tpSessionInfoUdpPort               InetPortNumber,
    docsRphyRpdDevL2tpSessionInfoDescr                 SnmpAdminString,
    docsRphyRpdDevL2tpSessionInfoSessionType           INTEGER,
    docsRphyRpdDevL2tpSessionInfoSessionSubType        INTEGER,
    docsRphyRpdDevL2tpSessionInfoMaxPayload            Unsigned32,
    docsRphyRpdDevL2tpSessionInfoPathPayload           Unsigned32,
    docsRphyRpdDevL2tpSessionInfoRpdIfMtu              Unsigned32,
    docsRphyRpdDevL2tpSessionInfoCoreIfMtu             Unsigned32,
    docsRphyRpdDevL2tpSessionInfoErrorCode             INTEGER,
    docsRphyRpdDevL2tpSessionInfoCreationTime          TimeStamp,
    docsRphyRpdDevL2tpSessionInfoOperStatus            OperStatusType,
    docsRphyRpdDevL2tpSessionInfoLocalStatus           BITS,
    docsRphyRpdDevL2tpSessionInfoLastChange            TimeStamp,
    docsRphyRpdDevL2tpSessionInfoExtendedRemoteEndId   OCTET STRING
    }

docsRphyRpdDevL2tpSessionInfoSessionIpAddrType OBJECT-TYPE
    SYNTAX      InetAddressType    
    MAX-ACCESS  not-accessible
    STATUS      current
    DESCRIPTION 
        "This key attribute indicates whether the IP address
         provided in the CcapLcceIpAddress and RpdLcceIpAddr 
         attributes are IPv4 or IPv6."
    ::= { docsRphyRpdDevL2tpSessionInfoEntry 1 }

docsRphyRpdDevL2tpSessionInfoCcapLcceIpAddr OBJECT-TYPE
    SYNTAX      InetAddress (SIZE (4|16)) 
    MAX-ACCESS  not-accessible
    STATUS      current
    DESCRIPTION 
        "This key attribute provides the LCCE IP address on the
         CCAP Core of the session detailed in the instance. As
         reported by the RPD for a static multicast session, 
         this attribute is zero for an any source multicast and 
         the source IP for Source Specific Multicast (SSM)."
    ::= { docsRphyRpdDevL2tpSessionInfoEntry 2 }

docsRphyRpdDevL2tpSessionInfoRpdLcceIpAddr OBJECT-TYPE
    SYNTAX      InetAddress  (SIZE (4|16))
    MAX-ACCESS  not-accessible
    STATUS      current
    DESCRIPTION 
        "This key attribute reports the remote-side
         RPD LCCE IP address of the session detailed
         in the instance."
    ::= { docsRphyRpdDevL2tpSessionInfoEntry 3 }
    
docsRphyRpdDevL2tpSessionInfoDirection OBJECT-TYPE
    SYNTAX      INTEGER {
                         forward(0),
                         return(1)
                        }
    MAX-ACCESS  not-accessible
    STATUS      current
    DESCRIPTION 
        "This key attribute reports the direction of the 
         session detailed in the instance. Valid values include:
         'forward' - Forward (downstream) direction toward the RPD.
         'return' -  Return (upstream) direction toward the CCAP Core."
    ::= { docsRphyRpdDevL2tpSessionInfoEntry 4 }

docsRphyRpdDevL2tpSessionInfoL2tpSessionId OBJECT-TYPE
    SYNTAX      Unsigned32  
    MAX-ACCESS  not-accessible
    STATUS      current
    DESCRIPTION 
        "This key attribute reports the value of the 
            L2TPv3 session ID transmitted or received on 
            the session. "
    ::= { docsRphyRpdDevL2tpSessionInfoEntry 5 }
    
docsRphyRpdDevL2tpSessionInfoCoreId OBJECT-TYPE
    SYNTAX      OCTET STRING (SIZE (6))
    MAX-ACCESS  read-only
    STATUS      current
    DESCRIPTION 
        "This attribute reports the unique identifier, 
         for example a MAC address, of the CCAP Core with which 
         this session terminates. The CCAP Core sends its unique 
         identifier to the RPD periodically via the DOCSIS SYNC MAC 
         Message in the Source Address field."
    ::= { docsRphyRpdDevL2tpSessionInfoEntry 6 }
    
docsRphyRpdDevL2tpSessionInfoConnCtrlID OBJECT-TYPE
    SYNTAX      Unsigned32
    MAX-ACCESS  read-only
    STATUS      current
    DESCRIPTION 
        "This attribute indicates the control connection
         identifier (CCID) for this session."
    ::= { docsRphyRpdDevL2tpSessionInfoEntry 7 }
    
docsRphyRpdDevL2tpSessionInfoUdpPort OBJECT-TYPE
    SYNTAX      InetPortNumber
    MAX-ACCESS  read-only
    STATUS      current
    DESCRIPTION 
        "This attribute provides the UDP Port reported by the RPD
         when the DEPI session uses L2TPv3 Header Over
         UDP. This attribute reports a value of 0 when the session 
         is running with the L2TPv3 Session IP Header. 
         This port number is negotiated between the CCAP Core and 
         the RPD according to the L2TPv3 RFC."
    ::= { docsRphyRpdDevL2tpSessionInfoEntry 8 }
    
docsRphyRpdDevL2tpSessionInfoDescr OBJECT-TYPE
    SYNTAX      SnmpAdminString
    MAX-ACCESS  read-only
    STATUS      current
    DESCRIPTION 
        "This attribute provides an ASCII string constructed with
         the form:
         
         RemoteEndId=(pp:mmm:ccc), ...  
           { repeated for multiple endpoints } 

         where
         pp is the 0-based port num signaled in the RemoteEndId AVP
         mmm is the channel-type enum value from the RemoteEndId AVP 
         ccc is the channel number from the RemoteEndId AVP."
    ::= { docsRphyRpdDevL2tpSessionInfoEntry 9 }
    
docsRphyRpdDevL2tpSessionInfoSessionType OBJECT-TYPE
    SYNTAX      INTEGER {
                         psp(1),
                         mpt(2)
                   }
    MAX-ACCESS  read-only
    STATUS      current
    DESCRIPTION 
        "This attribute specifies whether the session is an MPT 
         session or PSP session."
    ::= { docsRphyRpdDevL2tpSessionInfoEntry 10 }
    
docsRphyRpdDevL2tpSessionInfoSessionSubType OBJECT-TYPE
    SYNTAX      INTEGER {
                         mptLegacy(1),
                         pspLegacy(2),
                         mcm(3),
                         pspDepiMultichannel(4),
                         pspUepiScQam(5),
                         pspUepiOfdma(6),
                         pspBwReqScQam(7),
                         pspBwReqOfdma(8),
                         pspProbe(9),
                         pspRngReqScQam(10),
                         pspRngReqOfdma(11),
                         pspMapScQam(12),
                         pspMapOfdma(13),
                         pspSpecman(14),
                         pspPnm(15),
                         psp551Fwd(16),
                         psp551Ret(17),
                         psp552Fwd(18),
                         psp552Ret(19),
                         pspNdf(20),
                         pspNdr(21),
                         pspEc(22),
                         pspZbl(23)
                        }
    MAX-ACCESS  read-only
    STATUS      current
    DESCRIPTION 
        "This attribute specifies the type of DEPI MPT or DEPI 
         PSP session."
    ::= { docsRphyRpdDevL2tpSessionInfoEntry 11 }

docsRphyRpdDevL2tpSessionInfoMaxPayload OBJECT-TYPE
    SYNTAX      Unsigned32
    MAX-ACCESS  read-only
    STATUS      current
    DESCRIPTION 
        "This attribute indicates the maximum MTU negotiated between
         the CCAP Core and the RPD during the session establishment 
         process. It considers the header subtractions as indicated 
         in the DEPI specification."
    REFERENCE 
        "Information Model Mapping: CM-SP-R-OSSI 
         SessionInfo::MaxPayload"
    ::= { docsRphyRpdDevL2tpSessionInfoEntry 12 }

docsRphyRpdDevL2tpSessionInfoPathPayload OBJECT-TYPE
    SYNTAX      Unsigned32
    MAX-ACCESS  read-only
    STATUS      current
    DESCRIPTION 
        "This attribute indicates the maximum MTU traversing the CIN
         from CCAP Core to the RPD. This is calculated by the CCAP 
         Core by procedures such as MTU discovery as described in 
         the DEPI specification."
    REFERENCE 
        "Information Model Mapping: CM-SP-R-OSSI 
         SessionInfo::PathPayload"
    ::= { docsRphyRpdDevL2tpSessionInfoEntry 13 }
    
docsRphyRpdDevL2tpSessionInfoRpdIfMtu OBJECT-TYPE
    SYNTAX      Unsigned32
    MAX-ACCESS  read-only
    STATUS      current
    DESCRIPTION 
        "This attribute provides the RPD's CIN interface MTU and is
         read as the value of the following L2TPV3 AVP transmitted 
         by the RPD during session setup:
         
         DEPI Downstream PW          UEPI Upstream PW
         DEPI Remote MTU AVP (ICRP)  UEPI Remote MTU AVP (ICRP)."
    ::= { docsRphyRpdDevL2tpSessionInfoEntry 14 }
    
docsRphyRpdDevL2tpSessionInfoCoreIfMtu OBJECT-TYPE
    SYNTAX      Unsigned32
    MAX-ACCESS  read-only
    STATUS      current
    DESCRIPTION 
        "This attribute provides the CCAP Core's CIN interface MTU
         and is read as the value of the following L2TPv3 AVP as 
         received by the device during session setup:
         
         DEPI Downstream PW          UEPI Upstream PW
         DEPI Local MTU AVP (ICRQ)   UEPI Local MTU AVP (ICRQ)."
    ::= { docsRphyRpdDevL2tpSessionInfoEntry 15 }

docsRphyRpdDevL2tpSessionInfoErrorCode OBJECT-TYPE
    SYNTAX      INTEGER {
                         none(1),
                         invalidMACInterfaceValue(2),
                         invalidInterfaceValue(3),
                         noResourcesForInterfaceIndex(4),
                         l2tpv3Error(5),
                         ifAdminStatusSetToDown(6)
                        }
    MAX-ACCESS  read-only
    STATUS      current
    DESCRIPTION 
        "The error code raised when the session is in an error
         state: 
         'invalidMACInterfaceValue'  
          Indicates wrong assignment of the CCAP Core MAC interface
          ifIndex.
         'invalidInterfaceValue'  
          Indicates wrong assignment of the CCAP Core Downstream 
          interface ifIndex
         'noResourcesForInterfaceIfIndex' 
          Indicates the CCAP Core has no more resources to
          assign a session to this entry.
         'l2tpv3Error'
          An L2TPv3 StopCCN or CDN message was issued 
         'ifAdminStatusSetToDown'
          Indicates the ifAdminStatus was set to down and the
          session was torn down."
    ::= { docsRphyRpdDevL2tpSessionInfoEntry 16 }

docsRphyRpdDevL2tpSessionInfoCreationTime OBJECT-TYPE
    SYNTAX      TimeStamp
    MAX-ACCESS  read-only
    STATUS      current
    DESCRIPTION 
        "The attribute contains the sysUptime when the entry was 
         turned active."
    ::= { docsRphyRpdDevL2tpSessionInfoEntry 17 }
    
docsRphyRpdDevL2tpSessionInfoOperStatus OBJECT-TYPE
    SYNTAX      OperStatusType
    MAX-ACCESS  read-only
    STATUS      current
    DESCRIPTION 
        "This attribute provides the current status of the 
         pseudowire from the point of view of the specific 
         reporting entity (RPD).For static psuedowires,
         the only values that the RPD can report are 'up' and 
         'down'. 
         These values are conveyed to the Core via the 
         RpdCircuitStatus TLV (TLV 59.1.3)."
    ::= { docsRphyRpdDevL2tpSessionInfoEntry 18 }

docsRphyRpdDevL2tpSessionInfoLocalStatus OBJECT-TYPE
    SYNTAX      BITS {
                      other(0),
                      pwNotForwarding(1), 
                      servicePwRxFault(2), 
                      servicePwTxFault(3), 
                      psnPwRxFault(4), 
                      psnPwTxFault(5)
                     }
    MAX-ACCESS  read-only
    STATUS      current
    DESCRIPTION 
        "The attribute provides the status of the pseudowire 
         in the local node. If the 'other' bit is set, it indicates
         that an additional vendor-specific status is reported. 
         If none of the bits are set, it indicates no faults are 
         reported."
    ::= { docsRphyRpdDevL2tpSessionInfoEntry 19 }
    
docsRphyRpdDevL2tpSessionInfoLastChange OBJECT-TYPE
    SYNTAX      TimeStamp
    MAX-ACCESS  read-only
    STATUS      current
    DESCRIPTION 
        "The attribute provides the value of sysUpTime 
         when the session entered its current OperStatus 
         state from the point of view of the specific 
         reporting entity (RPD)."
    ::= { docsRphyRpdDevL2tpSessionInfoEntry 20 }
    
docsRphyRpdDevL2tpSessionInfoExtendedRemoteEndId OBJECT-TYPE
    SYNTAX      OCTET STRING  
    MAX-ACCESS  read-only
    STATUS      current
    DESCRIPTION 
        "This attribute provides an ASCII string 
         constructed with the form:
         RemoteEndId=(pp:mmm:ccc),... { repeated for multiple channels } 

         where
         pp is the zero-based port number signaled in the RemoteEndId AVP
         mmm is the channel-type Enum value from the RemoteEndId AVP 
         ccc is the channel number from the RemoteEndId AVP
         
         This attribute conveys largely the same information
         as the Description attribute. Its longer length however
         permits communication of the complete RemoteEndId 
         description, even when the length of the string exceeds 
         255 octets."
    ::= { docsRphyRpdDevL2tpSessionInfoEntry 21 }
    
-- ---------------------------------------------------------
-- RPD L2TP Session Statistics Table 
-- ---------------------------------------------------------
             
docsRphyRpdDevL2tpSessionStatsTable OBJECT-TYPE
    SYNTAX      SEQUENCE OF DocsRphyRpdDevL2tpSessionStatsEntry
    MAX-ACCESS  not-accessible
    STATUS      current
    DESCRIPTION
        "This table provides statistics about each tunnel 
         session between the RPD and each CCAP Core with which the 
         RPD is associated from the RPD's point of view. The RPD 
         must create an entry in this table for each DEPI, UEPI, OOB, NDF, 
         and NDR pseudowire it has established with CCAP Cores.
         The RpdSessionStats attributes are read with GCP Complex 
         TLV type 100.2.21."
    REFERENCE 
        "Information Model Mapping: CM-SP-R-OSSI 
         RpdSessionStats"
    ::= { docsRphyRpdDevMibObjects 9 }

docsRphyRpdDevL2tpSessionStatsEntry OBJECT-TYPE
    SYNTAX      DocsRphyRpdDevL2tpSessionStatsEntry
    MAX-ACCESS  not-accessible
    STATUS      current
    DESCRIPTION
        "The conceptual row of docsRphyRpdDevL2tpSessionStatsTable.
         This table is an augmentation of 
         docsRphyL2tpSessionInfoTable."
    AUGMENTS { docsRphyRpdDevL2tpSessionInfoEntry }
    ::= { docsRphyRpdDevL2tpSessionStatsTable 1 }

DocsRphyRpdDevL2tpSessionStatsEntry ::= SEQUENCE
    {
    docsRphyRpdDevL2tpSessionStatsOutOfSeqPkts                Counter32,
    docsRphyRpdDevL2tpSessionStatsInPkts                      Counter64,
    docsRphyRpdDevL2tpSessionStatsInDiscards                  Counter64,
    docsRphyRpdDevL2tpSessionStatsOutPkts                     Counter64,
    docsRphyRpdDevL2tpSessionStatsOutErrors                   Counter64,
    docsRphyRpdDevL2tpSessionStatsCounterDiscontinuityTime    DateAndTime
    }
    
docsRphyRpdDevL2tpSessionStatsOutOfSeqPkts OBJECT-TYPE
    SYNTAX      Counter32
    MAX-ACCESS  read-only
    STATUS      current
    DESCRIPTION 
        "This attribute indicates the count of session packets that
         were received out of sequence from the point of view of the
         reporting entity. It is vendor dependent the re-sequence of 
         packets. Implementations that do not re-sequence packets 
         also increase the value of ifInDiscards for the respective 
         entry."
    REFERENCE 
        "Information Model Mapping: CM-SP-R-OSSI 
         RpdSessionStats::OutOfSequencePackets"
    ::= { docsRphyRpdDevL2tpSessionStatsEntry 1 }
    
 docsRphyRpdDevL2tpSessionStatsInPkts OBJECT-TYPE
    SYNTAX      Counter64
    MAX-ACCESS  read-only
    STATUS      current
    DESCRIPTION 
        "This attribute counts the number of received packets accepted 
         for processing above the L2TPv3 protocol layer. The InPackets 
         attribute count excludes packets dropped by the L2TPv3 protocol 
         layer itself (e.g. OutOfSequencePackets and InDiscards)."
    REFERENCE 
        "Information Model Mapping: CM-SP-R-OSSI 
         RpdSessionStats::InPackets"
    ::= { docsRphyRpdDevL2tpSessionStatsEntry 2 } 
    
 docsRphyRpdDevL2tpSessionStatsInDiscards OBJECT-TYPE
    SYNTAX      Counter64
    MAX-ACCESS  read-only
    STATUS      current
    DESCRIPTION 
        "This attribute counts the number of received packets discarded 
         by the L2TPv3 protocol layer itself, including those discarded 
         because they were out of sequence. The InDiscards attribute 
         count includes packets unable to be forwarded to a higher layer 
         for processing (e.g. unknown L2tpv3 session Id). Interpretation 
         of what discards are counted in this attribute is 
         vendor-specific."
    REFERENCE 
        "Information Model Mapping: CM-SP-R-OSSI 
         RpdSessionStats::InDiscards"
    ::= { docsRphyRpdDevL2tpSessionStatsEntry 3 } 
    
 docsRphyRpdDevL2tpSessionStatsOutPkts OBJECT-TYPE
    SYNTAX      Counter64
    MAX-ACCESS  read-only
    STATUS      current
    DESCRIPTION 
        "This attribute counts the number of packets conceptually 
         attempted to be transmitted from above the L2TPv3 protocol layer. 
         The OutPackets attribute counts packets discarded by the L2TPv3 
         protocol layer itself (i.e. as counted by OutErrors)."
    REFERENCE 
        "Information Model Mapping: CM-SP-R-OSSI 
         RpdSessionStats::OutPackets"
    ::= { docsRphyRpdDevL2tpSessionStatsEntry 4 }    
    
 docsRphyRpdDevL2tpSessionStatsOutErrors OBJECT-TYPE
    SYNTAX      Counter64
    MAX-ACCESS  read-only
    STATUS      current
    DESCRIPTION 
        "This attribute counts the number of packets attempted to be 
         transmitted from above the L2TPv3 protocol layer that could not 
         be transmitted below the L2TPv3 protocol layer itself. 
         Interpretation of what errors are counted in this attribute is 
         vendor specific."
    REFERENCE 
        "Information Model Mapping: CM-SP-R-OSSI 
         RpdSessionStats::OutErrors"
    ::= { docsRphyRpdDevL2tpSessionStatsEntry 5 }

docsRphyRpdDevL2tpSessionStatsCounterDiscontinuityTime OBJECT-TYPE
    SYNTAX      DateAndTime
    MAX-ACCESS  read-only
    STATUS      current
    DESCRIPTION 
        "This attribute reports the date and time at which any 
         one or more of the counters in this group were created or 
         last reset to zero. If the RPD does not acquire time of day 
         it can report an initial CounterDiscontinuityTime of Jan 1 1970."
    REFERENCE 
        "Information Model Mapping: CM-SP-R-OSSI 
         RpdSessionStats::CounterDiscontinuityTime"
    ::= { docsRphyRpdDevL2tpSessionStatsEntry 6 }     
  
-- ---------------------------------------------------------------------
-- RPD Diagnostic Status Table
-- ---------------------------------------------------------------------

docsRphyRpdDevDiagStatusTable OBJECT-TYPE
    SYNTAX      SEQUENCE OF DocsRphyRpdDevDiagStatusEntry
    MAX-ACCESS  not-accessible
    STATUS      current
    DESCRIPTION
        "This table reports information about an RPD's diagnostic
         self test results. The CCAP Core reads DiagnosticStatus
         attributes with GCP complex TLV Type 100.4."
    REFERENCE 
        "Information Model Mapping: CM-SP-R-OSSI 
         DiagnosticStatus"
    ::= { docsRphyRpdDevMibObjects 10 }


docsRphyRpdDevDiagStatusEntry OBJECT-TYPE
    SYNTAX     DocsRphyRpdDevDiagStatusEntry
    MAX-ACCESS not-accessible
    STATUS     current
    DESCRIPTION
        "The conceptual row of docsRphyRpdDevDiagStatusTable.
         This table returns at least one row indicating pass or
         failure for the diagnostic self test."
    INDEX { docsRphyRpdDevInfoUniqueId }
    ::= { docsRphyRpdDevDiagStatusTable 1 }


DocsRphyRpdDevDiagStatusEntry ::= SEQUENCE
    {
    docsRphyRpdDevDiagStatusProbableCause         SnmpAdminString,
    docsRphyRpdDevDiagStatusAdditionalText        SnmpAdminString,
    docsRphyRpdDevDiagStatusSeverityLevel         EvPriorityType
    }

docsRphyRpdDevDiagStatusProbableCause OBJECT-TYPE
    SYNTAX      SnmpAdminString
    MAX-ACCESS  read-only
    STATUS      current
    DESCRIPTION 
        "This attribute reports the probable cause of the 
         diagnostic test error condition.  Probable causes 
         may be related to:
         - Communications error
         - Quality of Service error
         - Processing error
         - Equipment error
         - Environmental error
         The format for values returned are vendor-specific.
         When the self test result is a pass, this attribute 
         returns 'Self Test Passed'."
    REFERENCE 
        "Information Model Mapping: CM-SP-R-OSSI 
         DiagnosticStatus::ProbableCause"
    ::= { docsRphyRpdDevDiagStatusEntry 1 }
        
docsRphyRpdDevDiagStatusAdditionalText OBJECT-TYPE
    SYNTAX      SnmpAdminString
    MAX-ACCESS  read-only
    STATUS      current
    DESCRIPTION 
        "This attribute reports a free form text description of the 
         diagnostic test error condition.  This provides 
         supplemental information for the ProbableCause.
         When the self test result is a pass, this attribute returns 
         'No errors found'."
    REFERENCE 
        "Information Model Mapping: CM-SP-R-OSSI 
         DiagnosticStatus::AdditionalText"
    ::= { docsRphyRpdDevDiagStatusEntry 2 }
        
docsRphyRpdDevDiagStatusSeverityLevel OBJECT-TYPE
    SYNTAX      EvPriorityType
    MAX-ACCESS  read-only
    STATUS      current
    DESCRIPTION 
        "This attribute reports the severity level for the 
         diagnostic test error condition. Severity levels are based 
         on the DOCSIS event priority levels.
         When the self test result is a pass, this attribute returns 
         'information'."
    REFERENCE 
        "Information Model Mapping: CM-SP-R-OSSI 
         DiagnosticStatus::SeverityLevel"
    ::= { docsRphyRpdDevDiagStatusEntry 3 }
        
-- ---------------------------------------------------------------------
-- RPD DEPI Multicast Session Table
-- ---------------------------------------------------------------------

docsRphyRpdDevDepiMcastSessionTable OBJECT-TYPE
    SYNTAX      SEQUENCE OF DocsRphyRpdDevDepiMcastSessionEntry
    MAX-ACCESS  not-accessible
    STATUS      current
    DESCRIPTION
        "This table reports the DEPI IP multicast sessions 
         currently joined by an RPD. The CCAP Core reads 
         DepiMcastSession attributes with GCP complex TLV 
         Type 100.5."
    REFERENCE 
        "Information Model Mapping: CM-SP-R-OSSI 
         DepiMcastSession"
    ::= { docsRphyRpdDevMibObjects 11 }


docsRphyRpdDevDepiMcastSessionEntry OBJECT-TYPE
    SYNTAX     DocsRphyRpdDevDepiMcastSessionEntry
    MAX-ACCESS not-accessible
    STATUS     current
    DESCRIPTION
        "The conceptual row of docsRphyRpdDevDepiMcastSessionTable.
         A row entry of this table represents one DEPI IP Multicast 
         session replicated to one RPD. The indexing provides the 
         RPD unique identifier and the (S,G) IP address pair that 
         uniquely identifies an IP multicast session. The CCAP Core 
         creates a row entry when it confirms an RPD has joined a 
         DEPI IP multicast session. The CCAP Core deletes the row
         entry when it confirms an RPD has left the DEPI IP 
         multicast session or disconnects its GCP session with 
         the CCAP Core."
    INDEX { docsRphyRpdDevInfoUniqueId,
         docsRphyRpdDevDepiMcastSessionIpAddrType,
         docsRphyRpdDevDepiMcastSessionGrpIpAddr,
         docsRphyRpdDevDepiMcastSessionSrcIpAddr,
         docsRphyRpdDevDepiMcastSessionL2tpSessionId }
    ::= { docsRphyRpdDevDepiMcastSessionTable 1 }


DocsRphyRpdDevDepiMcastSessionEntry ::= SEQUENCE
    {
    docsRphyRpdDevDepiMcastSessionIpAddrType            InetAddressType,
    docsRphyRpdDevDepiMcastSessionGrpIpAddr             InetAddress,
    docsRphyRpdDevDepiMcastSessionSrcIpAddr             InetAddress,
    docsRphyRpdDevDepiMcastSessionL2tpSessionId         Unsigned32,
    docsRphyRpdDevDepiMcastSessionRpdLcceIpAddr         InetAddress,
    docsRphyRpdDevDepiMcastSessionCcapLcceIpAddr        InetAddress,
    docsRphyRpdDevDepiMcastSessionJoinTime              DateAndTime
    }

docsRphyRpdDevDepiMcastSessionIpAddrType OBJECT-TYPE
    SYNTAX      InetAddressType  
    MAX-ACCESS  not-accessible
    STATUS      current
    DESCRIPTION 
        "This key attribute reports whether the IP addresses 
         provided in GrpIpAddr, SrcIpAddr, RpdLcceIpAddr 
         and CcapLcceIpAddr are IPv4 or IPv6."
    ::= { docsRphyRpdDevDepiMcastSessionEntry 1 }
        
docsRphyRpdDevDepiMcastSessionGrpIpAddr OBJECT-TYPE
    SYNTAX      InetAddress   (SIZE(4|16))
    MAX-ACCESS  not-accessible
    STATUS      current
    DESCRIPTION 
        "This key attribute reports the group (destination) address 
         of an IP multicast session transmitted via DEPI 
         multicast."
    ::= { docsRphyRpdDevDepiMcastSessionEntry 2 }
        
docsRphyRpdDevDepiMcastSessionSrcIpAddr OBJECT-TYPE
    SYNTAX      InetAddress  (SIZE(4|16))
    MAX-ACCESS  not-accessible
    STATUS      current
    DESCRIPTION 
        "For Source Specific Multicast (SSM), this key attribute 
         reports the source IP address of an IP multicast session 
         transmitted via DEPI multicast. For Any-Source Multicast 
         (ASM) sessions, this attribute reports the all-0s IP 
         address."
    ::= { docsRphyRpdDevDepiMcastSessionEntry 3 }

docsRphyRpdDevDepiMcastSessionL2tpSessionId OBJECT-TYPE
    SYNTAX      Unsigned32 (2147483649..2147549183)
    MAX-ACCESS  not-accessible
    STATUS      current
    DESCRIPTION 
        "This attribute reports the L2TPv3 Session ID assigned by 
         the CCAP Core to the DEPI IP multicast session. The value 
         is assigned according to the referenced specification in 
         the range 0x80000001 through 0x8000FFFF."
    ::= { docsRphyRpdDevDepiMcastSessionEntry 4 }
        
docsRphyRpdDevDepiMcastSessionRpdLcceIpAddr OBJECT-TYPE
    SYNTAX      InetAddress  (SIZE(4|16))
    MAX-ACCESS  read-only
    STATUS      current
    DESCRIPTION 
        "This attribute reports the RPD local LCCE IP address of 
         the L2TPv3 DEPI control session that instructed the RPD 
         to join the IP multicast session. In the case of static 
         Multicast sessions, this attribute reports RPD IP Address 
         associated with the Ethernet Port on which the static 
         Multcast session has been configured"
    ::= { docsRphyRpdDevDepiMcastSessionEntry 5 }
        
docsRphyRpdDevDepiMcastSessionCcapLcceIpAddr OBJECT-TYPE
    SYNTAX      InetAddress   (SIZE(4|16))
    MAX-ACCESS  read-only
    STATUS      current
    DESCRIPTION 
        "This attribute reports the RPD remote LCCE IP address 
         (i.e. on the CCAP Core) of the L2TPv3 control session 
         that instructed the RPD to join the IP multicast session. 
         In the case of static Multicast sessions, this attribute 
         reports a zero value."
    ::= { docsRphyRpdDevDepiMcastSessionEntry 6 }
  
docsRphyRpdDevDepiMcastSessionJoinTime OBJECT-TYPE
    SYNTAX      DateAndTime
    MAX-ACCESS  read-only
    STATUS      current
    DESCRIPTION 
        "This attribute reports the last time the RPD has joined this session."
    ::= { docsRphyRpdDevDepiMcastSessionEntry 7 }  
        
-- ---------------------------------------------------------------------
-- RPD Event Log Table
-- ---------------------------------------------------------------------

docsRphyRpdDevEventLogTable OBJECT-TYPE
    SYNTAX      SEQUENCE OF DocsRphyRpdDevEventLogEntry
    MAX-ACCESS  not-accessible
    STATUS      current
    DESCRIPTION
        "This table reports event log information for an RPD."
    REFERENCE 
        "Information Model Mapping: CM-SP-R-OSSI 
         Event"
    ::= { docsRphyRpdDevMibObjects 12 }


docsRphyRpdDevEventLogEntry OBJECT-TYPE
    SYNTAX     DocsRphyRpdDevEventLogEntry
    MAX-ACCESS not-accessible
    STATUS     current
    DESCRIPTION
        "The conceptual row of docsRphyRpdDevEventLogTable."
    INDEX { docsRphyRpdDevInfoUniqueId,
            docsRphyRpdDevEventLogIndex }
    ::= { docsRphyRpdDevEventLogTable 1 }


DocsRphyRpdDevEventLogEntry ::= SEQUENCE
    {
    docsRphyRpdDevEventLogIndex             Unsigned32,
    docsRphyRpdDevEventLogFirstTime         DateAndTime,
    docsRphyRpdDevEventLogLastTime          DateAndTime,
    docsRphyRpdDevEventLogCounts            Counter32,
    docsRphyRpdDevEventLogLevel             EvPriorityType,
    docsRphyRpdDevEventLogId                Unsigned32,
    docsRphyRpdDevEventLogText              SnmpAdminString
    }

docsRphyRpdDevEventLogIndex OBJECT-TYPE
    SYNTAX      Unsigned32
    MAX-ACCESS  not-accessible
    STATUS      current
    DESCRIPTION 
        "This key attribute provides relative ordering of the events 
         in the event log. This attribute will always increase 
         except when
         (a) the log is reset 
         (b) the device reboots and does not implement non-volatile 
         storage for this log, or 
         (c) it reaches the value 2^31. The next entry for all the 
         above cases is 1."
    REFERENCE 
        "Information Model Mapping: CM-SP-R-OSSI 
         Event::Index"
    ::= { docsRphyRpdDevEventLogEntry 1 }
        
docsRphyRpdDevEventLogFirstTime OBJECT-TYPE
    SYNTAX      DateAndTime
    MAX-ACCESS  read-only
    STATUS      current
    DESCRIPTION 
        "This attribute provides the local RPD time 
         when this event was created."
    REFERENCE 
        "Information Model Mapping: CM-SP-R-OSSI 
         Event::FirstTime"
    ::= { docsRphyRpdDevEventLogEntry 2 }
        
docsRphyRpdDevEventLogLastTime OBJECT-TYPE
    SYNTAX      DateAndTime
    MAX-ACCESS  read-only
    STATUS      current
    DESCRIPTION 
        "When an event reports only one event occurrence, this 
         attribute will have the same value as the corresponding 
         instance of FirstTime. When an event reports multiple 
         event occurrences, this attribute will record the local 
         RPD time when the most recent occurrence for this event 
         occurred."
    REFERENCE 
        "Information Model Mapping: CM-SP-R-OSSI 
         Event::LastTime"
    ::= { docsRphyRpdDevEventLogEntry 3 }
        
docsRphyRpdDevEventLogCounts OBJECT-TYPE
    SYNTAX      Counter32
    MAX-ACCESS  read-only
    STATUS      current
    DESCRIPTION 
        "This attribute provides the number of consecutive event 
         occurrences reported by this event. This starts at 1 with 
         the creation of this event occurrence and increments by 1 
         for each subsequent duplicate event occurrence."
    REFERENCE 
        "Information Model Mapping: CM-SP-R-OSSI 
         Event::Counts"
    ::= { docsRphyRpdDevEventLogEntry 4 }
        
docsRphyRpdDevEventLogLevel OBJECT-TYPE
    SYNTAX      EvPriorityType
    MAX-ACCESS  read-only
    STATUS      current
    DESCRIPTION 
        "This attribute provides the priority level of this event, 
         as defined by Annex B. These are ordered from most serious 
         (emergency) to least serious (debug)."
    REFERENCE 
        "Information Model Mapping: CM-SP-R-OSSI 
         Event::Level"
    ::= { docsRphyRpdDevEventLogEntry 5 }  
        
docsRphyRpdDevEventLogId OBJECT-TYPE
    SYNTAX      Unsigned32
    MAX-ACCESS  read-only
    STATUS      current
    DESCRIPTION 
        "This attribute provides the identifier of this event, 
         as defined by Annex B."
    REFERENCE 
        "Information Model Mapping: CM-SP-R-OSSI 
         Event::Id"
    ::= { docsRphyRpdDevEventLogEntry 6 }
        
docsRphyRpdDevEventLogText OBJECT-TYPE
    SYNTAX      SnmpAdminString
    MAX-ACCESS  read-only
    STATUS      current
    DESCRIPTION 
        "This attribute provides the message text of this event, 
         as defined by Annex B."
    REFERENCE 
        "Information Model Mapping: CM-SP-R-OSSI 
         Event::Text"
    ::= { docsRphyRpdDevEventLogEntry 7 }
        
-- ---------------------------------------------------------------------
-- RPD Oob551UsChanStatus Table
-- ---------------------------------------------------------------------

docsRphyRpdDevOob551UsChanStatusTable OBJECT-TYPE
    SYNTAX      SEQUENCE OF DocsRphyRpdDevOob551UsChanStatusEntry
    MAX-ACCESS  not-accessible
    STATUS      current
    DESCRIPTION
        "This table provides per-RPD counts of upstream SCTE 55-1 cells sent 
         to a Network Controller. These counts are updated by the CCAP Core, 
         which parses each upstream SCTE 55-1 packet and uses the power level 
         and packet status (which are really cell status) bits in those packets 
         to determine how to update the counters. The only exception is the 
         OperStatus attribute, which is read from the RPD using TLV 80.1.
         The CCAP Core must compute the per-RPD power level 
         (i.e., PwrLevel, MaxPwrLevel, MinPwrLevel) values 
         in the Oob551UsChanStatus table over a sliding 15 minute window. 
         The sliding window method for calculating the power level values is 
         left to vendor implementations.
         This object uses the virtual port and virtual channel ID as the keys
         because it is impossible to determine the physical port and channel 
         number for an SCTE 55-1 US data packet. Only the virtual port number 
         and virtual demodulator ID are in the packet. It is also very difficult,
         if it is even possible for the RPD to keep such counts per physical port
         and channel for reporting using GCP TLVs. If an operator wants counts by
         physical port and physical demodulator ID (channel number), one way is to
         have a different virtual port for each physical port and a different virtual
         demodulator ID for each of the OOB 55-1 US channels on a port."
    ::= { docsRphyRpdDevMibObjects 13 }


docsRphyRpdDevOob551UsChanStatusEntry OBJECT-TYPE
    SYNTAX     DocsRphyRpdDevOob551UsChanStatusEntry
    MAX-ACCESS not-accessible
    STATUS     current
    DESCRIPTION
        "The conceptual row of docsRphyRpdDevOob551UsChanStatusTable.
         A row entry of this table represents counts that are updated 
         by the CCAP Core, which parses each upstream SCTE 55-1 packet 
         and uses the power level and packet status 
         (which are really cell status) bits in those packets to determine
         how to update the counters."
    INDEX { docsRphyRpdDevInfoUniqueId,
            docsRphyRpdDevOob551UsChanStatusRfPort,
            docsRphyRpdDevOob551UsChanStatusChannelId }
    ::= { docsRphyRpdDevOob551UsChanStatusTable 1 }


DocsRphyRpdDevOob551UsChanStatusEntry ::= SEQUENCE
    {
    docsRphyRpdDevOob551UsChanStatusRfPort                    Unsigned32,
    docsRphyRpdDevOob551UsChanStatusChannelId                 Unsigned32,
    docsRphyRpdDevOob551UsChanStatusNcIpAddrType              InetAddressType,
    docsRphyRpdDevOob551UsChanStatusNcIpAddr                  InetAddress,
    docsRphyRpdDevOob551UsChanStatusArpdSrcIpAddrType         InetAddressType,
    docsRphyRpdDevOob551UsChanStatusArpdSrcIpAddr             InetAddress,
    docsRphyRpdDevOob551UsChanStatusPerfectCellsRcvd          Counter64,
    docsRphyRpdDevOob551UsChanStatusCorrectedCellsRcvd        Counter64,
    docsRphyRpdDevOob551UsChanStatusUncorrectableCellsRcvd    Counter64,
    docsRphyRpdDevOob551UsChanStatusTotalCellsRcvd            Counter64,
    docsRphyRpdDevOob551UsChanStatusPwrLevel                  TenthdB,
    docsRphyRpdDevOob551UsChanStatusMaxPwrLevel               TenthdB,
    docsRphyRpdDevOob551UsChanStatusMinPwrLevel               TenthdB,
    docsRphyRpdDevOob551UsChanStatusCounterDiscontinuityTime  DateAndTime,
    docsRphyRpdDevOob551UsChanStatusOperStatus                OperStatusType
    }

docsRphyRpdDevOob551UsChanStatusRfPort OBJECT-TYPE
    SYNTAX      Unsigned32
    MAX-ACCESS  not-accessible
    STATUS      current
    DESCRIPTION 
        "This key attribute reports the RPD RF virtual port number carrying
         this SCTE 55-1 US channel."
    ::= { docsRphyRpdDevOob551UsChanStatusEntry 1 }
        
docsRphyRpdDevOob551UsChanStatusChannelId OBJECT-TYPE
    SYNTAX      Unsigned32 (0..2)
    MAX-ACCESS  not-accessible
    STATUS      current
    DESCRIPTION 
        "This key attribute reports the virtual demodulator ID (channel number) 
         for this SCTE 55-1 US channel."
    ::= { docsRphyRpdDevOob551UsChanStatusEntry 2 }
        
docsRphyRpdDevOob551UsChanStatusNcIpAddrType OBJECT-TYPE
    SYNTAX      InetAddressType    
    MAX-ACCESS  read-only
    STATUS      current
    DESCRIPTION 
        "This attribute indicates whether the IP address provide in 
         docsRphyRpdDevOob551UsChanStatusNcIpAddr is IPv4 or IPv6."
    ::= { docsRphyRpdDevOob551UsChanStatusEntry 3 }
    
docsRphyRpdDevOob551UsChanStatusNcIpAddr OBJECT-TYPE
    SYNTAX      InetAddress
    MAX-ACCESS  read-only
    STATUS      current
    DESCRIPTION 
        "This attribute reports the IP host address of the 
         Network Controller receiving the cells on this 
         SCTE 55-1 US channel."
    ::= { docsRphyRpdDevOob551UsChanStatusEntry 4 }
        
docsRphyRpdDevOob551UsChanStatusArpdSrcIpAddrType OBJECT-TYPE
    SYNTAX      InetAddressType    
    MAX-ACCESS  read-only
    STATUS      current
    DESCRIPTION 
        "This attribute indicates whether the IP address provide in 
         docsRphyRpdDevOob551UsChanStatusArpdSrcIpAddr is IPv4 or IPv6."
    ::= { docsRphyRpdDevOob551UsChanStatusEntry 5 }
    
docsRphyRpdDevOob551UsChanStatusArpdSrcIpAddr OBJECT-TYPE
    SYNTAX      InetAddress
    MAX-ACCESS  read-only
    STATUS      current
    DESCRIPTION 
        "This attribute reports the virtual ARPD source 
         IP host address used when sending cells to the 
         Network Controller."
    ::= { docsRphyRpdDevOob551UsChanStatusEntry 6 }
        
docsRphyRpdDevOob551UsChanStatusPerfectCellsRcvd OBJECT-TYPE
    SYNTAX      Counter64
    UNITS       "Cells"
    MAX-ACCESS  read-only
    STATUS      current
    DESCRIPTION 
        "This attribute reports the number of perfect cells
         received by the demodulator for this SCTE 55-1 US channel. 
         Perfect cells have status 0 in the US SCTE 55-1 OOB packet."
    ::= { docsRphyRpdDevOob551UsChanStatusEntry 7 }
        
docsRphyRpdDevOob551UsChanStatusCorrectedCellsRcvd OBJECT-TYPE
    SYNTAX      Counter64
    UNITS       "Cells"
    MAX-ACCESS  read-only
    STATUS      current
    DESCRIPTION 
        "This attribute reports the number of errored cells 
         received by the demodulator for this SCTE 55-1 US channel 
         that were successfully corrected. Corrected cells have 
         status 1 in the US SCTE 55-1 OOB packet."
    ::= { docsRphyRpdDevOob551UsChanStatusEntry 8 }
  
docsRphyRpdDevOob551UsChanStatusUncorrectableCellsRcvd OBJECT-TYPE
    SYNTAX      Counter64
    UNITS       "Cells"
    MAX-ACCESS  read-only
    STATUS      current
    DESCRIPTION 
        "This attribute reports the number of errored cells received 
         by the demodulator for this SCTE 55-1 US channel that could 
         not be corrected. Uncorrectable cells have status 3 in the 
         US SCTE 55-1 OOB packet."
    ::= { docsRphyRpdDevOob551UsChanStatusEntry 9 }          

docsRphyRpdDevOob551UsChanStatusTotalCellsRcvd OBJECT-TYPE
    SYNTAX      Counter64
    UNITS       "Cells"
    MAX-ACCESS  read-only
    STATUS      current
    DESCRIPTION 
        "This attribute reports the total of all cells received for 
         this SCTE 55-1 US channel."
    ::= { docsRphyRpdDevOob551UsChanStatusEntry 10 }
        
docsRphyRpdDevOob551UsChanStatusPwrLevel OBJECT-TYPE
    SYNTAX      TenthdB (-160..155)
    UNITS       "dB"
    MAX-ACCESS  read-only
    STATUS      current
    DESCRIPTION 
        "This attribute reports the arithmetic mean power level 
         from nominal of all received MAC Cells by the demodulator 
         for this upstream SCTE 55-1 channel with precision of tenths of a dB. The 
         six power level bits 1 in the US SCTE 55-1 OOB packet report 
         the nominal power per cell in units of 0.5 dB."
    ::= { docsRphyRpdDevOob551UsChanStatusEntry 11 }
        
docsRphyRpdDevOob551UsChanStatusMaxPwrLevel OBJECT-TYPE
    SYNTAX      TenthdB (-160..155)
    UNITS       "dB"
    MAX-ACCESS  read-only
    STATUS      current
    DESCRIPTION 
        "This attribute reports the maximum power level from nominal 
         of all received MAC Cells by the demodulator for this upstream 
         SCTE 55-1 channel with precision of tenths of a dB."
    ::= { docsRphyRpdDevOob551UsChanStatusEntry 12 }
        
docsRphyRpdDevOob551UsChanStatusMinPwrLevel OBJECT-TYPE
    SYNTAX      TenthdB (-160..155)
    UNITS       "dB"
    MAX-ACCESS  read-only
    STATUS      current
    DESCRIPTION 
        "This attribute reports the minimum power level from nominal of 
         all received MAC Cells by the demodulator for this upstream SCTE 55-1 
         channel with precision of tenths of a dB."
    ::= { docsRphyRpdDevOob551UsChanStatusEntry 13 }
  
docsRphyRpdDevOob551UsChanStatusCounterDiscontinuityTime OBJECT-TYPE
    SYNTAX      DateAndTime
    MAX-ACCESS  read-only
    STATUS      current
    DESCRIPTION 
        "This attribute reports the date and time at which 
         any one or more of the counters in this group 
         were created or last reset to zero."
    ::= { docsRphyRpdDevOob551UsChanStatusEntry 14 }

docsRphyRpdDevOob551UsChanStatusOperStatus   OBJECT-TYPE
    SYNTAX      OperStatusType
    MAX-ACCESS  read-only
    STATUS      current
    DESCRIPTION 
        "This attribute reports the operational status
         of the selected channel."
    ::= { docsRphyRpdDevOob551UsChanStatusEntry 15 } 

-- ---------------------------------------------------------------------
-- RPD CrashDataFileStatus Table
-- ---------------------------------------------------------------------

docsRphyRpdDevCrashDataFileStatusTable OBJECT-TYPE
    SYNTAX      SEQUENCE OF DocsRphyRpdDevCrashDataFileStatusEntry
    MAX-ACCESS  not-accessible
    STATUS      current
    DESCRIPTION
        "This table provides status information for the 
         crash analysis data files. The RPD must generate a crash 
         analysis file when it encounters an unrecoverable 
         software or hardware error. 
         The CrashDataFileStatus TLV Type is 100.20."
    REFERENCE 
        "Information Model Mapping: CM-SP-R-OSSI 
         CrashDataFileStatus"
    ::= { docsRphyRpdDevMibObjects 14 }


docsRphyRpdDevCrashDataFileStatusEntry OBJECT-TYPE
    SYNTAX     DocsRphyRpdDevCrashDataFileStatusEntry
    MAX-ACCESS not-accessible
    STATUS     current
    DESCRIPTION
        "The conceptual row of docsRphyRpdDevCrashDataFileStatusTable.
         A row entry of this table represents a file 
         that is available in the device for upload or 
         for which an upload is in progress."
    INDEX { docsRphyRpdDevInfoUniqueId,
            docsRphyRpdDevCrashDataFileStatusIndex}
    ::= { docsRphyRpdDevCrashDataFileStatusTable 1 }


DocsRphyRpdDevCrashDataFileStatusEntry ::= SEQUENCE
    {
    docsRphyRpdDevCrashDataFileStatusIndex                  Unsigned32,
    docsRphyRpdDevCrashDataFileStatusFilename               SnmpAdminString,
    docsRphyRpdDevCrashDataFileStatusFileStatus             INTEGER
    }

docsRphyRpdDevCrashDataFileStatusIndex OBJECT-TYPE
    SYNTAX      Unsigned32
    MAX-ACCESS  not-accessible
    STATUS      current
    DESCRIPTION 
        "This key attribute uniquely identifies a crash analysis file."
    REFERENCE 
        "Information Model Mapping: CM-SP-R-OSSI 
         CrashDataFileStatus::Index"
    ::= { docsRphyRpdDevCrashDataFileStatusEntry 1 }
        
docsRphyRpdDevCrashDataFileStatusFilename OBJECT-TYPE
    SYNTAX      SnmpAdminString (SIZE (1..255))
    MAX-ACCESS  read-only
    STATUS      current
    DESCRIPTION 
        "This attribute contains the name of the crash analysis file,
         stored in the device that is available to be uploaded to the
         server.  Filenames are defined by the application that creates 
         them. The RPD SHOULD generate crash analysis files with names 
         which include RPD's unique id and a timestamp. The timestamp 
         indicates the time when the crash has occurred with granularity
         of one second. The RPD SHOULD format the timestamp in the form 
         'Unix time', which is defined as the number of seconds that have 
         elapsed since midnight Coordinated Universal Time (UTC), 
         Thursday, 1 January 1970. For example, a crash file name 
         'RPD_crash_dump_id_00000187ADF_time_1403405123' indicates that 
         the file was generated by RPD with Unique ID of 00.00.00.18.7A.DF 
         on Sunday 22nd June 2014 02:45:23 AM."
    REFERENCE 
        "Information Model Mapping: CM-SP-R-OSSI 
         CrashDataFileStatus::Filename"
    ::= { docsRphyRpdDevCrashDataFileStatusEntry 2 }
        
docsRphyRpdDevCrashDataFileStatusFileStatus OBJECT-TYPE
    SYNTAX      INTEGER {
                         other(1),
                         availableForUpload(2),
                         uploadInProgress(3),
                         uploadCompleted(4),
                         uploadPending(5),
                         uploadCancelled(6),
                         error(7)                     
                        }
    MAX-ACCESS  read-only
    STATUS      current
    DESCRIPTION 
        "This attribute reflects the status of the crash data file. 
         The possible values are listed below.
         other(1) - Any condition not covered by the other defined values.
         availableForUpload(2) - The file is available to be uploaded.
         uploadInProgress(3) - The file is currently being uploaded. 
         The file is not available for another upload in this state.
         uploadCompleted(4) - The file was successfully uploaded. 
         The file is available for another upload.
         uploadPending(5) - The file has been selected for upload but a 
         condition does not allow the upload to take place. The upload 
         will start when the condition blocking uploads has been removed. 
         For example, another upload that is currently in progress could 
         cause this value to be returned. uploadPending status can also 
         indicate a situation where the RPD is waiting to retry the upload 
         after the initial attempt(s) has failed. The file is not available 
         for another upload in this state.
         uploadCancelled(6) - An upload was cancelled before it completed. 
         The file is available for another upload.
         error(7) - An error occurred and the file was not successfully uploaded. 
         The file is available for another upload."
    REFERENCE 
        "Information Model Mapping: CM-SP-R-OSSI 
         CrashDataFileStatus::FileStatus"
    ::= { docsRphyRpdDevCrashDataFileStatusEntry 3 }

-- ---------------------------------------------------------------------
-- RPD US Signal Quality Table
-- ---------------------------------------------------------------------

docsRphyRpdDevUsSignalQualityTable OBJECT-TYPE
    SYNTAX      SEQUENCE OF DocsRphyRpdDevUsSignalQualityEntry
    MAX-ACCESS  not-accessible
    STATUS      current
    DESCRIPTION
        "This table provide individual upstream signal quality 
         values for RPDs."
    ::= { docsRphyRpdDevMibObjects 15 }


docsRphyRpdDevUsSignalQualityEntry OBJECT-TYPE
    SYNTAX     DocsRphyRpdDevUsSignalQualityEntry
    MAX-ACCESS not-accessible
    STATUS     current
    DESCRIPTION
        "The conceptual row of docsRphyRpdDevUsSignalQualityTable.
         A row entry of this table represents the upstream signal quality
         values of a single RPD"
    INDEX { docsRphyRpdDevInfoUniqueId,
            docsRphyRpdDevUsSignalQualityRfPort,
            docsRphyRpdDevUsSignalQualityChannelIfIndex }
    ::= { docsRphyRpdDevUsSignalQualityTable 1 }


DocsRphyRpdDevUsSignalQualityEntry ::= SEQUENCE
    {
    docsRphyRpdDevUsSignalQualityRfPort                Unsigned32,
    docsRphyRpdDevUsSignalQualityChannelIfIndex        InterfaceIndex,
    docsRphyRpdDevUsSignalQualityRxMer                 TenthdB,
    docsRphyRpdDevUsSignalQualityRxMerSamples          Unsigned32,
    docsRphyRpdDevUsSignalQualityUnerroreds            Counter64,
    docsRphyRpdDevUsSignalQualityCorrecteds            Counter64,
    docsRphyRpdDevUsSignalQualityUncorrectables        Counter64
    }

docsRphyRpdDevUsSignalQualityRfPort OBJECT-TYPE
    SYNTAX      Unsigned32
    MAX-ACCESS  not-accessible
    STATUS      current
    DESCRIPTION 
        "This key attribute reports the RPD RF port number carrying 
         this US channel. This corresponds to the attribute RpdUsRfPortNum 
         of the RpdUsRfPortRef object in the configuration Information Model."
    ::= { docsRphyRpdDevUsSignalQualityEntry 1 }
        
docsRphyRpdDevUsSignalQualityChannelIfIndex OBJECT-TYPE
    SYNTAX      InterfaceIndex
    MAX-ACCESS  not-accessible
    STATUS      current
    DESCRIPTION 
        "This attribute corresponds to the ifIndex of the logical upstream
         channel (ifType docsCableUpstreamChannel(205)) of the CCAP Core
         for this US channel. Note that with upstream virtual combining, 
         this attribute corresponds to the same CCAP Core ifIndex for 
         different RPD unique Ids."
    ::= { docsRphyRpdDevUsSignalQualityEntry 2 }

docsRphyRpdDevUsSignalQualityRxMer OBJECT-TYPE
    SYNTAX      TenthdB (-2147483648..2147483647)
    UNITS       "dB"
    MAX-ACCESS  read-only
    STATUS      current
    DESCRIPTION 
        "This attribute reports an in-channel received average 
         Modulation Error Ratio (MER). An RxMER sample is defined 
         as an estimate, provided by the demodulator, of the ratio: 
         (average constellation energy with equally likely symbols) / 
         (average squared magnitude of error vector)
         RxMER is measured just prior to FEC (trellis/Reed-Solomon) 
         decoding. RxMER includes the effects of the HFC channel as 
         well as implementation effects of the modulator and demodulator. 
         Error vector estimation may vary among demodulator implementations.  
         The CCAP Core RxMER is averaged over a given number of bursts at 
         the burst receiver, which may correspond to transmissions from 
         multiple users. "
    ::= { docsRphyRpdDevUsSignalQualityEntry 3 }    
        
docsRphyRpdDevUsSignalQualityRxMerSamples OBJECT-TYPE
    SYNTAX      Unsigned32
    MAX-ACCESS  read-only
    STATUS      current
    DESCRIPTION 
        "This attribute reports RxMerSamples which is a statistically 
         significant number of bursts for the CCAP Core, processed to 
         arrive at the RxMER value. For the CCAP Core, the MER measurement 
         includes only valid bursts that are not in contention regions."
    ::= { docsRphyRpdDevUsSignalQualityEntry 4 }  

docsRphyRpdDevUsSignalQualityUnerroreds OBJECT-TYPE
    SYNTAX      Counter64
    MAX-ACCESS  read-only
    STATUS      current
    DESCRIPTION 
        "This attribute reports the count of codewords received on 
         this channel without error. This includes all codewords, 
         whether or not they were part of frames destined for this device."
    ::= { docsRphyRpdDevUsSignalQualityEntry 5 }   
        
docsRphyRpdDevUsSignalQualityCorrecteds OBJECT-TYPE
    SYNTAX      Counter64
    MAX-ACCESS  read-only
    STATUS      current
    DESCRIPTION 
        "This attribute reports the count of codewords received on 
         this channel with correctable errors.  This includes all 
         codewords, whether or not they were part of frames destined 
         for this device."
    ::= { docsRphyRpdDevUsSignalQualityEntry 6 }    
        
docsRphyRpdDevUsSignalQualityUncorrectables OBJECT-TYPE
    SYNTAX      Counter64
    MAX-ACCESS  read-only
    STATUS      current
    DESCRIPTION 
        "This attribute reports the count of codewords received on 
         this channel with uncorrectable errors.  This includes all 
         codewords, whether or not they were part of frames destined 
         for this device."
    ::= { docsRphyRpdDevUsSignalQualityEntry 7 } 
            



-- ---------------------------------------------------------------------
-- RPD Host Resources System Table
-- Derived from RFC 2790    
-- ---------------------------------------------------------------------

docsRphyRpdDevHostResSysTable OBJECT-TYPE
    SYNTAX      SEQUENCE OF DocsRphyRpdDevHostResSysEntry
    MAX-ACCESS  not-accessible
    STATUS      current
    DESCRIPTION
        "This object is the container for RPD system attributes.
         The HostResourcesSystem TLV Type is 100.21."
    REFERENCE 
        "Information Model Mapping: CM-SP-R-OSSI 
         HostResourcesSystem"
    ::= { docsRphyRpdDevMibObjects 16 }


docsRphyRpdDevHostResSysEntry OBJECT-TYPE
    SYNTAX     DocsRphyRpdDevHostResSysEntry
    MAX-ACCESS not-accessible
    STATUS     current
    DESCRIPTION
        "The conceptual row of docsRphyRpdDevHostResSysTable.
         A row entry of this table represents the details and statistics 
         of the RPD."
    INDEX { docsRphyRpdDevInfoUniqueId }
    ::= { docsRphyRpdDevHostResSysTable 1 }


DocsRphyRpdDevHostResSysEntry ::= SEQUENCE
    {
    docsRphyRpdDevHostResSysDate    DateAndTime
    }

docsRphyRpdDevHostResSysDate OBJECT-TYPE
    SYNTAX  DateAndTime
    MAX-ACCESS  read-only
    STATUS  current
    DESCRIPTION
        "This attribute reports the RPD's notion of the current 
         local date and time of day."
    REFERENCE 
        "Information Model Mapping: CM-SP-R-OSSI 
         HostResourcesSystem::Date"
    ::= { docsRphyRpdDevHostResSysEntry 1 }


-- ---------------------------------------------------------------------
-- RPD Host Resources Storage Table
-- Derived from RFC 2790    
-- ---------------------------------------------------------------------

docsRphyRpdDevHostResStorTable OBJECT-TYPE
    SYNTAX      SEQUENCE OF DocsRphyRpdDevHostResStorEntry
    MAX-ACCESS  not-accessible
    STATUS      current
    DESCRIPTION
        "This table reports information about logical storage areas on the
        host at the time when the values are read. An entry is associated
        with each logical storage area that is allocated and that has 
        constrained resources. This table represents logical storage areas
        (file systems, disk partitions, etc.), as seen by applications, 
        rather than physical storage resources seen by the operating system. 

         The RPD should log event 66070522 when a memory storage threshold 
         condition is detected. Configuration of memory utilization thresholds
         are left to vendor implementations. For example, a vendor might provide
         a default (non-configurable) threshold of 80 percent utilization as triggering
         a threshold exceeded condition. A vendor might also report a threshold 
         value in bytes utilized. Additional troubleshooting can be performed by 
         reading the HostResourcesStorage table for the Index reported in 
         event 66070522.
     
         The RPD should log event 66070523 when a memory storage threshold condition
         is cleared. A clear condition generally occurs when the memory utilization 
         falls below the defined threshold.
         The HostResourcesStorage TLV Type is 100.22."
    REFERENCE 
        "Information Model Mapping: CM-SP-R-OSSI 
         HostResourcesStorage"
    ::= { docsRphyRpdDevMibObjects 17 }

docsRphyRpdDevHostResStorEntry OBJECT-TYPE
    SYNTAX     DocsRphyRpdDevHostResStorEntry
    MAX-ACCESS not-accessible
    STATUS     current
    DESCRIPTION
        "The conceptual row of docsRphyRpdDevHostResStorTable.
         A row entry of this table represents a logical storage area on
         the host."
     INDEX { docsRphyRpdDevInfoUniqueId,
             docsRphyRpdDevHostResStorIndex}
    ::= { docsRphyRpdDevHostResStorTable 1 }


DocsRphyRpdDevHostResStorEntry ::= SEQUENCE
    {
    docsRphyRpdDevHostResStorIndex                 Unsigned32,
    docsRphyRpdDevHostResStorType                  INTEGER,
    docsRphyRpdDevHostResStorAllocationUnits       Unsigned32,
    docsRphyRpdDevHostResStorAllocationFailures    Counter64,
    docsRphyRpdDevHostResStorSize                  Unsigned32,
    docsRphyRpdDevHostResStorUsed                  Unsigned32,
    docsRphyRpdDevHostResStorDescr                 SnmpAdminString
    }

docsRphyRpdDevHostResStorIndex OBJECT-TYPE
    SYNTAX       Unsigned32  
    MAX-ACCESS   not-accessible
    STATUS       current
    DESCRIPTION
        "A unique value for each logical storage area
         contained by the host."
    REFERENCE 
        "Information Model Mapping: CM-SP-R-OSSI 
         HostResourcesStorage::Index"
    ::= {  docsRphyRpdDevHostResStorEntry 1 }

docsRphyRpdDevHostResStorType OBJECT-TYPE
    SYNTAX       INTEGER {
                          other(1),
                          ram(2),
                          virtualMemory(3),
                          fixedDisk(4),
                          removableDisk(5),
                          floppyDisk(6),
                          compactDisc(7),
                          ramDisk(8),
                          flashMemory(9),
                          networkDisk(10)
                        }
    MAX-ACCESS    read-only
    STATUS        current
    DESCRIPTION
        "This attribute contains the type of storage represented
         by this object. The following storage types are supported:

         other: The storage type identifier used when no other 
         defined type is appropriate

         ram: The storage type identifier used for RAM.

         virtualMemory: The storage type identifier used for virtual memory, 
         temporary storage of swapped or paged memory.

         fixedDisk: The storage type identifier used for non-removable 
         rigid rotating magnetic storage devices.

         removableDisk: The storage type identifier used for removable 
         rigid rotating magnetic storage devices.

         floppyDisk: The storage type identifier used for non-rigid 
         rotating magnetic storage devices.

         compactDisc: The storage type identifier used for read-only
         rotating optical storage devices.

         ramDisk: The storage type identifier used for a file system 
         that is stored in RAM.

         flashMemory: The storage type identifier used for flash memory.

         networkDisk: The storage type identifier used for a networked
         file system."
    REFERENCE 
        "Information Model Mapping: CM-SP-R-OSSI 
         HostResourcesStorage::Type"
       ::= { docsRphyRpdDevHostResStorEntry 2 }
    

docsRphyRpdDevHostResStorAllocationUnits OBJECT-TYPE
    SYNTAX      Unsigned32
    UNITS       "Bytes"
    MAX-ACCESS  read-only
    STATUS      current
    DESCRIPTION
        "The size, in bytes, of the data objects allocated
         from this pool.  If this entry is monitoring sectors,
         blocks, buffers, or packets, for example, this number
         will commonly be greater than one.  Otherwise this
         number will typically be one."
    REFERENCE 
        "Information Model Mapping: CM-SP-R-OSSI 
         HostResourcesStorage::AllocationUnits"
    ::= {  docsRphyRpdDevHostResStorEntry 3 }


docsRphyRpdDevHostResStorAllocationFailures OBJECT-TYPE
    SYNTAX      Counter64
    MAX-ACCESS  read-only
    STATUS      current
    DESCRIPTION
        "The number of requests for storage represented by
         this entry that could not be honored due to not enough
         storage.  It should be noted that as this object has a
         SYNTAX of Counter64, that it does not have a defined
         initial value.  However, it is recommended that this
         object be initialized to zero, even though management
         stations must not depend on such an initialization."
    REFERENCE 
        "Information Model Mapping: CM-SP-R-OSSI 
         HostResourcesStorage::AllocationFailures"
    ::= { docsRphyRpdDevHostResStorEntry 4 }


docsRphyRpdDevHostResStorSize OBJECT-TYPE
    SYNTAX      Unsigned32
    MAX-ACCESS  read-write
    STATUS      current
    DESCRIPTION
        "The size of the storage represented by this entry, in
         units of Storage Allocation Units. This object is
         writable to allow remote configuration of the size of
         the storage area in those cases where such an
         operation makes sense and is possible on the
         underlying system. For example, the amount of main
         memory allocated to a buffer pool might be modified or
         the amount of disk space allocated to virtual memory
         might be modified."
    REFERENCE 
        "Information Model Mapping: CM-SP-R-OSSI 
         HostResourcesStorage::Size"
    ::= {  docsRphyRpdDevHostResStorEntry 5 }

docsRphyRpdDevHostResStorUsed OBJECT-TYPE
    SYNTAX      Unsigned32
    MAX-ACCESS  read-only
    STATUS      current
    DESCRIPTION
        "The amount of the storage represented by this entry
         that is allocated, in units of
         Storage Allocation Units"
    REFERENCE 
        "Information Model Mapping: CM-SP-R-OSSI 
         HostResourcesStorage::Used"
    ::= { docsRphyRpdDevHostResStorEntry 6 }

docsRphyRpdDevHostResStorDescr OBJECT-TYPE
    SYNTAX      SnmpAdminString
    MAX-ACCESS  read-only
    STATUS      current
    DESCRIPTION
        "A description of the type and instance of the storage
         described by this entry."
    REFERENCE 
        "Information Model Mapping: CM-SP-R-OSSI 
         HostResourcesStorage::Descr"
    ::= { docsRphyRpdDevHostResStorEntry 7 }

-- ---------------------------------------------------------------------
-- RPD Host Resources Sw Run Table
-- Derived from RFC 2790    
-- ---------------------------------------------------------------------

docsRphyRpdDevHostResSwRunTable OBJECT-TYPE
    SYNTAX      SEQUENCE OF DocsRphyRpdDevHostResSwRunEntry
    MAX-ACCESS  not-accessible
    STATUS      current
    DESCRIPTION
        "Entries in this table represent each distinct process (i.e., piece of software)
         that is running or loaded into physical or virtual memory in preparation for 
         running at the time when the values are read. This includes the host's operating 
         system, device drivers, and applications.
         The HostResourcesSwRun table does not contain processor resource information, 
         such as CPU information or metrics. However, certain DOCSIS defined events are 
         defined for performance monitoring of RPD processors. 

         The RPD should log event 66070520 when a processor overload condition is detected. 
         Configuration of processor utilization thresholds (percentages) are left to vendor 
         implementations. For example, a vendor might provide a default (non-configurable) 
         threshold of 80% utilization as triggering an overload condition.
         
         The RPD should log event 66070521 when a processor overload condition is cleared. 
         A clear condition generally occurs when the processor utilization falls below the 
         overload threshold over a certain period of time.
         
         The HostResourcesSwRun TLV Type is 100.23."
    REFERENCE 
        "Information Model Mapping: CM-SP-R-OSSI 
         HostResourcesSwRun"
    ::= { docsRphyRpdDevMibObjects 18 }


docsRphyRpdDevHostResSwRunEntry OBJECT-TYPE
    SYNTAX     DocsRphyRpdDevHostResSwRunEntry
    MAX-ACCESS not-accessible
    STATUS     current
    DESCRIPTION
        "The (conceptual) entry for one piece of software
         running on the host. Note that because the installed
         software table only contains information for software
         stored locally on this host, not every piece of
         running software will be found in the installed
         software table.  This is true of software that was
         loaded and run from a non-local source, such as a
         network-mounted file systemA row entry of this table 
         represents a logical storage area on the host."
    INDEX { docsRphyRpdDevInfoUniqueId,
            docsRphyRpdDevHostResSwRunIndex}
    ::= { docsRphyRpdDevHostResSwRunTable 1 }


DocsRphyRpdDevHostResSwRunEntry ::= SEQUENCE
    {
    docsRphyRpdDevHostResSwRunIndex           Unsigned32,
    docsRphyRpdDevHostResSwRunType            INTEGER,
    docsRphyRpdDevHostResSwRunStatus          INTEGER,
    docsRphyRpdDevHostResSwRunPerfCpu         Unsigned32,
    docsRphyRpdDevHostResSwRunPerfMem         Unsigned32,
    docsRphyRpdDevHostResSwRunName            SnmpAdminString
    }
    
docsRphyRpdDevHostResSwRunIndex OBJECT-TYPE
    SYNTAX      Unsigned32
    MAX-ACCESS  not-accessible
    STATUS      current
    DESCRIPTION
        "A unique value for each piece of software running on
         the host.  Wherever possible, this should be the
         system's native, unique identification number."
    REFERENCE 
        "Information Model Mapping: CM-SP-R-OSSI 
         HostResourcesSwRun::Index"
    ::= { docsRphyRpdDevHostResSwRunEntry 1 }

docsRphyRpdDevHostResSwRunType OBJECT-TYPE
    SYNTAX      INTEGER {
                         unknown(1),
                         operatingSystem(2),
                         deviceDriver(3),
                         application(4)
                        }
    MAX-ACCESS  read-only
    STATUS      current
    DESCRIPTION
        "This attribute contains the type of the 
         software piece running on the host.
         Valid values are listed below: 
         
         unknown(1) if the software type is unknown or is not defined by the other options.
         
         operatingSystem(2) if the software is RPD operating system software.
         
         deviceDriver(3) if the software provides communication between RPD operating system 
         software and external devices.
         
         application(4) if the software performs an end-user function."
    REFERENCE 
        "Information Model Mapping: CM-SP-R-OSSI 
         HostResourcesSwRun::Type"
    ::= { docsRphyRpdDevHostResSwRunEntry 2 }


docsRphyRpdDevHostResSwRunStatus OBJECT-TYPE
    SYNTAX      INTEGER {
                         running(1),
                         runnable(2),    -- waiting for resource
                                         -- (i.e., CPU, memory, IO)
                         notRunnable(3), -- loaded but waiting for event
                         invalid(4)      -- not loaded
                        }
    MAX-ACCESS  read-only
    STATUS      current
    DESCRIPTION
         "The status of this running piece of software.
          Setting this value to invalid(4) shall cause this
          software to stop running and to be unloaded. Sets to
          other values are not valid.
          Valid values are listed below:
          
          running(1) if the software is being executed by the RPD.
          
          runnable(2) if the software can be executed by the RPD and is 
          waiting for resources.
          
          notRunnable(3) if the software is loaded on the RPD but awaiting
          an event to initiate execution.
          
          invalid(4) if the software is not installed on the RPD."
    REFERENCE 
        "Information Model Mapping: CM-SP-R-OSSI 
         HostResourcesSwRun::Status"
    ::= { docsRphyRpdDevHostResSwRunEntry 3 }

docsRphyRpdDevHostResSwRunPerfCpu OBJECT-TYPE
    SYNTAX      Unsigned32
    UNITS       "Centiseconds"
    MAX-ACCESS  read-only
    STATUS      current
    DESCRIPTION
         "The number of centi-seconds of the total system's CPU
          resources consumed by this process.  Note that on a
          multi-processor system, this value may increment by
          more than one centi-second in one centi-second of real
          (wall clock) time."
    REFERENCE 
        "Information Model Mapping: CM-SP-R-OSSI 
         HostResourcesSwRun::PerfCpu"
    ::= {  docsRphyRpdDevHostResSwRunEntry 4 }

docsRphyRpdDevHostResSwRunPerfMem OBJECT-TYPE
    SYNTAX      Unsigned32
    MAX-ACCESS  read-only
    STATUS      current
    DESCRIPTION
        "The total amount of real system memory allocated to
         this process."
    REFERENCE 
        "Information Model Mapping: CM-SP-R-OSSI 
         HostResourcesSwRun::PerfMem"
    ::= {  docsRphyRpdDevHostResSwRunEntry 5 }

docsRphyRpdDevHostResSwRunName OBJECT-TYPE
    SYNTAX      SnmpAdminString (SIZE(1..64))
    MAX-ACCESS  read-only
    STATUS      current
    DESCRIPTION
        "A textual description of this running piece of
         software, including the manufacturer, revision, and
         the name by which it is commonly known."
    REFERENCE 
        "Information Model Mapping: CM-SP-R-OSSI 
         HostResourcesSwRun::Name"
    ::= { docsRphyRpdDevHostResSwRunEntry 6 }


-- ---------------------------------------------------------------------
-- RPD Static Pw Capabilities Table
-- ---------------------------------------------------------------------

docsRphyRpdDevStaticPwCapTable OBJECT-TYPE
    SYNTAX      SEQUENCE OF DocsRphyRpdDevStaticPwCapEntry
    MAX-ACCESS  not-accessible
    STATUS      current
    DESCRIPTION
        "This table provides information about the static pseudo-wire
         capabilities of the RPD."
    ::= { docsRphyRpdDevMibObjects 19 }


docsRphyRpdDevStaticPwCapEntry OBJECT-TYPE
    SYNTAX     DocsRphyRpdDevStaticPwCapEntry
    MAX-ACCESS not-accessible
    STATUS     current
    DESCRIPTION
        "The conceptual row of docsRphyRpdDevStaticPwCapTable."
    INDEX { docsRphyRpdDevInfoUniqueId }
    ::= { docsRphyRpdDevStaticPwCapTable 1 }


DocsRphyRpdDevStaticPwCapEntry ::= SEQUENCE
    {
    docsRphyRpdDevStaticPwCapMaxFwdStaticPws                 Unsigned32,
    docsRphyRpdDevStaticPwCapMaxRetStaticPws                 Unsigned32,
    docsRphyRpdDevStaticPwCapSupportsStaticMptDepiPw         TruthValue,
    docsRphyRpdDevStaticPwCapSupportsStaticMpt55d1RetPw      TruthValue,
    docsRphyRpdDevStaticPwCapSupportsStaticPspNdfPw          TruthValue,
    docsRphyRpdDevStaticPwCapSupportsStaticPspNdrPw          TruthValue,
    docsRphyRpdDevStaticPwCapMaxUcastFwdStaticPws            Unsigned32,
    docsRphyRpdDevStaticPwCapSupportsStaticPspNdfUcastPw     TruthValue,
    docsRphyRpdDevStaticPwCapSupportsStaticPspPnmPw          TruthValue,
    docsRphyRpdDevStaticPwCapSupportsStaticPspSpecmanPw      TruthValue,
    docsRphyRpdDevStaticPwCapSupportsDepiPspMultichanPw      TruthValue,
    docsRphyRpdDevStaticPwCapSupportsUepiPws                 TruthValue,
    docsRphyRpdDevStaticPwCapSupportsDtpPw                   TruthValue
    }

docsRphyRpdDevStaticPwCapMaxFwdStaticPws OBJECT-TYPE
    SYNTAX      Unsigned32 (0..65535)
    MAX-ACCESS  read-only
    STATUS      current
    DESCRIPTION 
        "This attribute reports the maximum number of 
         (multicast and unicast) forward static pseudowires
         supported by the RPD."
    ::= { docsRphyRpdDevStaticPwCapEntry 1 }

docsRphyRpdDevStaticPwCapMaxRetStaticPws OBJECT-TYPE
    SYNTAX      Unsigned32 (0..65535)
    MAX-ACCESS  read-only
    STATUS      current
    DESCRIPTION 
        "This attribute reports the maximum number of
         return static pseudowires supported by the RPD.
         An RPD which does not support return static pseudowires
         reports zero."
    ::= { docsRphyRpdDevStaticPwCapEntry 2 }
        
docsRphyRpdDevStaticPwCapSupportsStaticMptDepiPw OBJECT-TYPE
    SYNTAX      TruthValue
    MAX-ACCESS  read-only
    STATUS      current
    DESCRIPTION 
        "This attribute reports whether the RPD supports 
         configuration of static pseudowires of DEPI MPT 
         (MPT-DEPI-PW) subtype.

         The RPD reports a value of false(0) if it does not support 
         configuration of DEPI MPT static pseudowires.

         The RPD reports a value of true(1) if it supports 
         configuration of DEPI MPT static pseudowires."
    ::= { docsRphyRpdDevStaticPwCapEntry 3 }

docsRphyRpdDevStaticPwCapSupportsStaticMpt55d1RetPw OBJECT-TYPE
    SYNTAX      TruthValue
    MAX-ACCESS  read-only
    STATUS      current
    DESCRIPTION 
        "This attribute reports whether the RPD supports 
         configuration of static pseudowires of SCTE 55-1 
         return (MPT-55-1-RET) subtype.

         The RPD reports a value of false(0) if it does not support 
         configuration of SCTE 55-1 return static pseudowires.

         The RPD reports a value of true(1) if it supports configuration
         of SCTE 55-1 return static pseudowires."
    ::= { docsRphyRpdDevStaticPwCapEntry 4 }

docsRphyRpdDevStaticPwCapSupportsStaticPspNdfPw OBJECT-TYPE
    SYNTAX      TruthValue
    MAX-ACCESS  read-only
    STATUS      current
    DESCRIPTION 
        "This attribute reports whether the RPD supports 
         configuration of multicast static pseudowires of PSP NDF
         (PSP-NDF) subtype.

         The RPD reports a value of false(0) if it does not support 
         configuration of multicast PSP-NDF static pseudowires.

         The RPD reports a value of true(1) if it supports configuration
         of multicast PSP-NDF static pseudowires."
        REFERENCE    "DOCSIS DCA MHAv2 Remote PHY OSS Interface Specification
         CM-SP-R-OSSI-I12, SupportsStaticPspNdfMcastPw section."
    ::= { docsRphyRpdDevStaticPwCapEntry 5 }

docsRphyRpdDevStaticPwCapSupportsStaticPspNdrPw OBJECT-TYPE
    SYNTAX      TruthValue
    MAX-ACCESS  read-only
    STATUS      current
    DESCRIPTION 
        "This attribute reports whether the RPD supports 
         configuration of static pseudowires of PSP NDR 
         (PSP-NDR) subtype.

         The RPD reports a value of false(0) if it does not 
         support configuration of PSP-NDR static pseudowires.

         The RPD reports a value of true(1) if it supports configuration
         of PSP-NDR static pseudowires."
    ::= { docsRphyRpdDevStaticPwCapEntry 6 }

docsRphyRpdDevStaticPwCapMaxUcastFwdStaticPws OBJECT-TYPE
    SYNTAX      Unsigned32 (0..65535)
    MAX-ACCESS  read-only
    STATUS      current
    DESCRIPTION 
        "This attribute is used to report the maximum number of
         unicast forward static pseudowires supported by the RPD. 
         An RPD which does not support unicast forward static 
         pseudowires reports zero."
    ::= { docsRphyRpdDevStaticPwCapEntry 7 }

docsRphyRpdDevStaticPwCapSupportsStaticPspNdfUcastPw OBJECT-TYPE
    SYNTAX      TruthValue
    MAX-ACCESS  read-only
    STATUS      current
    DESCRIPTION 
        "This attribute reports whether the RPD supports configuration of
         unicast forward static pseudowires of PSP NDF (PSP-NDF) subtype.

         The RPD reports a value of false(0) if it does not support 
         unicast PSP-NDF static pseudowires.

         The RPD reports a value of true(1) if it supports 
         unicast PSP-NDF static pseudowires."
    ::= { docsRphyRpdDevStaticPwCapEntry 8 }

docsRphyRpdDevStaticPwCapSupportsStaticPspPnmPw OBJECT-TYPE
    SYNTAX      TruthValue
    MAX-ACCESS  read-only
    STATUS      current
    DESCRIPTION 
        "This attribute reports whether the RPD supports configuration
         of static pseudowires of PSP-PNM subtype.

         The RPD reports a value of false(0) if it does not support
         PSP-PNM static pseudowires.

         The RPD reports a value of true(1) if it supports 
         PSP-PNM static pseudowires."
    ::= { docsRphyRpdDevStaticPwCapEntry 9 }

docsRphyRpdDevStaticPwCapSupportsStaticPspSpecmanPw OBJECT-TYPE
    SYNTAX      TruthValue
    MAX-ACCESS  read-only
    STATUS      current
    DESCRIPTION 
        "This attribute reports whether the RPD supports configuration
         of static pseudowires of PSP-SPECMAN subtype.

         The RPD reports a value of false(0) if it does not support 
         PSP-SPECMAN static pseudowires.

         The RPD reports a value of true(1) if it supports
         PSP-SPECMAN static pseudowires."
    ::= { docsRphyRpdDevStaticPwCapEntry 10 }
    
docsRphyRpdDevStaticPwCapSupportsDepiPspMultichanPw  OBJECT-TYPE
    SYNTAX      TruthValue
    MAX-ACCESS  read-only
    STATUS      current
    DESCRIPTION 
        "This attribute reports whether the RPD supports configuration 
         of static pseudowires of subtype PSP-MULTICHAN-PW.
         
         The RPD reports a value of false(0) if is does not support
         PSP-MULTICHAN-PW static pseudowires.
         
         The RPD reports a value of true(1) if is supports 
         PSP-MULTICHAN-PW static pseudowires."
    ::= { docsRphyRpdDevStaticPwCapEntry 11 }
    
docsRphyRpdDevStaticPwCapSupportsUepiPws  OBJECT-TYPE
    SYNTAX      TruthValue
    MAX-ACCESS  read-only
    STATUS      current
    DESCRIPTION 
        "This attribute reports whether the RPD supports configuration 
        of UEPI static pseudowires. A single capability indicates support
        for the pseudowire subtypes listed below.
        
        The RPD reports a value of false(0) if it does not support 
        UEPI static pseudowires.
        
        The RPD reports a value of true(1) if it supports UEPI 
        static pseudowires.
        
        PSP-UEPI-SCQ
        PSP-UEPI-OFDMA  
        PSP-BW-REQ-SCQ 
        PSP-BW-REQ-OFDMA
        PSP-PROBE
        PSP-RNG-REQ-SCQ 
        PSP-RNG-REQ-OFDMA 
        PSP-MAP-SCQ 
        PSP-MAP-OFDMA "
    ::= { docsRphyRpdDevStaticPwCapEntry 12 }
    
docsRphyRpdDevStaticPwCapSupportsDtpPw  OBJECT-TYPE
    SYNTAX      TruthValue
    MAX-ACCESS  read-only
    STATUS      current
    DESCRIPTION 
        "This attribute reports whether the RPD supports configuration
        of static pseudowires for DOCSIS Time Protocol (DTP) operation.

        The RPD reports a value of false(0) if it does not support 
        static pseudowires for DTP operation.
        
        The RPD reports a value of true(1) if it supports UEPI static 
        pseudowires for DTP operation."
    ::= { docsRphyRpdDevStaticPwCapEntry 13 }

-- ---------------------------------------------------------------------
-- RPD External Software Image Support Table
-- ---------------------------------------------------------------------

docsRphyRpdDevExtSwImageSupportTable OBJECT-TYPE
    SYNTAX      SEQUENCE OF DocsRphyRpdDevExtSwImageSupportEntry
    MAX-ACCESS  not-accessible
    STATUS      current
    DESCRIPTION
        "This object provides information about the Main Software Image
         and the additional optional software images that can be maintained
         by the RPD. The ExtSwImageSupport TLV Type is 100.25."
    REFERENCE 
        "Information Model Mapping: CM-SP-R-OSSI 
         ExtSwImageSupport"
    ::= { docsRphyRpdDevMibObjects 20 }


docsRphyRpdDevExtSwImageSupportEntry OBJECT-TYPE
    SYNTAX     DocsRphyRpdDevExtSwImageSupportEntry
    MAX-ACCESS not-accessible
    STATUS     current
    DESCRIPTION
        "The conceptual row of docsRphyRpdDevExtSwImageSupportTable."
    INDEX { docsRphyRpdDevInfoUniqueId,
            docsRphyRpdDevExtSwImageSupportSwImageIndex}
    ::= { docsRphyRpdDevExtSwImageSupportTable 1 }


DocsRphyRpdDevExtSwImageSupportEntry ::= SEQUENCE
    {
    docsRphyRpdDevExtSwImageSupportSwImageIndex         Unsigned32,
    docsRphyRpdDevExtSwImageSupportSwImageLastUpdate    DateAndTime,
    docsRphyRpdDevExtSwImageSupportSwImageName          SnmpAdminString,
    docsRphyRpdDevExtSwImageSupportSwImageDescr         SnmpAdminString,
    docsRphyRpdDevExtSwImageSupportSwImageServerType    InetAddressType,
    docsRphyRpdDevExtSwImageSupportSwImageServerAddress InetAddress
    }

docsRphyRpdDevExtSwImageSupportSwImageIndex OBJECT-TYPE
    SYNTAX  Unsigned32 (0..3)
    MAX-ACCESS  not-accessible
    STATUS  current
    DESCRIPTION
        "This key attribute is used in selecting a software image
         maintained by the RPD. The value of zero is reseved for the 
         Main Software Image. The maximum value of SwImageIndex 
         supported by an RPD is communicated via the RPD Capabilities object."
    REFERENCE 
        "Information Model Mapping: CM-SP-R-OSSI 
         ExtSwImageSupport::SwImageIndex"
    ::= { docsRphyRpdDevExtSwImageSupportEntry 1 }

docsRphyRpdDevExtSwImageSupportSwImageLastUpdate  OBJECT-TYPE
    SYNTAX      DateAndTime
    MAX-ACCESS  read-only
    STATUS      current
    DESCRIPTION
        "This attribute reports the most recent date and time when the selected
         RPD's software image was updated. The RPD preserves the value of this 
         attribute across reboots."
    REFERENCE 
        "Information Model Mapping: CM-SP-R-OSSI 
         ExtSwImageSupport::SwImageLastUpdate"
    ::= { docsRphyRpdDevExtSwImageSupportEntry 2 }
        
docsRphyRpdDevExtSwImageSupportSwImageName OBJECT-TYPE
    SYNTAX      SnmpAdminString (SIZE(1..255))
    MAX-ACCESS  read-only 
    STATUS      current 
    DESCRIPTION 
        "This attribute reports the name of the RPD's software image. 
         The RPD preserves the value of this attribute across reboots."
    REFERENCE 
        "Information Model Mapping: CM-SP-R-OSSI 
         ExtSwImageSupport::SwImageName"
    ::= { docsRphyRpdDevExtSwImageSupportEntry 3 }

docsRphyRpdDevExtSwImageSupportSwImageDescr OBJECT-TYPE
    SYNTAX      SnmpAdminString 
    MAX-ACCESS  read-only 
    STATUS      current 
    DESCRIPTION 
        "This attribute reports human readable description of the SW image
         running at the selected index. For example it can report that the 
         that selected index points to a Fallback software image. The RPD 
         preserves the value of this attribute across reboots."
    REFERENCE 
        "Information Model Mapping: CM-SP-R-OSSI 
         ExtSwImageSupport::SwImageDescr"
    ::= { docsRphyRpdDevExtSwImageSupportEntry 4 }

docsRphyRpdDevExtSwImageSupportSwImageServerType OBJECT-TYPE
    SYNTAX      InetAddressType   
    MAX-ACCESS  read-only
    STATUS      current
    DESCRIPTION 
        "This attribute reports the server Internet address type of the 
         server from which the RPD's selected software image was downloaded. 
         The RPD preserves the value of this attribute across reboots."
    REFERENCE 
        "Information Model Mapping: CM-SP-R-OSSI 
         ExtSwImageSupport::SwImageServerType"
    ::= { docsRphyRpdDevExtSwImageSupportEntry 5 }

docsRphyRpdDevExtSwImageSupportSwImageServerAddress OBJECT-TYPE
    SYNTAX      InetAddress  (SIZE(4|16))
    MAX-ACCESS  read-only
    STATUS      current
    DESCRIPTION 
        "This attribute reports the Internet address of the server from 
         which the RPD's selected software image was downloaded. The RPD 
         preserves the value of this attribute across reboots."
    REFERENCE 
        "Information Model Mapping: CM-SP-R-OSSI 
         ExtSwImageSupport::SwImageServerAddress"
    ::= { docsRphyRpdDevExtSwImageSupportEntry 6 }

-- ---------------------------------------------------------------------
-- RPD Sw Image Capabilities Table
-- ---------------------------------------------------------------------

docsRphyRpdDevSwImageCapTable OBJECT-TYPE
    SYNTAX      SEQUENCE OF DocsRphyRpdDevSwImageCapEntry
    MAX-ACCESS  not-accessible
    STATUS      current
    DESCRIPTION
        "This table provides information about the software image
         capabilities of the RPD."
    ::= { docsRphyRpdDevMibObjects 21 }


docsRphyRpdDevSwImageCapEntry OBJECT-TYPE
    SYNTAX     DocsRphyRpdDevSwImageCapEntry
    MAX-ACCESS not-accessible
    STATUS     current
    DESCRIPTION
        "The conceptual row of docsRphyRpdDevSwImageCapTable."
    INDEX { docsRphyRpdDevInfoUniqueId }
    ::= { docsRphyRpdDevSwImageCapTable 1 }


DocsRphyRpdDevSwImageCapEntry ::= SEQUENCE
    {
    docsRphyRpdDevSwImageCapNumSwImages                  Unsigned32,
    docsRphyRpdDevSwImageCapImageUpgradability           BITS
    }

docsRphyRpdDevSwImageCapNumSwImages OBJECT-TYPE
    SYNTAX      Unsigned32 (1..4)
    MAX-ACCESS  read-only
    STATUS      current
    DESCRIPTION 
        "This attribute reports the number of software 
         images that the RPD supports."
    ::= { docsRphyRpdDevSwImageCapEntry 1 }

docsRphyRpdDevSwImageCapImageUpgradability OBJECT-TYPE
    SYNTAX      BITS {
                      image1Upgradeable(0), 
                      image2Upgradeable(1), 
                      image3Upgradeable(2), 
                      image4Upgradeable(3)
                     }
    MAX-ACCESS  read-only
    STATUS      current
    DESCRIPTION 
        "Bitmask indicating whether the RPD supports SSD of the 
         corresponding sowtware image. For example, bit 0 corresponds 
         to software image with index 0, bit 1 corresponds to software 
         image with index 1, etc.  The value of each bit indicates:
         0 - RPD does not support SSD of the selected image.
         1 - RPD supports SSD of the selected image."
    ::= { docsRphyRpdDevSwImageCapEntry 2 }

-- ---------------------------------------------------------------------
-- RPD Gcp Capabilities Table
-- ---------------------------------------------------------------------

docsRphyRpdDevGcpCapTable OBJECT-TYPE
    SYNTAX      SEQUENCE OF DocsRphyRpdDevGcpCapEntry
    MAX-ACCESS  not-accessible
    STATUS      current
    DESCRIPTION
        "This table provides information about the gcp
         capabilities of the RPD."
    ::= { docsRphyRpdDevMibObjects 22 }


docsRphyRpdDevGcpCapEntry OBJECT-TYPE
    SYNTAX     DocsRphyRpdDevGcpCapEntry
    MAX-ACCESS not-accessible
    STATUS     current
    DESCRIPTION
        "The conceptual row of docsRphyRpdDevGcpCapTable."
    INDEX { docsRphyRpdDevInfoUniqueId }
    ::= { docsRphyRpdDevGcpCapTable 1 }


DocsRphyRpdDevGcpCapEntry ::= SEQUENCE
    {
    docsRphyRpdDevGcpCapGcpKaResponseTime          Unsigned32
    }

docsRphyRpdDevGcpCapGcpKaResponseTime OBJECT-TYPE
    SYNTAX      Unsigned32 (10..1000)
    UNITS       "Milliseconds"
    MAX-ACCESS  read-only
    STATUS      current
    DESCRIPTION 
        "This attribute reports how quickly the
         RPD can respond to GCP Keep Alive messages."
    ::= { docsRphyRpdDevGcpCapEntry 1 }

-- ---------------------------------------------------------------------
-- RPD Ofdm Cfg Capabilities Table
-- ---------------------------------------------------------------------

docsRphyRpdDevOfdmCfgCapTable OBJECT-TYPE
    SYNTAX      SEQUENCE OF DocsRphyRpdDevOfdmCfgCapEntry
    MAX-ACCESS  not-accessible
    STATUS      current
    DESCRIPTION
        "This table provides information about the ofdm cfg
         capabilities of the RPD."
    ::= { docsRphyRpdDevMibObjects 23 }


docsRphyRpdDevOfdmCfgCapEntry OBJECT-TYPE
    SYNTAX     DocsRphyRpdDevOfdmCfgCapEntry
    MAX-ACCESS not-accessible
    STATUS     current
    DESCRIPTION
        "The conceptual row of docsRphyRpdDevOfdmCfgCapTable."
    INDEX { docsRphyRpdDevInfoUniqueId }
    ::= { docsRphyRpdDevOfdmCfgCapTable 1 }


DocsRphyRpdDevOfdmCfgCapEntry ::= SEQUENCE
    {
    docsRphyRpdDevOfdmCfgCapReqOfdmaImDurationCfg          TruthValue,
    docsRphyRpdDevOfdmCfgCapSupportedPilotPatterns         BITS,
    docsRphyRpdDevOfdmCfgCapNumDsOfdmProfiles              Unsigned32,
    docsRphyRpdDevOfdmCfgCapOptionalOfdmModulations        BITS,
    docsRphyRpdDevOfdmCfgCapOptionalOfdmaModulations       BITS
    }

docsRphyRpdDevOfdmCfgCapReqOfdmaImDurationCfg OBJECT-TYPE
    SYNTAX      TruthValue
    MAX-ACCESS  read-only
    STATUS      current
    DESCRIPTION 
        "This attribute is a Boolean value that reports the 
         RPDs need to explicitly configure IM grant duration for OFDMA channels. 
         
         The RPD reports a value of false(0) if the RPD does not require
         configuration of the IM grant duration.

         The RPD reports a value of true(1) if the RPD requires explicit configurations
         IM grant duration."
    ::= { docsRphyRpdDevOfdmCfgCapEntry 1 }

docsRphyRpdDevOfdmCfgCapSupportedPilotPatterns  OBJECT-TYPE
    SYNTAX      BITS {
                      pilotPatternNum5(0),
                      pilotPatternNum6(1),
                      pilotPatternNum7(2), 
                      pilotPatternNum12(3),
                      pilotPatternNum13(4), 
                      pilotPatternNum14(5)   
                     }
    MAX-ACCESS  read-only
    STATUS      current
    DESCRIPTION 
        "This attribute reports the set of supported OFDMA 
         optional pilot patterns for an RPD.
         The RPD reports '0' for the bit corresponding to a pilot 
         pattern not supported by the RPD.
         The RPD reports '1' for the bit corresponding to a pilot
         pattern supported by the RPD."
    REFERENCE 
        "Information Model Mapping: CM-SP-R-OSSI 
         OfdmaCfgCapabilities::SupportedPilotPatterns"
    ::= { docsRphyRpdDevOfdmCfgCapEntry 2 }

docsRphyRpdDevOfdmCfgCapNumDsOfdmProfiles  OBJECT-TYPE
    SYNTAX      Unsigned32 (4..16)
    MAX-ACCESS  read-only
    STATUS      current
    DESCRIPTION 
        "This attribute reports how many OFDM profiles 
         are supported by the RPD."
    ::= { docsRphyRpdDevOfdmCfgCapEntry 3 }

docsRphyRpdDevOfdmCfgCapOptionalOfdmModulations  OBJECT-TYPE
    SYNTAX      BITS {
                      modOrder8192Qam(0),
                      modOrder16384Qam(1)
                     }
    MAX-ACCESS  read-only
    STATUS      current
    DESCRIPTION 
        "This attribute reports whether the RPD supports optional
         OFDM modulation orders defined in [PHYv4.0].

         The RPD reports '0' for the bit corresponding to an OFDM
         modulation order not supported by the RPD.

         The RPD reports '1' for the bit corresponding to an OFDM 
         modulation order supported by the RPD."
    ::= { docsRphyRpdDevOfdmCfgCapEntry 4 }

docsRphyRpdDevOfdmCfgCapOptionalOfdmaModulations  OBJECT-TYPE
    SYNTAX      BITS {
                      modOrder2048Qam(0),
                      modOrder4096Qam(1)
                     }
    MAX-ACCESS  read-only
    STATUS      current
    DESCRIPTION 
        "This attribute reports whether the RPD supports optional 
         OFDMA modulation orders defined in [PHYv4.0].

         The RPD reports '0' for the bit corresponding to an OFDMA
         modulation order not supported by the RPD.

         The RPD reports '1' for the bit corresponding to an OFDMA
         modulation order supported by the RPD."
    ::= { docsRphyRpdDevOfdmCfgCapEntry 5 }

-- ---------------------------------------------------------------------
-- RPD Core Redundancy Capabilities Table
-- ---------------------------------------------------------------------

docsRphyRpdDevCoreRedundancyCapTable OBJECT-TYPE
    SYNTAX      SEQUENCE OF DocsRphyRpdDevCoreRedundancyCapEntry
    MAX-ACCESS  not-accessible
    STATUS      current
    DESCRIPTION
        "This table provides information about the core redundancy
         capabilities of the RPD."
    ::= { docsRphyRpdDevMibObjects 24 }

docsRphyRpdDevCoreRedundancyCapEntry OBJECT-TYPE
    SYNTAX     DocsRphyRpdDevCoreRedundancyCapEntry
    MAX-ACCESS not-accessible
    STATUS     current
    DESCRIPTION
        "The conceptual row of docsRphyRpdDevCoreRedundancyCapTable."
    INDEX { docsRphyRpdDevInfoUniqueId }
    ::= { docsRphyRpdDevCoreRedundancyCapTable 1 }

DocsRphyRpdDevCoreRedundancyCapEntry ::= SEQUENCE
    {
    docsRphyRpdDevCoreRedundancyCapSupportsRedundancy         BITS
    }

 docsRphyRpdDevCoreRedundancyCapSupportsRedundancy  OBJECT-TYPE
     SYNTAX      BITS {
                      handoverSupport(0), 
                      connectionStatusSupport(1), 
                      ccapCoreReconnectSupport(2) 
                     }
     MAX-ACCESS  read-only
     STATUS      current
     DESCRIPTION 
        "This attribute is a bit mask indicating whether the RPD 
         supports HandoverToBackup, ConnectionStatus,      
         and/or ReconnectFromCore features as indicated below:
         xxxxxxx0: RPD does not support handover to backup CCAP
                   Core following failure.
         xxxxxxx1: RPD supports handover to backup CCAP Core.
         xxxxxx0x: RPD does not support ConnectionStatus to 
                   control reconnect to CCAP Core following a failure.
         xxxxxx1x: RPD supports ConnectionStatus to control 
                   reconnect to CCAP Core.
         xxxxx0xx: RPD does not support CCAP Core initiated 
                   reconnect following GCP failure.
         xxxxx1xx: RPD supports CCAP Core initiated reconnect 
                   following GCP failure. "
     ::= { docsRphyRpdDevCoreRedundancyCapEntry 1 }

-- ---------------------------------------------------------------------
-- RPD Core Reset Capabilities Table
-- ---------------------------------------------------------------------

docsRphyRpdDevResetCapTable OBJECT-TYPE
    SYNTAX      SEQUENCE OF DocsRphyRpdDevResetCapEntry
    MAX-ACCESS  not-accessible
    STATUS      current
    DESCRIPTION
        "This table provides information about the reset
         capabilities of the RPD."
    ::= { docsRphyRpdDevMibObjects 25 }

docsRphyRpdDevResetCapEntry OBJECT-TYPE
    SYNTAX     DocsRphyRpdDevResetCapEntry
    MAX-ACCESS not-accessible
    STATUS     current
    DESCRIPTION
        "The conceptual row of docsRphyRpdDevResetCapTable."
    INDEX { docsRphyRpdDevInfoUniqueId }
    ::= { docsRphyRpdDevResetCapTable 1 }

DocsRphyRpdDevResetCapEntry ::= SEQUENCE
    {
    docsRphyRpdDevResetCapSupportsReset         BITS,
    docsRphyRpdDevResetCapResetHistorySize      Unsigned32
    }

docsRphyRpdDevResetCapSupportsReset  OBJECT-TYPE
    SYNTAX      BITS {
                      softResetSupport(0), 
                      nvResetSupport(1), 
                      factoryResetSupport(2)
                     }
    MAX-ACCESS  read-only
    STATUS      current
    DESCRIPTION 
        "This attribute is a bitmask indicating whether the 
         RPD supports SoftReset, NvReset, or FactoryReset as 
         indicated below:
         xxxxxxx0: RPD does not support SoftReset.
         xxxxxxx1: RPD supports SoftReset.
         xxxxxx0x: RPD does not support NvReset.
         xxxxxx1x: RPD supports NvReset.
         xxxxx0xx: RPD does not support FactoryReset.
         xxxxx1xx: RPD supports FactoryReset."
    ::= { docsRphyRpdDevResetCapEntry 1 }
    
docsRphyRpdDevResetCapResetHistorySize OBJECT-TYPE
    SYNTAX      Unsigned32 (0..65535)
    MAX-ACCESS  read-only
    STATUS      current
    DESCRIPTION 
        "This attribute provides the maximum size of the 
         ResetHistory table.
         The RPD is required to support a minimum of 50 entries
         in the ResetHistory table."
    ::= { docsRphyRpdDevResetCapEntry 2 }

-- ---------------------------------------------------------------------
-- RPD Full Duplex Capabilities Table
-- ---------------------------------------------------------------------

docsRphyRpdDevFdxCapTable OBJECT-TYPE
    SYNTAX      SEQUENCE OF DocsRphyRpdDevFdxCapEntry
    MAX-ACCESS  not-accessible
    STATUS      current
    DESCRIPTION
        "This table provides information about the full-duplex
         capabilities of the RPD."
    ::= { docsRphyRpdDevMibObjects 26 }

docsRphyRpdDevFdxCapEntry OBJECT-TYPE
    SYNTAX     DocsRphyRpdDevFdxCapEntry
    MAX-ACCESS not-accessible
    STATUS     current
    DESCRIPTION
        "The conceptual row of docsRphyRpdDevFdxCapTable."
    INDEX { docsRphyRpdDevInfoUniqueId }
    ::= { docsRphyRpdDevFdxCapTable 1 }

DocsRphyRpdDevFdxCapEntry ::= SEQUENCE
    {
    docsRphyRpdDevFdxCapSupportsFdx           TruthValue,
    docsRphyRpdDevFdxCapSupportsZblInsertion  TruthValue,
    docsRphyRpdDevFdxCapZblInsMsgLeadTime     Unsigned32
    }

docsRphyRpdDevFdxCapSupportsFdx  OBJECT-TYPE
    SYNTAX      TruthValue
    MAX-ACCESS  read-only
    STATUS      current
    DESCRIPTION 
        "This attribute reports the RPDs capability to 
         support FDX operation. The value 0 (false) indicates 
         the RPD does not support FDX operation. The value 1 (true) 
         indicates the RPD does support FDX operation."
    REFERENCE 
        "Information Model Mapping: CM-SP-R-OSSI 
         FdxCapabilities::SupportsFdx"
    ::= { docsRphyRpdDevFdxCapEntry 1 }

docsRphyRpdDevFdxCapSupportsZblInsertion  OBJECT-TYPE
    SYNTAX      TruthValue
    MAX-ACCESS  read-only
    STATUS      current
    DESCRIPTION 
        "This attribute reports the RPDs capability to 
         receive the Zero Bit Loading (ZBL) Insertion message 
         and insert ZBL as directed by the message. 
         The RPD reports a value of false(0) if the RPD does
         not support the ZBL  Insertion message.
         The RPD reports a value of true(1) if the RPD supports
         ZBL Insertion message."
    REFERENCE 
        "Information Model Mapping: CM-SP-R-OSSI 
         FdxCapabilities::SupportsZblInsertion"
    ::= { docsRphyRpdDevFdxCapEntry 2 }

docsRphyRpdDevFdxCapZblInsMsgLeadTime  OBJECT-TYPE
    SYNTAX      Unsigned32
    UNITS       "microseconds"
    MAX-ACCESS  read-only
    STATUS      current
    DESCRIPTION 
        "This attribute reports the minimum lead time required 
         by the RPD to receive the ZBL Insertion message 
         ahead of the starting timestamp."
    REFERENCE 
        "Information Model Mapping: CM-SP-R-OSSI 
         FdxCapabilities::ZblInsMsgLeadTime"
    ::= { docsRphyRpdDevFdxCapEntry 3 }

-- ---------------------------------------------------------------------
-- RPD Rdti Capabilities Table
-- ---------------------------------------------------------------------

docsRphyRpdDevRdtiCapTable OBJECT-TYPE
    SYNTAX      SEQUENCE OF DocsRphyRpdDevRdtiCapEntry
    MAX-ACCESS  not-accessible
    STATUS      current
    DESCRIPTION
        "This table reports the RPD's capabilities related 
         to time synchronization. The RdtiCapabilities TLV
         Type is 50.34."
    REFERENCE 
        "Information Model Mapping: CM-SP-R-OSSI 
         RdtiCapabilities"
    ::= { docsRphyRpdDevMibObjects 27 }

docsRphyRpdDevRdtiCapEntry OBJECT-TYPE
    SYNTAX     DocsRphyRpdDevRdtiCapEntry
    MAX-ACCESS not-accessible
    STATUS     current
    DESCRIPTION
        "The conceptual row of docsRphyRpdDevRdtiCapTable."
    INDEX { docsRphyRpdDevInfoUniqueId }
    ::= { docsRphyRpdDevRdtiCapTable 1 }

DocsRphyRpdDevRdtiCapEntry ::= SEQUENCE
    {
    docsRphyRpdDevRdtiCapNumPtpPortsPerEnetPort     Unsigned32,
    docsRphyRpdDevRdtiCapSupportsSyncE              TruthValue,
    docsRphyRpdDevRdtiCapSupportsG8275d1            TruthValue,
    docsRphyRpdDevRdtiCapSupportsDtpPseudowire      TruthValue
    }

docsRphyRpdDevRdtiCapNumPtpPortsPerEnetPort  OBJECT-TYPE
    SYNTAX      Unsigned32
    MAX-ACCESS  read-only
    STATUS      current
    DESCRIPTION 
        "This attribute reports how many PTP ports the RPD supports
         per CIN-facing Ethernet port. If the RPD does not support 
         PTP port configuration from the CCAP Core, as it can be 
         in the case of PHY Shelf device, the RPD reports zero."
    REFERENCE 
        "Information Model Mapping: CM-SP-R-OSSI 
         RdtiCapabilities::NumPtpPortsPerEnetPort"
    ::= { docsRphyRpdDevRdtiCapEntry 1 }
    
docsRphyRpdDevRdtiCapSupportsSyncE  OBJECT-TYPE
    SYNTAX      TruthValue
    MAX-ACCESS  read-only
    STATUS      current
    DESCRIPTION 
        "This attribute reports whether the RPD supports 
         synchronous Ethernet (SyncE).
         
         When the value of this attribute is reported as
         'true', the RPD supports SyncE.

         When the value of this attribute is reported as 
         'false', the RPD does not support SyncE."
    REFERENCE 
        "Information Model Mapping: CM-SP-R-OSSI 
         RdtiCapabilities::SupportsSyncE"
    ::= { docsRphyRpdDevRdtiCapEntry 2 }
    
docsRphyRpdDevRdtiCapSupportsG8275d1   OBJECT-TYPE
    SYNTAX      TruthValue
    MAX-ACCESS  read-only
    STATUS      current
    DESCRIPTION 
        "This attribute reports whether the RPD supports 
         G.8275.1 PTP profile.
 
         When the value of this attribute is reported as 'true', 
         the RPD supports G.8275.1 profile.

         When the value of this attribute is reported as 'false', 
         the RPD does not support G.8275.1 profile."
    REFERENCE 
        "Information Model Mapping: CM-SP-R-OSSI 
         RdtiCapabilities::SupportsG8275d1"
    ::= { docsRphyRpdDevRdtiCapEntry 3 }
    
docsRphyRpdDevRdtiCapSupportsDtpPseudowire   OBJECT-TYPE
    SYNTAX      TruthValue
    MAX-ACCESS  read-only
    STATUS      current
    DESCRIPTION 
        "This attribute reports whether the RPD supports 
         the DTP pseudowire.
 
         When the value of this attribute is reported as 'true', 
         the RPD supports the DTP pseudowire.
         
         When the value of this attribute is reported as 'false', 
         the RPD does not support the DTP pseudowire."
    REFERENCE 
        "Information Model Mapping: CM-SP-R-OSSI 
         RdtiCapabilities::SupportsDtpPseudowire"
    ::= { docsRphyRpdDevRdtiCapEntry 4 }


-- ---------------------------------------------------------------------
-- RPD Downstream Capabilities Table
-- ---------------------------------------------------------------------

docsRphyRpdDevDsCapTable OBJECT-TYPE
    SYNTAX      SEQUENCE OF DocsRphyRpdDevDsCapEntry
    MAX-ACCESS  not-accessible
    STATUS      current
    DESCRIPTION
        "This table reports the RPD's OFDM downstream 
         channel capabilities.
         The DsCapabilities TLV Type is 50.51."
    REFERENCE 
        "Information Model Mapping: CM-SP-R-OSSI 
         DsCapabilities"
    ::= { docsRphyRpdDevMibObjects 28 }

docsRphyRpdDevDsCapEntry OBJECT-TYPE
    SYNTAX     DocsRphyRpdDevDsCapEntry
    MAX-ACCESS not-accessible
    STATUS     current
    DESCRIPTION
        "The conceptual row of docsRphyRpdDevDsCapTable."
    INDEX { docsRphyRpdDevInfoUniqueId }
    ::= { docsRphyRpdDevDsCapTable 1 }

DocsRphyRpdDevDsCapEntry ::= SEQUENCE
    {
    docsRphyRpdDevDsCapScQamInterleaverSupport          BITS,
    docsRphyRpdDevDsCapMaxDocsisScQamChannels           Unsigned32,
    docsRphyRpdDevDsCapMaxMultipleScQamPspSessions      Unsigned32,
    docsRphyRpdDevDsCapMaxNumBdrs                       Unsigned32,
    docsRphyRpdDevDsCapMaxNumBcgs                       Unsigned32,
    docsRphyRpdDevDsCapSupportsDsScQamModulationQam128  TruthValue,
    docsRphyRpdDevDsCapSupportsTiltMinimumFrequency     TruthValue
    }

docsRphyRpdDevDsCapScQamInterleaverSupport OBJECT-TYPE
    SYNTAX      BITS {
                      reserved(0),
                      taps8Increment16(1),
                      taps16Increment8(2),
                      taps32Increment4(3),
                      taps64Increment2(4),
                      taps128Increment1(5),
                      taps12Increment17(6),
                      taps128Increment2(7),
                      taps128Increment3(8),
                      taps128Increment4(9),
                      taps128Increment5(10),
                      taps128Increment6(11),
                      taps128Increment7(12),
                      taps128Increment8(13)
                     }
    MAX-ACCESS  read-only
    STATUS      current
    DESCRIPTION 
        "This attribute reports the RPDs support for 
         interleaver settings for downstream SC-QAM channels. 
         The value is a bitmask specifying which of 13 downstream 
         SC-QAM interleaver settings the RPD is capable of supporting. 
         When a bit corresponding to an interleaver setting is set to 1, 
         the RPD supports the interleaver setting. If the bit corresponding 
         to an interleaver setting is set to 0, the RPD does not support
         the interleaver setting."
    REFERENCE 
        "Information Model Mapping: CM-SP-R-OSSI 
         DsCapabilities::ScQamInterleaverSupport"
    ::= { docsRphyRpdDevDsCapEntry 1 }

docsRphyRpdDevDsCapMaxDocsisScQamChannels  OBJECT-TYPE
    SYNTAX      Unsigned32
    MAX-ACCESS  read-only
    STATUS      current
    DESCRIPTION 
        "This attribute reports the maximum number of downstream 
         DOCSIS SC-QAM channels the RPD can be configured to support
         on each downstream RF port. A downstream DOCSIS SC-QAM channel 
         is one configured with OperationalMode (TLV 62.6) set to 
         Docsis(value 2). This value is equal or lower than the reported 
         capability NumDsScQamChannels, which is the number of supported SC-QAM 
         channels whether or not they are configured for DOCSIS operation."
    REFERENCE 
        "Information Model Mapping: CM-SP-R-OSSI 
         DsCapabilities::MaxDocsisScQamChannels"
    ::= { docsRphyRpdDevDsCapEntry 2}

docsRphyRpdDevDsCapMaxMultipleScQamPspSessions  OBJECT-TYPE
    SYNTAX      Unsigned32 (8..79)
    MAX-ACCESS  read-only
    STATUS      current
    DESCRIPTION 
        "This attribute reports the maximum number of PSP sessions 
         with more than one SC-QAM channel that the RPD can support 
         per downstream RF port. Currently, multiple-channel PSP sessions
         are specified for only DOCSIS SC-QAM channels [DEPI].
         An RPD supports at least 8 PSP sessions per port with multiple 
         DOCSIS SC-QAM channels (DEPI). This is the lowest permitted value 
         of the capability. The maximum value is when all NumDsScQamChannels 
         (TLV 50.6) are in two-channel PSP sessions."
    REFERENCE 
        "Information Model Mapping: CM-SP-R-OSSI 
         DsCapabilities::MaxMultipleScQamPspSessions"
    ::= { docsRphyRpdDevDsCapEntry 3}
    
docsRphyRpdDevDsCapMaxNumBdrs  OBJECT-TYPE
    SYNTAX      Unsigned32 
    MAX-ACCESS  read-only
    STATUS      current
    DESCRIPTION 
        "This attribute reports the maximum number of BDRs
         supported by the RPD."
    REFERENCE 
        "Information Model Mapping: CM-SP-R-OSSI 
         DsCapabilities::MaxNumBdrs"
    ::= { docsRphyRpdDevDsCapEntry 4}
    
docsRphyRpdDevDsCapMaxNumBcgs  OBJECT-TYPE
    SYNTAX      Unsigned32 
    MAX-ACCESS  read-only
    STATUS      current
    DESCRIPTION 
        "This attribute reports the maximum number of BCGs
         supported by the RPD."
    REFERENCE 
        "Information Model Mapping: CM-SP-R-OSSI 
         DsCapabilities::MaxNumBcgs"
    ::= { docsRphyRpdDevDsCapEntry 5}
    
docsRphyRpdDevDsCapSupportsDsScQamModulationQam128  OBJECT-TYPE
    SYNTAX      TruthValue
    MAX-ACCESS  read-only
    STATUS      current
    DESCRIPTION 
        "This attribute reports whether the RPD supports 
         QAM128 modulation for DS SC-QAM video channels.
         
         When the value of this attribute is reported as 
         'true', the RPD supports QAM128 modulation for 
         DS SC-QAM channels.
         
         When the value of this attribute is reported as 
         'false', the RPD does not support QAM128 
         modulation for DS SC-QAM channels."
    REFERENCE 
        "Information Model Mapping: CM-SP-R-OSSI 
         DsCapabilities::SupportsDsScQamModulationQam128"
    ::= { docsRphyRpdDevDsCapEntry 6}

    docsRphyRpdDevDsCapSupportsTiltMinimumFrequency  OBJECT-TYPE
    SYNTAX      TruthValue
    MAX-ACCESS  read-only
    STATUS      current
    DESCRIPTION 
        "This attribute reports whether the RPD supports
         TiltMinimumFrequency TLV 61.9 for configuring
         downstream tilt slope.
         When the value of this attribute is reported as
         'true', the RPD supports writes to TiltMinimumFrequency
         TLV 61.9 to fully specify the slope of the downstream
         tilt along with TiltValue TLV 61.5 and
         TiltMaximumFrequency TLV 61.6.
         When the value of this attribute is reported as
         'false', the slope of downstream tilt is vendor-specific
         based on configuration of TiltValue TLV 61.5 and
         TiltMaximumFrequency TLV 61.6."
    REFERENCE 
        "Information Model Mapping: CM-SP-R-OSSI 
         DsCapabilities::SupportsTiltMinimumFrequency"
    ::= { docsRphyRpdDevDsCapEntry 7}

-- ---------------------------------------------------------------------
-- RPD Spectrum Capture Capabilities Table
-- ---------------------------------------------------------------------

docsRphyRpdDevSpecCaptureCapTable OBJECT-TYPE
    SYNTAX      SEQUENCE OF DocsRphyRpdDevSpecCaptureCapEntry
    MAX-ACCESS  not-accessible
    STATUS      current
    DESCRIPTION
        "This table reports RPD capabilities for Upstream Triggered
           Spectrum Capture Proactive Network Management functionality.
         The SpectrumCaptureCapabilities TLV Type is 50.59."
    REFERENCE 
        "Information Model Mapping: CM-SP-R-OSSI 
         SpectrumCaptureCapabilities"
    ::= { docsRphyRpdDevMibObjects 29 }

docsRphyRpdDevSpecCaptureCapEntry OBJECT-TYPE
    SYNTAX     DocsRphyRpdDevSpecCaptureCapEntry
    MAX-ACCESS not-accessible
    STATUS     current
    DESCRIPTION
        "The conceptual row of docsRphyRpdDevSpecCaptureCapTable."
    INDEX { docsRphyRpdDevInfoUniqueId }
    ::= { docsRphyRpdDevSpecCaptureCapTable 1 }

DocsRphyRpdDevSpecCaptureCapEntry ::= SEQUENCE
    {
    docsRphyRpdDevSpecCaptureCapNumSacs     Unsigned32
    }

docsRphyRpdDevSpecCaptureCapNumSacs OBJECT-TYPE
    SYNTAX      Unsigned32
    MAX-ACCESS  read-only
    STATUS      current
    DESCRIPTION 
        "This attribute reports the number of 
         Spectrum Analysis Circuits (SACs) the RPD supports."
    REFERENCE 
        "Information Model Mapping: CM-SP-R-OSSI 
         SpectrumCaptureCapabilities::NumSacs"
    ::= { docsRphyRpdDevSpecCaptureCapEntry 1}

-- ---------------------------------------------------------------------
-- RPD Spectrum Analysis Circuit (SAC) Capabilities Table
-- ---------------------------------------------------------------------

docsRphyRpdDevSacCapTable OBJECT-TYPE
    SYNTAX      SEQUENCE OF DocsRphyRpdDevSacCapEntry
    MAX-ACCESS  not-accessible
    STATUS      current
    DESCRIPTION
        "This table reports the capabilities of each Spectrum Analysis 
         Circuit implemented in the RPD. 
         The SacCapabilities TLV Type is 50.59.2."
    REFERENCE 
        "Information Model Mapping: CM-SP-R-OSSI 
         SacCapabilities"
    ::= { docsRphyRpdDevMibObjects 30 }

docsRphyRpdDevSacCapEntry OBJECT-TYPE
    SYNTAX     DocsRphyRpdDevSacCapEntry
    MAX-ACCESS not-accessible
    STATUS     current
    DESCRIPTION
        "The conceptual row of docsRphyRpdDevSacCapTable."
    INDEX { docsRphyRpdDevInfoUniqueId, docsRphyRpdDevSacCapSacIndex }
    ::= { docsRphyRpdDevSacCapTable 1 }

DocsRphyRpdDevSacCapEntry ::= SEQUENCE
    {
    docsRphyRpdDevSacCapSacIndex               Unsigned32,
    docsRphyRpdDevSacCapSacDescription         SnmpAdminString,
    docsRphyRpdDevSacCapMaxCaptureSpan         Unsigned32,
    docsRphyRpdDevSacCapMinCaptureFreq         Unsigned32,
    docsRphyRpdDevSacCapMaxCaptureFreq         Unsigned32,
    docsRphyRpdDevSacCapSuppTriggerModes       BITS,
    docsRphyRpdDevSacCapSuppOutputFormats      BITS,
    docsRphyRpdDevSacCapSuppWindowFormats      BITS,
    docsRphyRpdDevSacCapSuppAveraging          TruthValue,
    docsRphyRpdDevSacCapSuppAggrMethods        BITS,
    docsRphyRpdDevSacCapSuppSpecQual           TruthValue,
    docsRphyRpdDevSacCapMaxNumBins             Unsigned32,
    docsRphyRpdDevSacCapMinNumBins             Unsigned32,
    docsRphyRpdDevSacCapMinRepeatPeriod        Unsigned32,
    docsRphyRpdDevSacCapSuppTrigChanTypes      BITS,
    docsRphyRpdDevSacCapPwType                 BITS,
    docsRphyRpdDevSacCapLowestCapturePort      Unsigned32,
    docsRphyRpdDevSacCapHighestCapturePort     Unsigned32,
    docsRphyRpdDevSacCapSuppScanCapture        TruthValue,
    docsRphyRpdDevSacCapMinScanRepeatPeriod    Unsigned32
    }

docsRphyRpdDevSacCapSacIndex OBJECT-TYPE
    SYNTAX      Unsigned32
    MAX-ACCESS  not-accessible
    STATUS      current
    DESCRIPTION 
        "This attribute uniquely identifies a SAC in an RPD."
    ::= { docsRphyRpdDevSacCapEntry 1}

docsRphyRpdDevSacCapSacDescription OBJECT-TYPE
    SYNTAX      SnmpAdminString (SIZE (0..64))
    MAX-ACCESS  read-only
    STATUS      current
    DESCRIPTION 
        "This attribute is a human readable description of a SAC, 
         for example: Wideband Spectrum Analysis Circuit, 
         frequency range 5-85 MHz."
    ::= { docsRphyRpdDevSacCapEntry 2}

docsRphyRpdDevSacCapMaxCaptureSpan OBJECT-TYPE
    SYNTAX      Unsigned32
    UNITS       "Hz"
    MAX-ACCESS  read-only
    STATUS      current
    DESCRIPTION 
        "This attribute reports the maximum value of 
         the frequency span supported by the SAC"
    ::= { docsRphyRpdDevSacCapEntry 3}

docsRphyRpdDevSacCapMinCaptureFreq OBJECT-TYPE
    SYNTAX      Unsigned32
    UNITS       "Hz"
    MAX-ACCESS  read-only
    STATUS      current
    DESCRIPTION 
        "This attribute reports the lowest limit of 
         the spectrum that can be captured by the SAC."
    ::= { docsRphyRpdDevSacCapEntry 4}

docsRphyRpdDevSacCapMaxCaptureFreq OBJECT-TYPE
    SYNTAX      Unsigned32
    UNITS       "Hz"
    MAX-ACCESS  read-only
    STATUS      current
    DESCRIPTION 
        "This attribute reports the upper limit of 
         the spectrum that can be captured by the SAC."
    ::= { docsRphyRpdDevSacCapEntry 5}

docsRphyRpdDevSacCapSuppTriggerModes OBJECT-TYPE
    SYNTAX      BITS {
                      freeRunning(0),
                      miniSlotCount(1), 
                      sid(2), 
                      notUsed(3), 
                      quietProbeSymbol(4), 
                      burstIuc(5),
                      timestamp(6),
                      activeProbe(7)
                    }
    MAX-ACCESS  read-only
    STATUS      current
    DESCRIPTION 
        "This attribute reports the Triggered Spectrum Capture
         trigger modes the RPD SAC supports. The value is a bitmask
         specifying which of 7 spectrum capture trigger modes the 
         SAC is capable of supporting. When a bit corresponding to a 
         trigger mode is set to 1, the RPD supports the trigger mode. 
         If the bit corresponding to a trigger mode is set to 0, 
         the SAC does not support the trigger mode."
    ::= { docsRphyRpdDevSacCapEntry 6 }

docsRphyRpdDevSacCapSuppOutputFormats OBJECT-TYPE
    SYNTAX      BITS {
                      timeIQ(0),
                      fftPower(1), 
                      rawAdc(2), 
                      fftIQ(3), 
                      fftAmplitude(4), 
                      fftDb(5)
                     }
    MAX-ACCESS  read-only
    STATUS      current
    DESCRIPTION 
        "This attribute reports the Triggered Spectrum Capture 
         output data file formats the RPD SAC supports. The value 
         is a bitmask specifying which of 6 output data file formats
         the SAC is capable of supporting. When a bit corresponding to 
         an output data file format is set to 1, the SAC supports the format. 
         If the bit corresponding to an output data file format is set 
         to 0, the SAC does not support the format."
    ::= { docsRphyRpdDevSacCapEntry 7 }

docsRphyRpdDevSacCapSuppWindowFormats OBJECT-TYPE
    SYNTAX      BITS {
                      rectangular(0),
                      hann(1), 
                      blackmanHarris(2), 
                      hamming(3), 
                      flatTop(4), 
                      gaussian(5),
                      chebyshev(6)
                     }
    MAX-ACCESS  read-only
    STATUS      current
    DESCRIPTION 
        "This attribute reports the Triggered Spectrum Capture 
         data sample window functions the RPD SAC supports. 
         The value is a bitmask specifying which of 7 window 
         functions or formats the SAC is capable of supporting. 
         When a bit corresponding to a window function is set to 1, 
         the SAC supports the window function. If the bit corresponding
         to a window function is set to 0, the SAC does not 
         support the window function."
    ::= { docsRphyRpdDevSacCapEntry 8 }

docsRphyRpdDevSacCapSuppAveraging OBJECT-TYPE
    SYNTAX      TruthValue
    MAX-ACCESS  read-only
    STATUS      current
    DESCRIPTION 
        "This attribute reports the RPD SACs capability to support 
         Triggered Spectrum Capture data averaging. The value 0 (false) 
         indicates the SAC does not support the data averaging operation. 
         The value 1 (true) indicates the SAC does support data averaging."
    ::= { docsRphyRpdDevSacCapEntry 9}

docsRphyRpdDevSacCapSuppAggrMethods OBJECT-TYPE
    SYNTAX      BITS {
                      maxHold(0)
                     }
    MAX-ACCESS  read-only
    STATUS      current
    DESCRIPTION 
        "This attribute reports the Triggered Spectrum Capture 
         data aggregation methods the RPD SAC supports. 
         The value is a bitmask specifying which aggregation method the 
         SAC is capable of supporting. When a bit corresponding to an 
         aggregation method is set to 1, the SAC supports the aggregation method. 
         If the bit corresponding to a window function is set to 0, the SAC does 
         not support the aggregation method."
    ::= { docsRphyRpdDevSacCapEntry 10 }

docsRphyRpdDevSacCapSuppSpecQual OBJECT-TYPE
    SYNTAX      TruthValue
    MAX-ACCESS  read-only
    STATUS      current
    DESCRIPTION 
        "This attribute reports the SACs capability to support
         Triggered Spectrum Capture spectrum qualification. 
         The value 0 (false) indicates the SAC does not 
         support spectrum qualification. The value 1 (true) indicates
         the SAC does support spectrum qualification."
    ::= { docsRphyRpdDevSacCapEntry 11 }

docsRphyRpdDevSacCapMaxNumBins OBJECT-TYPE
    SYNTAX      Unsigned32
    MAX-ACCESS  read-only
    STATUS      current
    DESCRIPTION 
        "This attribute reports the maximum number of 
         Fast Fourier Transform (FFT) bins the RPDs SAC 
         supports for Triggered Spectrum Capture."
    ::= { docsRphyRpdDevSacCapEntry 12 }

docsRphyRpdDevSacCapMinNumBins OBJECT-TYPE
    SYNTAX      Unsigned32
    MAX-ACCESS  read-only
    STATUS      current
    DESCRIPTION 
        "This attribute reports the minimum number of 
         Fast Fourier Transform (FFT) bins the RPDs SAC 
         supports for Triggered Spectrum Capture."
    ::= { docsRphyRpdDevSacCapEntry 13 }

docsRphyRpdDevSacCapMinRepeatPeriod OBJECT-TYPE
    SYNTAX      Unsigned32
    MAX-ACCESS  read-only
    STATUS      current
    DESCRIPTION 
        "This attribute reports the minimum duration 
         of the RepeatPeriod supported by the SAC."
    ::= { docsRphyRpdDevSacCapEntry 14 }

docsRphyRpdDevSacCapSuppTrigChanTypes OBJECT-TYPE
    SYNTAX      BITS {
                      scQamChan(0),
                      ofdmaChan(1)
                     }
    MAX-ACCESS  read-only
    STATUS      current
    DESCRIPTION 
        "This attribute reports all supported channel types 
         that can be used for triggers by the SAC. The value is a 
         bitmask specifying which channel types the SAC is capable 
         of supporting as triggers.The RPD reports 0 for the bit 
         corresponding to a channel type if the SAC does not 
         support the channel type as a trigger.The RPD reports 1 for 
         the bit corresponding to a channel type if the SAC supports
         the channel type as a trigger."
    ::= { docsRphyRpdDevSacCapEntry 15 }

docsRphyRpdDevSacCapPwType OBJECT-TYPE
    SYNTAX      BITS {
                      pnm(0),
                      specMan(1)
                     }
    MAX-ACCESS  read-only
    STATUS      current
    DESCRIPTION 
        "This attribute reports which pseudowire (PW) types
         the SAC is capable of using. The value is a bitmask 
         specifying which PW types the SAC is capable of using. 
         
         The RPD returns value 0 to the CCAP Core in GCP TLV 50.59.2.16 
         to report PwType as PNM pseudowire type and the CCAP Core will 
         return value 0x80 in response to an SNMP request for 
         SacCapabilities::PwType to report PNM pseudowire type.
         
         The RPD returns value 1 to the CCAP Core in GCP TLV 50.59.2.16 
         to report PwType as Spectrum Management pseudowire type and the CCAP 
         Core will return value 0x40 in response to an SNMP request for 
         SacCapabilities::PwType to report Spectrum Management pseudowire type.

         Other values are not defined."
    ::= { docsRphyRpdDevSacCapEntry 16 }

docsRphyRpdDevSacCapLowestCapturePort OBJECT-TYPE
    SYNTAX      Unsigned32
    MAX-ACCESS  read-only
    STATUS      current
    DESCRIPTION 
        "This attribute reports the lowest upstream RF port
         index the SAC can operate on."
    ::= { docsRphyRpdDevSacCapEntry 17 }

docsRphyRpdDevSacCapHighestCapturePort OBJECT-TYPE
    SYNTAX      Unsigned32
    MAX-ACCESS  read-only
    STATUS      current
    DESCRIPTION 
        "This attribute reports the highest upstream RF port
         index the SAC can operate on."
    ::= { docsRphyRpdDevSacCapEntry 18 }

docsRphyRpdDevSacCapSuppScanCapture OBJECT-TYPE
    SYNTAX      TruthValue
    MAX-ACCESS  read-only
    STATUS      current
    DESCRIPTION 
        "This attribute indicates whether the SAC supports 
         Port Scanning Capture. Port Scanning Capture is a 
         method of operation in free-running mode in which the 
         SAC sequentially captures spectrum from two or more
         US RF ports. The value 0 (false) indicates the SAC does
         not support Port Scanning Capture. The value 1 (true) 
         indicates the SAC does support Port Scanning Capture."
    ::= { docsRphyRpdDevSacCapEntry 19 }

docsRphyRpdDevSacCapMinScanRepeatPeriod OBJECT-TYPE
    SYNTAX      Unsigned32
    MAX-ACCESS  read-only
    STATUS      current
    DESCRIPTION 
        "This attribute reports the minimum duration of
         the RepeatPeriod the SAC supports when it is 
         operating in Port Scanning Capture."
    ::= { docsRphyRpdDevSacCapEntry 20 }
    

-- ---------------------------------------------------------------------
-- RPD Candidate Backup Cores Table
-- ---------------------------------------------------------------------

docsRphyRpdDevCandidateBackupCoresTable OBJECT-TYPE
    SYNTAX      SEQUENCE OF DocsRphyRpdDevCandidateBackupCoresEntry
    MAX-ACCESS  not-accessible
    STATUS      current
    DESCRIPTION
        "This table provides a list of IP addresses of those CCAP Cores 
         which are to be contacted by the RPD as potential backups to 
         the selected Core."
    ::= { docsRphyRpdDevMibObjects 31 }

docsRphyRpdDevCandidateBackupCoresEntry OBJECT-TYPE
    SYNTAX     DocsRphyRpdDevCandidateBackupCoresEntry
    MAX-ACCESS not-accessible
    STATUS     current
    DESCRIPTION
        "The conceptual row of docsRphyRpdDevCandidateBackupCoresTable."
    INDEX { docsRphyRpdDevInfoUniqueId, docsRphyRpdDevCoresConnectedIndex,
            docsRphyRpdDevCandidateBackupCoresBackupCoreIpAddrIndex}
    ::= { docsRphyRpdDevCandidateBackupCoresTable 1 }

DocsRphyRpdDevCandidateBackupCoresEntry ::= SEQUENCE
    {
    docsRphyRpdDevCandidateBackupCoresBackupCoreIpAddrIndex    Unsigned32,
    docsRphyRpdDevCandidateBackupCoresBackupCoreAddrType       InetAddressType,
    docsRphyRpdDevCandidateBackupCoresBackupCoreAddr           InetAddress
    }


docsRphyRpdDevCandidateBackupCoresBackupCoreIpAddrIndex OBJECT-TYPE
    SYNTAX      Unsigned32 (0..255)
    MAX-ACCESS  not-accessible
    STATUS      current
    DESCRIPTION 
        "This key attribute identifies a row in 
         CandidateBackupCores table."
    ::= { docsRphyRpdDevCandidateBackupCoresEntry 1}

docsRphyRpdDevCandidateBackupCoresBackupCoreAddrType OBJECT-TYPE
    SYNTAX     InetAddressType   
    MAX-ACCESS read-only
    STATUS     current
    DESCRIPTION
        "This attribute represents the IP address type of the 
         potential backup CCAP Core. This value is of type 
         InetAddressType, which is defined by [RFC 4001]."
       ::= { docsRphyRpdDevCandidateBackupCoresEntry 2}

docsRphyRpdDevCandidateBackupCoresBackupCoreAddr OBJECT-TYPE
    SYNTAX     InetAddress (SIZE(4|16))
    MAX-ACCESS read-only
    STATUS     current
    DESCRIPTION
        "This attribute reports the IPv4 or IPv6 address of
         the CCAP Core that the RPD needs to contact as a 
         potential backup."
       ::= { docsRphyRpdDevCandidateBackupCoresEntry 3}

-- ---------------------------------------------------------------------
-- RPD Shelf Info Table
-- ---------------------------------------------------------------------

docsRphyRpdDevShelfInfoTable OBJECT-TYPE
    SYNTAX      SEQUENCE OF DocsRphyRpdDevShelfInfoEntry
    MAX-ACCESS  not-accessible
    STATUS      current
    DESCRIPTION
        "This table identifies RPD shelves and each RPD in the shelf. 
         The CCAP Core MUST create an RpdShelfInfo entry for each RPD 
         reporting a chassis entity with EntityIndex equal one and 
         Class equal 'chassis'."
    ::= { docsRphyRpdDevMibObjects 32 }

docsRphyRpdDevShelfInfoEntry OBJECT-TYPE
    SYNTAX     DocsRphyRpdDevShelfInfoEntry
    MAX-ACCESS not-accessible
    STATUS     current
    DESCRIPTION
        "The conceptual row of docsRphyRpdDevShelfInfoTable."
    INDEX { docsRphyRpdDevShelfInfoShelfId,
            docsRphyRpdDevInfoUniqueId}
    ::= { docsRphyRpdDevShelfInfoTable 1 }

DocsRphyRpdDevShelfInfoEntry ::= SEQUENCE
    {
    docsRphyRpdDevShelfInfoShelfId                     SnmpAdminString,
    docsRphyRpdDevShelfInfoRpdSlot                     Unsigned32
    }

docsRphyRpdDevShelfInfoShelfId OBJECT-TYPE
    SYNTAX      SnmpAdminString (SIZE (0..64))
    MAX-ACCESS  not-accessible
    STATUS      current
    DESCRIPTION 
        "This attribute specifies the SerialNum of the RPD Entity
         with EntityIndex equal one and class equal 'chassis'. 
         All RPDs reporting the same SerialNum for the chassis 
         entity are in the same shelf."
    ::= { docsRphyRpdDevShelfInfoEntry 1 }

docsRphyRpdDevShelfInfoRpdSlot OBJECT-TYPE
    SYNTAX      Unsigned32
    MAX-ACCESS  read-only
    STATUS      current
    DESCRIPTION 
        "This attribute reports the slot number or, 
         for RPDs not in a slot, the location number for
         an RPD in a shelf. If the main RPD module is in a container
         (i.e., has ContainedIn set to an EntityIndex of class equal 
         'container') in the shelf chassis, this attribute equals the
         ParentRelPos for the container for the main RPD module. 
         If the main RPD module is contained directly in the shelf chassis 
         (i.e., has ContainedIn for the main module Entity with value one), 
         this equals the ParentRelPos of the main RPD module Entity. 
         RPDs that are not field replaceable may not be in slots and 
         would instead be directly contained in the chassis."
    ::= { docsRphyRpdDevShelfInfoEntry 2 }

-- ---------------------------------------------------------------------
-- RPD PMAP Capabilities Table
-- ---------------------------------------------------------------------

docsRphyRpdDevPmapCapTable OBJECT-TYPE
    SYNTAX      SEQUENCE OF DocsRphyRpdDevPmapCapEntry
    MAX-ACCESS  not-accessible
    STATUS      current
    DESCRIPTION
        "The PMAP capabilities table allows the RPD to inform the CCAP Core
         about its capabilities related to OFDMA probes and P-MAP messages.
         The PmapCapabilities TLV Type is 50.54.3."
    REFERENCE
        "Information Model Mapping: CM-SP-R-OSSI 
         OfdmaCfgCapabilities"
    ::= { docsRphyRpdDevMibObjects 33 }

docsRphyRpdDevPmapCapEntry OBJECT-TYPE
    SYNTAX     DocsRphyRpdDevPmapCapEntry
    MAX-ACCESS not-accessible
    STATUS     current
    DESCRIPTION
        "The conceptual row of docsRphyRpdDevPmapCapTable."
    INDEX { docsRphyRpdDevInfoUniqueId}
    ::= { docsRphyRpdDevPmapCapTable 1 }

DocsRphyRpdDevPmapCapEntry ::= SEQUENCE
    {
    docsRphyRpdDevPmapCapMaxNumPmaples          Unsigned32,
    docsRphyRpdDevPmapCapProbePowerControl      TruthValue,
    docsRphyRpdDevPmapCapSupportedPilotPatterns BITS
    }

docsRphyRpdDevPmapCapMaxNumPmaples OBJECT-TYPE
    SYNTAX      Unsigned32 (32..128)
    MAX-ACCESS  read-only
    STATUS      current
    DESCRIPTION 
        "This attribute reports the maximum number of P-IEs
         per P-MAP supported by the RPD."
    REFERENCE
        "Information Model Mapping: CM-SP-R-OSSI 
         OfdmaCfgCapabilities::MaxNumPmapIes"
    ::= { docsRphyRpdDevPmapCapEntry 1}

docsRphyRpdDevPmapCapProbePowerControl OBJECT-TYPE
    SYNTAX      TruthValue
    MAX-ACCESS  read-only
    STATUS      current
    DESCRIPTION 
        "This attribute reports whether the RPD supports 
         Power Control (P) bit in P-MAP messages.
         The RPD reports a value of false(0) if the RPD does
         not support P-bit in P-MAP messages.
         The RPD reports a value of true(1) if the RPD 
         supports P-bit in P-MAP messages."
REFERENCE
        "Information Model Mapping: CM-SP-R-OSSI 
         OfdmaCfgCapabilities::ProbePowerControl"
    ::= { docsRphyRpdDevPmapCapEntry 2 }

docsRphyRpdDevPmapCapSupportedPilotPatterns OBJECT-TYPE
    SYNTAX      BITS {
                     pilotPatternNum5(0),
                     pilotPatternNum6(1),
                     pilotPatternNum7(2),
                     pilotPatternNum12(3),
                     pilotPatternNum13(4),
                     pilotPatternNum14(5)

                     }
    MAX-ACCESS  read-only
    STATUS      current
    DESCRIPTION 
        "This attribute reports the set of supported OFDMA
         optional pilot patterns for an RPD. The RPD reports
         '0' for the bit corresponding to a pilot pattern not
         supported by the RPD. The RPD reports '1' for the bit
         corresponding to a pilot pattern supported by the RPD."
    REFERENCE
        "Information Model Mapping: CM-SP-R-OSSI 
         OfdmaCfgCapabilities::SupportedPilotPatterns"
    ::= { docsRphyRpdDevPmapCapEntry 3 }
-- ---------------------------------------------------------------------
-- RPD Echo Canceller Capabilities Table
-- ---------------------------------------------------------------------

docsRphyRpdDevEchoCanCapTable OBJECT-TYPE
    SYNTAX      SEQUENCE OF DocsRphyRpdDevEchoCanCapEntry
    MAX-ACCESS  not-accessible
    STATUS      current
    DESCRIPTION
        "The Echo Canceller Capabilities table reports RPD support for various
         FDX Node Echo Canceller functions.

         The FdxCapabilities TLV Type is 50.57.4"
    ::= { docsRphyRpdDevMibObjects 34 }

docsRphyRpdDevEchoCanCapEntry OBJECT-TYPE
    SYNTAX     DocsRphyRpdDevEchoCanCapEntry
    MAX-ACCESS not-accessible
    STATUS     current
    DESCRIPTION
        "The conceptual row of docsRphyRpdDevEchoCanCapTable."
    INDEX { docsRphyRpdDevInfoUniqueId}
    ::= { docsRphyRpdDevEchoCanCapTable 1 }

DocsRphyRpdDevEchoCanCapEntry ::= SEQUENCE
    {
    docsRphyRpdDevEchoCanCapEctMethod                 INTEGER,
    docsRphyRpdDevEchoCanCapMaxEctChannels            Unsigned32,
    docsRphyRpdDevEchoCanCapMinEctPeriod              Unsigned32,
    docsRphyRpdDevEchoCanCapErdDuration               Unsigned32
    }

docsRphyRpdDevEchoCanCapEctMethod OBJECT-TYPE
    SYNTAX      INTEGER {
                         other(0),       
                         autonomous(1),
                         scheduledChannel(2),
                         scheduledSubband(3)
                        }
    MAX-ACCESS  read-only
    STATUS      current
    DESCRIPTION
        "This attribute reports which EC training method is
         supported by the RPD.

         other:  The EC training method supported by the RPD is not covered by this specification.
         autonomous:  The RPD supports Autonomous EC Training.
         scheduledChannel:  The RPD supports Scheduled Channel EC Training.
         scheduledSubband: The RPD supports Scheduled Sub-band EC Training."
    REFERENCE
        "Information Model Mapping: CM-SP-R-OSSI 
         EchoCancellerCapabilities::EctMethod"
    ::= { docsRphyRpdDevEchoCanCapEntry 1 }

docsRphyRpdDevEchoCanCapMaxEctChannels OBJECT-TYPE
    SYNTAX      Unsigned32 (0..255)
    MAX-ACCESS  read-only
    STATUS      current
    DESCRIPTION 
        "This attribute reports the maximum number of FDX 
         OFDMA channels on which the RPD can train simultaneously."
    REFERENCE
        "Information Model Mapping: CM-SP-R-OSSI 
         EchoCancellerCapabilities::MaxEctChannels"
    ::= { docsRphyRpdDevEchoCanCapEntry 2 }

docsRphyRpdDevEchoCanCapMinEctPeriod OBJECT-TYPE
    SYNTAX      Unsigned32
    UNITS       "milliseconds"
    MAX-ACCESS  read-only
    STATUS      current
    DESCRIPTION 
        "This attribute reports the minimum EC training period the
         RPD can accept and still process EC Training Opportunities.
         A value of zero means that the RPD can accept back-to-back
         EC Training Opportunities. A value of 0xFFFF means that the
         RPD does not require periodic EC Training Opportunities."
    REFERENCE
        "Information Model Mapping: CM-SP-R-OSSI 
         EchoCancellerCapabilities::MinEctPeriod"
    ::= { docsRphyRpdDevEchoCanCapEntry 3 }


 docsRphyRpdDevEchoCanCapErdDuration  OBJECT-TYPE
    SYNTAX      Unsigned32  (0..65535)
    UNITS       "microseconds"
    MAX-ACCESS  read-only
    STATUS      current
    DESCRIPTION 
        "This attribute reports the RPD EC Re-convergence Delay (ERD). ERD
         is intended to permit the RPD ample time to determine EC
         coefficients and load them into the EC circuitry after reception
         of the ECTO."
    REFERENCE
        "Information Model Mapping: CM-SP-R-OSSI 
         EchoCancellerCapabilities::ErdDuration"
    ::= { docsRphyRpdDevEchoCanCapEntry 4 }

-- ---------------------------------------------------------------------
-- RPD RF Module Capabilities Table
-- ---------------------------------------------------------------------

docsRphyRpdDevRfmCapTable OBJECT-TYPE
    SYNTAX      SEQUENCE OF DocsRphyRpdDevRfmCapEntry
    MAX-ACCESS  not-accessible
    STATUS      current
    DESCRIPTION
        "The RFM capabilities table allows an RPD designed to operate
         in an optical node to communicate its capabilities for configuration
         and status reporting for features and functions of the RF Module (RFM).

          The RfmCapabilities TLV Type is 50.60."
    ::= { docsRphyRpdDevMibObjects 35 }

docsRphyRpdDevRfmCapEntry OBJECT-TYPE
    SYNTAX     DocsRphyRpdDevRfmCapEntry
    MAX-ACCESS not-accessible
    STATUS     current
    DESCRIPTION
        "The conceptual row of docsRphyRpdDevRfmCapTable."
    INDEX { docsRphyRpdDevInfoUniqueId}
    ::= { docsRphyRpdDevRfmCapTable 1 }

DocsRphyRpdDevRfmCapEntry ::= SEQUENCE
    {
    docsRphyRpdDevRfmCapSupportsRfmMgmt          TruthValue,
    docsRphyRpdDevRfmCapNumNodeRfPorts           Unsigned32,
    docsRphyRpdDevRfmCapSupportsDsCfgRfmGain     TruthValue,
    docsRphyRpdDevRfmCapMinDsCfgRfmGain          TenthdB, 
    docsRphyRpdDevRfmCapMaxDsCfgRfmGain          TenthdB,    
    docsRphyRpdDevRfmCapSupportsUsCfgRfmGain     TruthValue,
    docsRphyRpdDevRfmCapMinUsCfgRfmGain          TenthdB,       
    docsRphyRpdDevRfmCapMaxUsCfgRfmGain          TenthdB,           
    docsRphyRpdDevRfmCapSupportsRfmDsTiltConfig  TruthValue,  
    docsRphyRpdDevRfmCapMinRfmDsTilt             TenthdB,         
    docsRphyRpdDevRfmCapMaxRfmDsTilt             TenthdB, 
    docsRphyRpdDevRfmCapMaxDsPowerGainFunctions  Unsigned32,
    docsRphyRpdDevRfmCapMaxUsPowerGainFunctions  Unsigned32,  
    docsRphyRpdDevRfmCapMaxDsTiltCtrlFunctions   Unsigned32,        
    docsRphyRpdDevRfmCapMinRfmDsFreq             Unsigned32,
    docsRphyRpdDevRfmCapMaxRfmDsFreq             Unsigned32
     }

docsRphyRpdDevRfmCapSupportsRfmMgmt  OBJECT-TYPE
    SYNTAX      TruthValue
    MAX-ACCESS  read-only
    STATUS      current
    DESCRIPTION 
        "This attribute reports whether the RPD supports 
         management of the RFM.

         The RPD reports a value of false(0) if it does not
         support RFM management.

         The RPD reports a value of true(1) if it 
         supports RFM management."
    ::= { docsRphyRpdDevRfmCapEntry 1 }

docsRphyRpdDevRfmCapNumNodeRfPorts OBJECT-TYPE
    SYNTAX      Unsigned32 (0..65535)
    MAX-ACCESS  read-only
    STATUS      current
    DESCRIPTION 
        "This attribute reports how many node RF 
         ports the RPD supports."
    ::= { docsRphyRpdDevRfmCapEntry 2 }

docsRphyRpdDevRfmCapSupportsDsCfgRfmGain  OBJECT-TYPE
    SYNTAX      TruthValue
    MAX-ACCESS  read-only
    STATUS      current
    DESCRIPTION 
        "This attribute reports whether the RPD supports
         configuration of the RFM downstream power gain via GCP.

         The RPD reports a value of false(0) if it does not support 
         GCP configuration of the DS RFM power gain.

         The RPD reports a value of true(1) if it supports GCP 
         configuration of the DS RFM power gain."
    ::= { docsRphyRpdDevRfmCapEntry 3 } 

docsRphyRpdDevRfmCapMinDsCfgRfmGain  OBJECT-TYPE
    SYNTAX      TenthdB (-32768..32767)
    UNITS       "dB"
    MAX-ACCESS  read-only
    STATUS      current
    DESCRIPTION 
        "This attribute reports the RPD's minimum supported 
         value of the RFM DS power gain configuration."
    ::= { docsRphyRpdDevRfmCapEntry 4 }

docsRphyRpdDevRfmCapMaxDsCfgRfmGain  OBJECT-TYPE
    SYNTAX      TenthdB (-32768..32767)
    UNITS       "dB"
    MAX-ACCESS  read-only
    STATUS      current
    DESCRIPTION 
        "This attribute reports the RPD's maximum supported 
         value of the RFM DS power gain configuration."
    ::= { docsRphyRpdDevRfmCapEntry 5 }

docsRphyRpdDevRfmCapSupportsUsCfgRfmGain  OBJECT-TYPE
    SYNTAX      TruthValue
    MAX-ACCESS  read-only
    STATUS      current
    DESCRIPTION 
        "This attribute reports whether the RPD supports 
         configuration of the RFM upstream power gain via GCP.

         The RPD reports a value of false(0) if it does not support
         GCP configuration of the US RFM gain.

         The RPD reports a value of true(1) if it supports GCP 
         configuration of the US RFM gain."
    ::= { docsRphyRpdDevRfmCapEntry 6 } 

docsRphyRpdDevRfmCapMinUsCfgRfmGain  OBJECT-TYPE
    SYNTAX      TenthdB (-32768..32767)
    UNITS       "dB"
    MAX-ACCESS  read-only
    STATUS      current
    DESCRIPTION 
        "This attribute reports the RPD's minimum supported 
         value of the RFM US power gain configuration."
    ::= { docsRphyRpdDevRfmCapEntry 7 }

docsRphyRpdDevRfmCapMaxUsCfgRfmGain   OBJECT-TYPE
    SYNTAX      TenthdB (-32768..32767)
    UNITS       "dB"
    MAX-ACCESS  read-only
    STATUS      current
    DESCRIPTION 
        "This attribute reports the RPD's maximum supported 
         value of the RFM US power gain configuration."
    ::= { docsRphyRpdDevRfmCapEntry 8 }

docsRphyRpdDevRfmCapSupportsRfmDsTiltConfig  OBJECT-TYPE
    SYNTAX      TruthValue
    MAX-ACCESS  read-only
    STATUS      current
    DESCRIPTION 
        "This attribute reports whether the RPD supports configuration
         of the RFM downstream tilt via GCP.

         The RPD reports a value of false(0) if it does not support 
         GCP configuration of the RFM DS tilt.

         The RPD reports a value of true(1) if it supports GCP 
         configuration of the RFM DS tilt."
    ::= { docsRphyRpdDevRfmCapEntry 9 } 

  docsRphyRpdDevRfmCapMinRfmDsTilt  OBJECT-TYPE
    SYNTAX      TenthdB (-32768..32767)
    UNITS       "dB"
    MAX-ACCESS  read-only
    STATUS      current
    DESCRIPTION 
        "This attribute reports the RPD's minimum supported
         value of the RFM DS tilt configuration."
    ::= { docsRphyRpdDevRfmCapEntry 10 }

docsRphyRpdDevRfmCapMaxRfmDsTilt   OBJECT-TYPE
    SYNTAX      TenthdB (-32768..32767)
    UNITS       "dB"
    MAX-ACCESS  read-only
    STATUS      current
    DESCRIPTION 
        "This attribute reports the RPD's maximum supported
         value of the RFM DS tilt configuration."
    ::= { docsRphyRpdDevRfmCapEntry 11 }
 
docsRphyRpdDevRfmCapMaxDsPowerGainFunctions   OBJECT-TYPE
    SYNTAX      Unsigned32 (0..65535)
    MAX-ACCESS  read-only
    STATUS      current
    DESCRIPTION 
        "This attribute reports how many distinct DS power control
         functions (i.e., typically amplifiers) the RPD supports in the RFM."
    ::= { docsRphyRpdDevRfmCapEntry 12 }

docsRphyRpdDevRfmCapMaxUsPowerGainFunctions   OBJECT-TYPE
    SYNTAX      Unsigned32 (0..65535)
    MAX-ACCESS  read-only
    STATUS      current
    DESCRIPTION 
        "This attribute reports how many distinct US power control 
         functions (i.e., typically attenuators) the RPD supports in the RFM."
    ::= { docsRphyRpdDevRfmCapEntry 13 }

docsRphyRpdDevRfmCapMaxDsTiltCtrlFunctions   OBJECT-TYPE
    SYNTAX      Unsigned32 (0..65535)
    MAX-ACCESS  read-only
    STATUS      current
    DESCRIPTION 
        "This attribute reports how many distinct DS tilt control
         functions the RPD supports in the RFM."
    ::= { docsRphyRpdDevRfmCapEntry 14 }

 docsRphyRpdDevRfmCapMinRfmDsFreq   OBJECT-TYPE
    SYNTAX      Unsigned32 (0..4294967295)
    UNITS       "Hz"
    MAX-ACCESS  read-only
    STATUS      current
    DESCRIPTION 
        "This attribute reports the RPD's minimum DS frequency supported
         by the RFM."
    ::= { docsRphyRpdDevRfmCapEntry 15 }

 docsRphyRpdDevRfmCapMaxRfmDsFreq    OBJECT-TYPE
    SYNTAX      Unsigned32 (0..4294967295)
    UNITS       "Hz"
    MAX-ACCESS  read-only
    STATUS      current
    DESCRIPTION 
        "This attribute reports the RPD's maximum DS frequency
         supported by the RFM."
    ::= { docsRphyRpdDevRfmCapEntry 16 }

-- ---------------------------------------------------------------------
-- RPD Node RF Port Capabilities Table
-- ---------------------------------------------------------------------

docsRphyRpdDevNodeRfPortCapTable OBJECT-TYPE
    SYNTAX      SEQUENCE OF DocsRphyRpdDevNodeRfPortCapEntry
    MAX-ACCESS  not-accessible
    STATUS      current
    DESCRIPTION
        "The Node RF Port Capabilities table reports the RPD configuration 
         capabilities of the RFM Node RF ports.
         The NodeRfPortCapabilities TLV Type is 50.60.17."
    REFERENCE 
        "Information Model Mapping: CM-SP-R-OSSI 
         NodeRfPortCapabilities"
    ::= { docsRphyRpdDevMibObjects 36 }

docsRphyRpdDevNodeRfPortCapEntry OBJECT-TYPE
    SYNTAX     DocsRphyRpdDevNodeRfPortCapEntry
    MAX-ACCESS not-accessible
    STATUS     current
    DESCRIPTION
        "The conceptual row of docsRphyRpdDevNodeRfPortCapTable."
    INDEX { docsRphyRpdDevInfoUniqueId, 
            docsRphyRpdDevNodeRfPortCapNodeRfPortIndex }
    ::= { docsRphyRpdDevNodeRfPortCapTable 1 }

DocsRphyRpdDevNodeRfPortCapEntry ::= SEQUENCE
    {
      docsRphyRpdDevNodeRfPortCapNodeRfPortIndex        Unsigned32,
      docsRphyRpdDevNodeRfPortCapNodeRfPortVendorDesc   SnmpAdminString,
      docsRphyRpdDevNodeRfPortCapRpdUsRfPortMap         Unsigned32,
      docsRphyRpdDevNodeRfPortCapRpdDsRfPortMap         Unsigned32,
      docsRphyRpdDevNodeRfPortCapRfmUsGainCtrlIndex     Unsigned32,
      docsRphyRpdDevNodeRfPortCapRfmDsGainCtrlIndex     Unsigned32,
      docsRphyRpdDevNodeRfPortCapRfmDsTiltCtrlIndex     Unsigned32,
      docsRphyRpdDevNodeRfPortCapNodeRfPortOpLabel      SnmpAdminString
    }

 docsRphyRpdDevNodeRfPortCapNodeRfPortIndex OBJECT-TYPE
    SYNTAX      Unsigned32 (0..255)
    MAX-ACCESS  not-accessible
    STATUS      current
    DESCRIPTION 
        "This attribute is used to identify a node RF port in the RFM. 
         For the purpose of GCP management node RF ports are numbered
         from 0 to N-1, where N is the number reported by the RPD 
         through NumNodePorts attribute."
    REFERENCE 
        "Information Model Mapping: CM-SP-R-OSSI 
         NodeRfPortCapabilities::NodeRfPortIndex"
    ::= { docsRphyRpdDevNodeRfPortCapEntry 1}

docsRphyRpdDevNodeRfPortCapNodeRfPortVendorDesc OBJECT-TYPE
    SYNTAX      SnmpAdminString   (SIZE (0..64))
    MAX-ACCESS  read-only
    STATUS      current
    DESCRIPTION 
        "This attribute reports the RPD's human readable 
         description of the node RF Port."
    REFERENCE 
        "Information Model Mapping: CM-SP-R-OSSI 
         NodeRfPortCapabilities::NodeRfPortVendorDesc"
    ::= { docsRphyRpdDevNodeRfPortCapEntry 2}

 docsRphyRpdDevNodeRfPortCapRpdUsRfPortMap OBJECT-TYPE
    SYNTAX      Unsigned32 (0..255)
    MAX-ACCESS  read-only
    STATUS      current
    DESCRIPTION 
        "This attribute reports the index association of the node RF 
         port to the US RF Port in the RPD Module. If an RPD supports 
         configurable mapping between node RF ports and the US RF 
         port then this attribute reports the current mapping.
         An RPN with only downstream Partial Spectrum capabilities
         reports its upstream  Full Spectrum RF port capabilities
         with values that match those reported in the
         NodePortMapUsCapabilities object for the single upstream
         Partial Spectrum RF port index matching the NodeRfPortIndex
         key attribute. A Partial Spectrum-capable RPN omits reporting
         upstream Partial Spectrum RF ports in this attribute."
    REFERENCE 
        "Information Model Mapping: CM-SP-R-OSSI 
         NodeRfPortCapabilities::RpdUsRfPortMap"
     ::= { docsRphyRpdDevNodeRfPortCapEntry 3}

docsRphyRpdDevNodeRfPortCapRpdDsRfPortMap OBJECT-TYPE
    SYNTAX      Unsigned32 (0..255)
    MAX-ACCESS  read-only
    STATUS      current
    DESCRIPTION 
        "This attribute reports the index association of the node RF 
         port to the DS RF Port in the RPD Module. If an RPD supports
         configurable mapping between node RF ports and the DS RF
         ports then this attribute reports the current mapping.
         An RPN with only upstream Partial Spectrum capabilities
         reports its downstream Full Spectrum RF port capabilities
         with values that match those reported in the
         NodePortMapDsCapabilities object for the single downstream
         Partial Spectrum RF port index matching the NodeRfPortIndex
         key attribute. A Partial Spectrum-capable RPN omits reporting
         downstream Partial Spectrum RF ports in this attribute."
    REFERENCE 
        "Information Model Mapping: CM-SP-R-OSSI 
         NodeRfPortCapabilities::RpdDsRfPortMap"
    ::= { docsRphyRpdDevNodeRfPortCapEntry 4}

docsRphyRpdDevNodeRfPortCapRfmUsGainCtrlIndex OBJECT-TYPE
    SYNTAX      Unsigned32 (0..255)
    MAX-ACCESS  read-only
    STATUS      current
    DESCRIPTION 
        "This attribute reports the RPD's index association of the 
         node RF port with US gain control function in the RFM.
         An RPN with only downstream Partial Spectrum capabilities
         reports its upstream Full Spectrum RF port capabilities
         with values that match those reported in the
         NodePortMapUsCapabilities object for the single upstream
         Partial Spectrum RF port index matching the NodeRfPortIndex
         key attribute. A Partial Spectrum-capable RPN omits reporting
         upstream Partial Spectrum RF ports in this attribute."
    REFERENCE 
        "Information Model Mapping: CM-SP-R-OSSI 
         NodeRfPortCapabilities::RfmUsGainCtrlIndex"
    ::= { docsRphyRpdDevNodeRfPortCapEntry 5}

docsRphyRpdDevNodeRfPortCapRfmDsGainCtrlIndex OBJECT-TYPE
    SYNTAX      Unsigned32 (0..255)
    MAX-ACCESS  read-only
    STATUS      current
    DESCRIPTION 
        "This attribute reports the RPD's index association of the
         node RF port with DS gain control function in the RFM.
         An RPN with only upstream Partial Spectrum capabilities
         reports its downstream Full Spectrum RF port capabilities
         with values that match those reported in the 
         NodePortMapDsCapabilities object for the single downstream
         Partial Spectrum RF port index matching the NodeRfPortIndex
         key attribute. A Partial Spectrum-capable RPN omits reporting
         downstream Partial Spectrum RF ports in this attribute."
    REFERENCE 
        "Information Model Mapping: CM-SP-R-OSSI 
         NodeRfPortCapabilities::RfmDsGainCtrlIndex"
    ::= { docsRphyRpdDevNodeRfPortCapEntry 6}

docsRphyRpdDevNodeRfPortCapRfmDsTiltCtrlIndex   OBJECT-TYPE
    SYNTAX      Unsigned32 (0..255)
    MAX-ACCESS  read-only
    STATUS      current
    DESCRIPTION 
        "This attribute reports the RPD's index association of the 
         node RF port with DS tilt control function in the RFM."
    REFERENCE 
        "Information Model Mapping: CM-SP-R-OSSI 
         NodeRfPortCapabilities::RfmDsTiltCtrlIndex"
    ::= { docsRphyRpdDevNodeRfPortCapEntry 7}

docsRphyRpdDevNodeRfPortCapNodeRfPortOpLabel  OBJECT-TYPE
    SYNTAX      SnmpAdminString   (SIZE (0..64))
    MAX-ACCESS  read-only
    STATUS      current
    DESCRIPTION 
        "This attribute reports the RPD's operator label of the node 
         RF Port. The default value is the zero-length string."
    REFERENCE 
        "Information Model Mapping: CM-SP-R-OSSI 
         NodeRfPortCapabilities::NodeRfPortOperatorLabel"
    ::= { docsRphyRpdDevNodeRfPortCapEntry 8}

-- ---------------------------------------------------------------------
-- RPD Reset History Table
-- ---------------------------------------------------------------------

docsRphyRpdDevResetHistoryTable OBJECT-TYPE
    SYNTAX      SEQUENCE OF DocsRphyRpdDevResetHistoryEntry
    MAX-ACCESS  not-accessible
    STATUS      current
    DESCRIPTION
        "This table provides a record of the occurrences of a reset
         of an RPD. The RPD can reset for many reasons, including 
         loss of Principal Core, loss of IP connection, power failure,
         hardware or software failure, or reset command from CCAP Core
         or CLI. This table provides details of the conditions that caused
         the RPD to reset to assist operators with understanding why a 
         service interruption occurred. It also provides details on how 
         much time it took for the RPD to boot its software stack and 
         to become operational with the Principal Core.
         The ResetHistory TLV type is 100.31."
    REFERENCE 
        "Information Model Mapping: CM-SP-R-OSSI 
         ResetHistory"
    ::= { docsRphyRpdDevMibObjects 37 }

docsRphyRpdDevResetHistoryEntry OBJECT-TYPE
    SYNTAX     DocsRphyRpdDevResetHistoryEntry
    MAX-ACCESS not-accessible
    STATUS     current
    DESCRIPTION
        "The conceptual row of docsRphyRpdDevResetHistoryTable."
    INDEX { docsRphyRpdDevInfoUniqueId, 
            docsRphyRpdDevResetHistoryIndex }
    ::= { docsRphyRpdDevResetHistoryTable 1 }

DocsRphyRpdDevResetHistoryEntry ::= SEQUENCE
    {
      docsRphyRpdDevResetHistoryIndex                 Unsigned32,
      docsRphyRpdDevResetHistoryResetTimestamp        DateAndTime,
      docsRphyRpdDevResetHistoryType                  INTEGER,
      docsRphyRpdDevResetHistoryReason                SnmpAdminString,
      docsRphyRpdDevResetHistoryEventIdRef            Unsigned32,
      docsRphyRpdDevResetHistoryEventDescription      SnmpAdminString,
      docsRphyRpdDevResetHistoryRecoveryTime          Unsigned32,
      docsRphyRpdDevResetHistoryPrincipalOpTimestamp  DateAndTime
    }
    
docsRphyRpdDevResetHistoryIndex OBJECT-TYPE
    SYNTAX      Unsigned32 (0..65535)
    MAX-ACCESS  not-accessible
    STATUS      current
    DESCRIPTION 
        "This attribute is a key and provides an index into the table. 
         Indexes are consecutively ordered from 0..N-1 where N is the
         maximum number of reset history events supported by an RPD 
         as reported by the ResetHistorySize attribute of the 
         ResetCapabilities object. This attribute corresponds to the
         order in which reset events occurred. The most recent reset 
         event index is has a value of zero."
    REFERENCE 
        "Information Model Mapping: CM-SP-R-OSSI 
         ResetHistory::Index"
    ::= { docsRphyRpdDevResetHistoryEntry 1}
    
docsRphyRpdDevResetHistoryResetTimestamp OBJECT-TYPE
    SYNTAX      DateAndTime
    MAX-ACCESS  read-only
    STATUS      current
    DESCRIPTION 
        "This attribute provides the time at which the reset occurred. 
         If the RPD does not know what time the RPD reset occurred,
         the RPD MAY report a value of midnight, Jan 1, 1970 UTC
         in this attribute."
    REFERENCE 
        "Information Model Mapping: CM-SP-R-OSSI 
         ResetHistory::ResetTimestamp"
    ::= { docsRphyRpdDevResetHistoryEntry 2}
    
docsRphyRpdDevResetHistoryType OBJECT-TYPE
    SYNTAX      INTEGER {
                         softReset(1),       
                         hardReset(2),
                         nvReset(3),
                         factoryReset(4)
                        }
    MAX-ACCESS  read-only
    STATUS      current
    DESCRIPTION
        "This attribute identifies the type of reset that 
        the RPD is recording. The possible values match those
        of the Type TLV (TLV 40.1.1, sub-TLV of ResetCtrl) 
        and values are as follows:  
        softReset -  The RPD performed a softReset. 
        hardReset -  The RPD performed a power-on reset or equivalent reset. 
        nvReset   -  The RPD cleared most non-volatile configuration and
                     performed a hard reset. 
        factoryReset -  The RPD set all settings back to original factory 
                     settings and performed a hard reset."
    REFERENCE 
        "Information Model Mapping: CM-SP-R-OSSI 
         ResetHistory::Type"
    ::= { docsRphyRpdDevResetHistoryEntry 3 }
    
docsRphyRpdDevResetHistoryReason OBJECT-TYPE
    SYNTAX      SnmpAdminString (SIZE(1..255))
    MAX-ACCESS  read-only 
    STATUS      current 
    DESCRIPTION 
        "This attribute provides a vendor-specific string with a
         detailed explanation of why the RPD was reset. Vendors are 
         expected to add additional details, including diagnostic 
         information, whether this was a normal hard reset vs. a 
         vendor-specific type of hard reset, the RPD was disconnected
         from the node, etc."
    REFERENCE 
        "Information Model Mapping: CM-SP-R-OSSI 
         ResetHistory::Reason"
    ::= { docsRphyRpdDevResetHistoryEntry 4 }
    
docsRphyRpdDevResetHistoryEventIdRef OBJECT-TYPE
    SYNTAX       Unsigned32  (0..4294967295)
    MAX-ACCESS   read-only
    STATUS       current
    DESCRIPTION
        "If the reset was related to an event that was captured
         in a standardized DOCSIS event, this attribute provides
         the event ID of the corresponding event. If the RPD does
         not generate a DOCSIS event corresponding to the reset 
         occurrence, this attribute will have a value of 0."
    REFERENCE 
        "Information Model Mapping: CM-SP-R-OSSI 
         ResetHistory::EventIdRef"
    ::= {  docsRphyRpdDevResetHistoryEntry 5 }
    
docsRphyRpdDevResetHistoryEventDescription OBJECT-TYPE
    SYNTAX      SnmpAdminString
    MAX-ACCESS  read-only 
    STATUS      current 
    DESCRIPTION 
        "If the reset was related to an event that was captured
         in a standardized DOCSIS event, this attribute provides
         the standardized description of the corresponding event.
         If the reset does not have a corresponding event, 
         this attribute's value will be null."
    REFERENCE 
        "Information Model Mapping: CM-SP-R-OSSI 
         ResetHistory::EventDescription"
    ::= { docsRphyRpdDevResetHistoryEntry 6 }

docsRphyRpdDevResetHistoryRecoveryTime OBJECT-TYPE
    SYNTAX       Unsigned32  (0..4294967295)
    UNITS        "Seconds"
    MAX-ACCESS   read-only
    STATUS       current
    DESCRIPTION
        "This attribute provides the number of seconds that have
         elapsed between the time the reset event started and the 
         completion of the local RPD initialization stage. The 
         calculation of the number of seconds in this period is 
         vendor specific.
         
         The RPD might not always be able to record the timestamp
         of the most recent reset event. In addition, the RPD might
         not be able to determine the time of the completion of 
         'the local RPD init stage'. For example, after a reset event
         the RPD could reset again before being able to obtain the 
         current time from ToD.
         
         In such cases in which the RPD cannot determine the length
         of the RecoveryTime, the RPD MAY report a value of 0 (zero)."
    REFERENCE 
        "Information Model Mapping: CM-SP-R-OSSI 
         ResetHistory::RecoveryTime"
    ::= {  docsRphyRpdDevResetHistoryEntry 7 }
    
docsRphyRpdDevResetHistoryPrincipalOpTimestamp OBJECT-TYPE
    SYNTAX      DateAndTime
    MAX-ACCESS  read-only
    STATUS      current
    DESCRIPTION 
        "This attribute provides the time at which the RPD was moved
         to operational by the Principal Core. 

         If the RPD is unable to acquire the time of day by the  time 
         the RPD is moved to operational by the Principal Core, the 
         RPD MUST provide the date and time when the RPD was moved to
         operational. If the RPD is not moved to operational by the 
         Principal Core before another reset event, the RPD MAY set 
         the value of this attribute to midnight, Jan 1, 1970 UTC."
    REFERENCE 
        "Information Model Mapping: CM-SP-R-OSSI 
         ResetHistory::PrincipalOperationalTimestamp"
    ::= { docsRphyRpdDevResetHistoryEntry 8} 

-- ---------------------------------------------------------------------
-- RPD Channel Broadcast Group Status Table
-- ---------------------------------------------------------------------

docsRphyRpdDevChanBcastGroupStatusTable OBJECT-TYPE
    SYNTAX      SEQUENCE OF DocsRphyRpdDevChanBcastGroupStatusEntry
    MAX-ACCESS  not-accessible
    STATUS      current
    DESCRIPTION
        "This table indicates whether a downstream SC-QAM channel on
         an RPD is part of a BCG. Downstream SC-QAM channels on same
         RPD with the same channel selector channel index that have 
         the BcastChanGroup (TLV 62.17) attribute set to 'True' are 
         in the same BCG."
    REFERENCE 
        "Information Model Mapping: CM-SP-R-OSSI 
         ChanBcastGroupStatus"
    ::= { docsRphyRpdDevMibObjects 38 }

docsRphyRpdDevChanBcastGroupStatusEntry OBJECT-TYPE
    SYNTAX     DocsRphyRpdDevChanBcastGroupStatusEntry
    MAX-ACCESS not-accessible
    STATUS     current
    DESCRIPTION
        "The conceptual row of docsRphyRpdDevChanBcastGroupStatusTable."
    INDEX { docsRphyRpdDevInfoUniqueId, 
            docsRphyRpdDevChanBcastGroupStatusRfPortIndex,
            docsRphyRpdDevChanBcastGroupStatusScQamIndex}
    ::= { docsRphyRpdDevChanBcastGroupStatusTable 1 }

DocsRphyRpdDevChanBcastGroupStatusEntry ::= SEQUENCE
    {
      docsRphyRpdDevChanBcastGroupStatusRfPortIndex    Unsigned32,
      docsRphyRpdDevChanBcastGroupStatusScQamIndex     Unsigned32,
      docsRphyRpdDevChanBcastGroupStatusGroupMember    TruthValue
    } 

docsRphyRpdDevChanBcastGroupStatusRfPortIndex OBJECT-TYPE
    SYNTAX      Unsigned32 (0..255) 
    MAX-ACCESS  not-accessible
    STATUS      current
    DESCRIPTION 
        "This key attribute is the RF port number from the 
         channel selector for this DS SC-QAM channel. 
         This is part of a channel selector. A Partial
         Spectrum-capable RPN reports this attribute as
         an assigned Partial Spectrum RF port index."
    REFERENCE 
        "Information Model Mapping: CM-SP-R-OSSI 
         ChanBcastGroupStatus::RfPortIndex"
    ::= { docsRphyRpdDevChanBcastGroupStatusEntry 1 } 

docsRphyRpdDevChanBcastGroupStatusScQamIndex OBJECT-TYPE
    SYNTAX      Unsigned32 (0..255) 
    MAX-ACCESS  not-accessible
    STATUS      current
    DESCRIPTION 
        "This key attribute is the channel index from the 
         channel selector for this DS SC-QAM channel.
         This is part of a channel selector."  
    REFERENCE 
        "Information Model Mapping: CM-SP-R-OSSI 
         ChanBcastGroupStatus::ScQamIndex"

    ::= { docsRphyRpdDevChanBcastGroupStatusEntry 2 }

docsRphyRpdDevChanBcastGroupStatusGroupMember OBJECT-TYPE
    SYNTAX      TruthValue 
    MAX-ACCESS  read-only
    STATUS      current
    DESCRIPTION 
        "This attribute indicates whether or not this RPD's
         DS SC-QAM channel is part of a BCG."
    REFERENCE 
        "Information Model Mapping: CM-SP-R-OSSI 
         ChanBcastGroupStatus::GroupMember"
    ::= { docsRphyRpdDevChanBcastGroupStatusEntry 3 }   

-- ---------------------------------------------------------------------
-- RPD Upstream Capabilities Table
-- ---------------------------------------------------------------------

docsRphyRpdDevUsCapTable OBJECT-TYPE
    SYNTAX      SEQUENCE OF DocsRphyRpdDevUsCapEntry
    MAX-ACCESS  not-accessible
    STATUS      current
    DESCRIPTION
        "The UsCapabilities table reports the RPD's upstream
         channel capabilities.
         The UsCapabilities TLV Type is 50.61."
    REFERENCE 
        "Information Model Mapping: CM-SP-R-OSSI 
         UsCapabilities"
    ::= { docsRphyRpdDevMibObjects 39 }

docsRphyRpdDevUsCapEntry OBJECT-TYPE
    SYNTAX     DocsRphyRpdDevUsCapEntry
    MAX-ACCESS not-accessible
    STATUS     current
    DESCRIPTION
        "The conceptual row of docsRphyRpdDevUsCapTable."
    INDEX { docsRphyRpdDevInfoUniqueId }
    ::= { docsRphyRpdDevUsCapTable 1 }

DocsRphyRpdDevUsCapEntry ::= SEQUENCE
    {
      docsRphyRpdDevUsCapMaxUsFrequency    Unsigned32,
      docsRphyRpdDevUsCapMinUsFrequency    Unsigned32,
      docsRphyRpdDevUsCapMaxUnicastSids    Unsigned32
    }     

docsRphyRpdDevUsCapMaxUsFrequency OBJECT-TYPE
    SYNTAX      Unsigned32
    MAX-ACCESS  read-only
    STATUS      current
    DESCRIPTION 
        "This attribute reports the maximum frequency of
         any upstream signal that the RPD supports on a US RF port.
         It defines the highest frequency of the encompassed spectrum
         of the highest frequency upstream channel or OOB signal."
    REFERENCE 
        "Information Model Mapping: CM-SP-R-OSSI 
         UsCapabilities::MaxUsFrequency"
    ::= { docsRphyRpdDevUsCapEntry 1 }
    
docsRphyRpdDevUsCapMinUsFrequency OBJECT-TYPE
    SYNTAX      Unsigned32
    MAX-ACCESS  read-only
    STATUS      current
    DESCRIPTION 
        "This attribute reports the minimum frequency of any upstream
         signal that the RPD supports on a US RF port. It defines the 
         lowest frequency of the encompassed spectrum of the lowest 
         frequency upstream channel or OOB signal."
    REFERENCE 
        "Information Model Mapping: CM-SP-R-OSSI 
         UsCapabilities::MinUsFrequency"
    ::= { docsRphyRpdDevUsCapEntry 2 }
    
docsRphyRpdDevUsCapMaxUnicastSids OBJECT-TYPE
    SYNTAX      Unsigned32 (0..65535)
    MAX-ACCESS  read-only
    STATUS      current
    DESCRIPTION
        "This attribute reports the maximum number of unicast SIDs
         concurrently supported by the RPD on any upstream channel."
    REFERENCE 
        "Information Model Mapping: CM-SP-R-OSSI 
         UsCapabilities::MaxUnicastSids"
    ::= { docsRphyRpdDevUsCapEntry 3 }
    
-- ---------------------------------------------------------------------
-- RPD Path MTU Discovery (Pmtud) Capabilities Table
-- ---------------------------------------------------------------------

docsRphyRpdDevPmtudCapTable OBJECT-TYPE
    SYNTAX      SEQUENCE OF DocsRphyRpdDevPmtudCapEntry
    MAX-ACCESS  not-accessible
    STATUS      current
    DESCRIPTION
        "The PmtudCapabilities table reports the RPD capabilities 
         for Path MTU Discovery support for control plane connections.
         The PmtudCapabilities TLV Type is 50.62."
    REFERENCE 
        "Information Model Mapping: CM-SP-R-OSSI 
         PmtudCapabilities"
    ::= { docsRphyRpdDevMibObjects 40 }

docsRphyRpdDevPmtudCapEntry OBJECT-TYPE
    SYNTAX     DocsRphyRpdDevPmtudCapEntry
    MAX-ACCESS not-accessible
    STATUS     current
    DESCRIPTION
        "The conceptual row of docsRphyRpdDevPmtudCapTable."
    INDEX { docsRphyRpdDevInfoUniqueId }
    ::= { docsRphyRpdDevPmtudCapTable 1 }

DocsRphyRpdDevPmtudCapEntry ::= SEQUENCE
    {
      docsRphyRpdDevPmtdudCapSupportsIcmpBasedPmtud             TruthValue,
      docsRphyRpdDevPmtdudCapSupportsPacketizationBasedPmtud    TruthValue 
    }

docsRphyRpdDevPmtdudCapSupportsIcmpBasedPmtud OBJECT-TYPE
    SYNTAX      TruthValue 
    MAX-ACCESS  read-only
    STATUS      current
    DESCRIPTION 
        "This attribute reports the RPD's support of PMTUD
         based on [RFC 1191] and [RFC 8201].
         The RPD reports a value of 'false' if it does not
         support PMTUD based on [RFC 1191] and [RFC 8201].
         The RPD reports a value of 'true' if it supports PMTUD
         based on [RFC 1191] and [RFC 8201]."
    REFERENCE 
        "Information Model Mapping: CM-SP-R-OSSI 
         PmtudCapabilities::SupportsIcmpBasedPmtud"
    ::= { docsRphyRpdDevPmtudCapEntry 1 } 

docsRphyRpdDevPmtdudCapSupportsPacketizationBasedPmtud OBJECT-TYPE
    SYNTAX      TruthValue 
    MAX-ACCESS  read-only
    STATUS      current
    DESCRIPTION 
        "This attribute reports the RPD's support of PMTUD
         based on [RFC 4821].
         The RPD reports a value of 'false' if it does not support
         PMTUD based on [RFC 4821].
         The RPD reports a value of 'true' if it supports PMTUD
         based on [RFC 4821]."
    REFERENCE 
        "Information Model Mapping: CM-SP-R-OSSI 
         PmtudCapabilities::SupportsPacketizationBasedPmtud"
    ::= { docsRphyRpdDevPmtudCapEntry 2 }  

-- ---------------------------------------------------------------------
-- RPD PNM Capabilities Table
-- ---------------------------------------------------------------------

docsRphyRpdDevPnmCapTable OBJECT-TYPE
    SYNTAX      SEQUENCE OF DocsRphyRpdDevPnmCapEntry
    MAX-ACCESS  not-accessible
    STATUS      current
    DESCRIPTION
        "The PnmCapabilities table reports the RPD's capabilities
         for PNM test functionality. An RPD that implements PNM 
         functions implements the DOCSIS PNM MIB module to 
         enable control and reporting of PNM functions 
         [DOCS-PNM-MIB].
         The PnmCapabilities TLV Type is 50.64."
    REFERENCE 
        "Information Model Mapping: CM-SP-R-OSSI 
         PnmCapabilities"
    ::= { docsRphyRpdDevMibObjects 41 }

docsRphyRpdDevPnmCapEntry OBJECT-TYPE
    SYNTAX     DocsRphyRpdDevPnmCapEntry
    MAX-ACCESS not-accessible
    STATUS     current
    DESCRIPTION
        "The conceptual row of docsRphyRpdDevPnmCapTable."
    INDEX { docsRphyRpdDevInfoUniqueId }
    ::= { docsRphyRpdDevPnmCapTable 1 }

DocsRphyRpdDevPnmCapEntry ::= SEQUENCE
    {
      docsRphyRpdDevPnmCapSupportedPnmTests     BITS
    }  

docsRphyRpdDevPnmCapSupportedPnmTests OBJECT-TYPE
    SYNTAX      BITS {
                      usCapActiveAndQuietProbes(0),
                      usRxMer(1),
                      usImpNoiseStatistics(2),
                      dsSymCap(3),
                      usHist(4)
                     }
    MAX-ACCESS  read-only
    STATUS      current
    DESCRIPTION 
        "The SupportedPnmTests attribute allows an RPD to
        communicate which PNM tests it supports. SupportedPnmTests
        is represented as a bitmask with each assigned bit representing
        an individual PNM test. The Upstream Triggered Spectrum Capture
        (UTSC) test is not represented in the bitmask since UTSC 
        capabilities are defined separately via SpectrumCaptureCapabilities.
        The RPD reports bit 0 as '1' if it supports Upstream 
        of Active and Quiet Probes test.
        The RPD reports bit 1 as '1' if it supports Upstream Receive MER test.
        The RPD reports bit 2 as '1' if it supports Upstream Impulse
        Noise Statistics test.
        The RPD reports bit 3 as '1' if it supports Downstream Symbol
        Capture test.
        The RPD reports bit 4 as '1' if it supports Upstream Histogram test.
        The RPD reports all other bits as '0'."
    REFERENCE 
        "Information Model Mapping: CM-SP-R-OSSI 
         PnmCapabilities::SupportedPnmTests"
    ::= { docsRphyRpdDevPnmCapEntry 1 } 

-- ---------------------------------------------------------------------
-- RPD Upstream Probe Capture (UPC) Capabilities Table
-- ---------------------------------------------------------------------

docsRphyRpdDevUpcCapTable OBJECT-TYPE
    SYNTAX      SEQUENCE OF DocsRphyRpdDevUpcCapEntry
    MAX-ACCESS  not-accessible
    STATUS      current
    DESCRIPTION
        "The UpcCapabilities table reports the RPD capabilities
         for Upstream Probe Capture PNM tests.
         The UpcCapabilities TLV Type is 50.64.2."
    REFERENCE 
        "Information Model Mapping: CM-SP-R-OSSI 
         UpcCapabilities"
    ::= { docsRphyRpdDevMibObjects 42 }

docsRphyRpdDevUpcCapEntry OBJECT-TYPE
    SYNTAX     DocsRphyRpdDevUpcCapEntry
    MAX-ACCESS not-accessible
    STATUS     current
    DESCRIPTION
        "The conceptual row of docsRphyRpdDevUpcCapTable."
    INDEX { docsRphyRpdDevInfoUniqueId }
    ::= { docsRphyRpdDevUpcCapTable 1 }

DocsRphyRpdDevUpcCapEntry ::= SEQUENCE
    {
      docsRphyRpdDevUpcCapMinNumSymbols25Khz            Unsigned32,
      docsRphyRpdDevUpcCapMaxNumSymbols25Khz            Unsigned32,
      docsRphyRpdDevUpcCapMinNumSymbols50Khz            Unsigned32,
      docsRphyRpdDevUpcCapMaxNumSymbols50Khz            Unsigned32,
      docsRphyRpdDevUpcCapSupportsStaggeredPies         TruthValue,
      docsRphyRpdDevUpcCapSupportsDedicatedPwUpcRxMer   TruthValue,
      docsRphyRpdDevUpcCapSupportsFreqDomainSamples     TruthValue
    } 

docsRphyRpdDevUpcCapMinNumSymbols25Khz OBJECT-TYPE
    SYNTAX      Unsigned32 (1..255) 
    MAX-ACCESS  read-only
    STATUS      current
    DESCRIPTION 
        "This attribute reports the minimum number of probe 
         symbols that can be captured by the RPD in one test 
         when an OFDMA channel is configured for 25 kHz 
         subcarrier spacing. It takes a value of 1..MaxNumPmapIes."
    REFERENCE 
        "Information Model Mapping: CM-SP-R-OSSI 
         UpcCapabilities::MinNumSymbols25Khz"
    ::= { docsRphyRpdDevUpcCapEntry 1 }

docsRphyRpdDevUpcCapMaxNumSymbols25Khz OBJECT-TYPE
    SYNTAX      Unsigned32 (1..255) 
    MAX-ACCESS  read-only
    STATUS      current
    DESCRIPTION 
        "This attribute reports the maximum number of probe 
         symbols that can be captured by the RPD in one test 
         when an OFDMA channel is configured for 25 kHz 
         subcarrier spacing. It takes a value of 
         MinNumSymbols25Khz..MaxNumPmapIes."
    REFERENCE 
        "Information Model Mapping: CM-SP-R-OSSI 
         UpcCapabilities::MaxNumSymbols25Khz"
    ::= { docsRphyRpdDevUpcCapEntry 2 }  
    
docsRphyRpdDevUpcCapMinNumSymbols50Khz OBJECT-TYPE
    SYNTAX      Unsigned32 (1..255) 
    MAX-ACCESS  read-only
    STATUS      current
    DESCRIPTION 
        "This attribute reports the minimum number of probe 
         symbols that can be captured by the RPD in one test 
         when an OFDMA channel is configured for 50 kHz 
         subcarrier spacing. It takes a value of 
         1..MaxNumPmapIes."
    REFERENCE 
        "Information Model Mapping: CM-SP-R-OSSI 
         UpcCapabilities::MinNumSymbols50Khz"
    ::= { docsRphyRpdDevUpcCapEntry 3 }

docsRphyRpdDevUpcCapMaxNumSymbols50Khz OBJECT-TYPE
    SYNTAX      Unsigned32 (1..255) 
    MAX-ACCESS  read-only
    STATUS      current
    DESCRIPTION 
        "This attribute reports the maximum number of probe 
         symbols that can be captured by the RPD in one test 
         when an OFDMA channel is configured for 50 kHz 
         subcarrier spacing. It takes a value of 
         MinNumSymbols50Khz..MaxNumPmapIes."
    REFERENCE 
        "Information Model Mapping: CM-SP-R-OSSI 
         UpcCapabilities::MaxNumSymbols50Khz"
    ::= { docsRphyRpdDevUpcCapEntry 4 } 

docsRphyRpdDevUpcCapSupportsStaggeredPies OBJECT-TYPE
    SYNTAX      TruthValue 
    MAX-ACCESS  read-only
    STATUS      current
    DESCRIPTION 
        "This attribute reports whether the RPD supports 
         UPC PNM test with staggered Probe Information Elements (PIE),
         i.e., the RPD supports the use of a P-IE that specifies a 
         staggered probe as the indicator for triggering the start of
         the capture and capturing consecutive symbols as defined by the 
         P-IE subject to the RPD capability of the maximum number of symbols.
         The RPD reports a value of 'false' if it does not support UPC 
         test with staggered PIEs.
         The RPD reports a value of 'true' if it supports UPC test with
         staggered PIEs."
    REFERENCE 
        "Information Model Mapping: CM-SP-R-OSSI 
         UpcCapabilities::SupportsStaggeredPies"
    ::= { docsRphyRpdDevUpcCapEntry 5 } 

docsRphyRpdDevUpcCapSupportsDedicatedPwUpcRxMer OBJECT-TYPE
    SYNTAX      TruthValue 
    MAX-ACCESS  read-only
    STATUS      current
    DESCRIPTION 
        "This attribute reports whether the RPD supports
        dedicated pseudowires for UPC and RxMER PNM tests.
        The RPD reports a value of 'false' if it does not support
        dedicated pseudowires for UPC and RxMER tests. 
        The RPD only supports a shared pseudowire for UPC and RxMER tests.
        The RPD reports a value of 'true' if it supports dedicated 
        pseudowires for UPC and RxMER tests."
    REFERENCE 
        "Information Model Mapping: CM-SP-R-OSSI 
         UpcCapabilities::SupportsDedicatedPwUpcRxMer"
    ::= { docsRphyRpdDevUpcCapEntry 6 }  

docsRphyRpdDevUpcCapSupportsFreqDomainSamples  OBJECT-TYPE
    SYNTAX      TruthValue 
    MAX-ACCESS  read-only
    STATUS      current
    DESCRIPTION 
        "This attribute reports whether the RPD supports UPC
         test with samples represented in frequency domain.
         The RPD reports a value of 'false' if it does not 
         support samples represented in frequency domain.
         The RPD reports a value of 'true' if it supports 
         samples represented in frequency domain."
    REFERENCE 
        "Information Model Mapping: CM-SP-R-OSSI 
         UpcCapabilities::SupportsFreqDomainSamples"
    ::= { docsRphyRpdDevUpcCapEntry 7 }      

-- ---------------------------------------------------------------------
-- RPD Initialization Capabilities Table
-- ---------------------------------------------------------------------

docsRphyRpdDevInitCapTable OBJECT-TYPE
    SYNTAX      SEQUENCE OF DocsRphyRpdDevInitCapEntry
    MAX-ACCESS  not-accessible
    STATUS      current
    DESCRIPTION
        "The InitCapabilities table reports the RPD 
        capabilities for initialization.
        The InitializationCapabilities TLV Type is 50.65."
    REFERENCE 
        "Information Model Mapping: CM-SP-R-OSSI 
         InitializationCapabilities"
    ::= { docsRphyRpdDevMibObjects 43 }

docsRphyRpdDevInitCapEntry OBJECT-TYPE
    SYNTAX     DocsRphyRpdDevInitCapEntry
    MAX-ACCESS not-accessible
    STATUS     current
    DESCRIPTION
        "The conceptual row of docsRphyRpdDevInitCapTable."
    INDEX { docsRphyRpdDevInfoUniqueId }
    ::= { docsRphyRpdDevInitCapTable 1 }

DocsRphyRpdDevInitCapEntry ::= SEQUENCE
    {
      docsRphyRpdDevInitCapPerCoreInitTimers            TruthValue,
      docsRphyRpdDevInitCapStagingConfigInitTimers      TruthValue
    } 

docsRphyRpdDevInitCapPerCoreInitTimers OBJECT-TYPE
    SYNTAX      TruthValue
    MAX-ACCESS  read-only
    STATUS      current
    DESCRIPTION 
        "This attribute reports whether the RPD supports
         per Core initialization timers.

         The RPD reports a value of false(0) if it does
         not support per Core initialization timers.
         
         The RPD reports a value of true(1) if it supports
         per Core initialization timers."
    REFERENCE 
        "Information Model Mapping: CM-SP-R-OSSI 
         InitializationCapabilities::PerCoreInitTimers"
    ::= { docsRphyRpdDevInitCapEntry 1 }
    
docsRphyRpdDevInitCapStagingConfigInitTimers OBJECT-TYPE
    SYNTAX      TruthValue
    MAX-ACCESS  read-only
    STATUS      current
    DESCRIPTION 
        "This attribute reports whether the RPD supports
         setting initialization timers during staging.

         The RPD reports a value of false(0) if it does
         not support setting of timers during staging.
         
         The RPD reports a value of true(1) if it 
         supports setting of timers during staging."
    REFERENCE 
        "Information Model Mapping: CM-SP-R-OSSI 
         InitializationCapabilities::StagingConfigurableInitTimers"
    ::= { docsRphyRpdDevInitCapEntry 2 }
    
-- ---------------------------------------------------------------------
-- RPD Upstream Power Capabilities Table
-- ---------------------------------------------------------------------

docsRphyRpdDevUsPowerCapTable OBJECT-TYPE
    SYNTAX      SEQUENCE OF DocsRphyRpdDevUsPowerCapEntry
    MAX-ACCESS  not-accessible
    STATUS      current
    DESCRIPTION
        "The UsPowerCapabilities table reports the RPD 
         capabilities related to upstream power management.
         The UsPowerCapabilities TLV Type is 50.49."
    REFERENCE 
        "Information Model Mapping: CM-SP-R-OSSI 
         UsPowerCapabilities"
    ::= { docsRphyRpdDevMibObjects 44}

docsRphyRpdDevUsPowerCapEntry OBJECT-TYPE
    SYNTAX     DocsRphyRpdDevUsPowerCapEntry
    MAX-ACCESS not-accessible
    STATUS     current
    DESCRIPTION
        "The conceptual row of docsRphyRpdDevUsPowerCapTable."
    INDEX { docsRphyRpdDevInfoUniqueId }
    ::= { docsRphyRpdDevUsPowerCapTable 1 }

DocsRphyRpdDevUsPowerCapEntry ::= SEQUENCE
    {
      docsRphyRpdDevUsPowerCapMinTarRxPowerAdjust55d2  TenthdB,
      docsRphyRpdDevUsPowerCapMaxTarRxPowerAdjust55d2  TenthdB
    } 
    
docsRphyRpdDevUsPowerCapMinTarRxPowerAdjust55d2 OBJECT-TYPE
    SYNTAX      TenthdB (-32768..32767)  
    UNITS       "dB"
    MAX-ACCESS  read-only
    STATUS      current
    DESCRIPTION
        "This attribute reports the minimum value of the 
         TargetRxPowerAdjust attribute that the RPD supports
         for SCTE 55-2 upstream channels."
    REFERENCE 
        "Information Model Mapping: CM-SP-R-OSSI 
         UsPowerCapabilities::MinTargetRxPowerAdjust55d2"
    ::= { docsRphyRpdDevUsPowerCapEntry 1 }
    
docsRphyRpdDevUsPowerCapMaxTarRxPowerAdjust55d2 OBJECT-TYPE
    SYNTAX      TenthdB (-32768..32767)  
    UNITS       "dB"
    MAX-ACCESS  read-only
    STATUS      current
    DESCRIPTION
        "This attribute reports the maximum value of the 
         TargetRxPowerAdjust attribute that the RPD supports
         for SCTE 55-2 upstream channels."
    REFERENCE 
         "Information Model Mapping: CM-SP-R-OSSI 
          UsPowerCapabilities::MaxTargetRxPowerAdjust55d2"
    ::= { docsRphyRpdDevUsPowerCapEntry 2 }
    
-- ---------------------------------------------------------------------
-- RPD Tunnel Replace Failures (TRF) Statistics
-- ---------------------------------------------------------------------

docsRphyRpdDevTrfStatsTable OBJECT-TYPE
    SYNTAX      SEQUENCE OF DocsRphyRpdDevTrfStatsEntry
    MAX-ACCESS  not-accessible
    STATUS      current
    DESCRIPTION
        "The RpdTrfStats table is supported by an RPD that implements
         TRF and is used to report on the TRF activity by the RPD.
         The CCAP Core reads all attributes of an RpdTrfStats object 
         with complex GCP TLV 100.32."
    ::= { docsRphyRpdDevMibObjects 45}

docsRphyRpdDevTrfStatsEntry OBJECT-TYPE
    SYNTAX     DocsRphyRpdDevTrfStatsEntry
    MAX-ACCESS not-accessible
    STATUS     current
    DESCRIPTION
        "The conceptual row of docsRphyRpdDevTrfStatsTable."
    INDEX { docsRphyRpdDevInfoUniqueId }
    ::= { docsRphyRpdDevTrfStatsTable 1 }

DocsRphyRpdDevTrfStatsEntry ::= SEQUENCE
    {
      docsRphyRpdDevTrfStatsTunnelReplacements         Counter32,
      docsRphyRpdDevTrfStatsTunnelReplacementFailures  Counter32,
      docsRphyRpdDevTrfStatsTunnelHandovers            Counter32,
      docsRphyRpdDevTrfStatsTunnelHandoverFailures     Counter32
    } 
    
docsRphyRpdDevTrfStatsTunnelReplacements  OBJECT-TYPE
    SYNTAX      Counter32  
    MAX-ACCESS  read-only
    STATUS      current
    DESCRIPTION
        "This attribute counts the number of tunnels successfully
         replaced by the RPD due to reception of an SCCRQ containing
         a DEPI Replaced Tunnel ID AVP identifying the tunnel to be
         replaced."
    REFERENCE 
         "Information Model Mapping: CM-SP-R-OSSI 
          RpdTrfStats::TunnelReplacements"
    ::= { docsRphyRpdDevTrfStatsEntry 1 } 

docsRphyRpdDevTrfStatsTunnelReplacementFailures  OBJECT-TYPE
    SYNTAX      Counter32  
    MAX-ACCESS  read-only
    STATUS      current
    DESCRIPTION
        "This attribute counts the number of tunnel replacement
         attempts due to reception of an SCCRQ containing a DEPI 
         Replaced Tunnel ID AVP by the RPD that failed."
    REFERENCE 
         "Information Model Mapping: CM-SP-R-OSSI 
          RpdTrfStats::TunnelReplacementFailures"
    ::= { docsRphyRpdDevTrfStatsEntry 2 } 

docsRphyRpdDevTrfStatsTunnelHandovers  OBJECT-TYPE
    SYNTAX      Counter32  
    MAX-ACCESS  read-only
    STATUS      current
    DESCRIPTION
        "This attribute counts the number of tunnels successfully
         transitioned from standby to inService HA state by the 
         RPD due to reception of a DTU message."
    REFERENCE 
         "Information Model Mapping: CM-SP-R-OSSI 
          RpdTrfStats::TunnelHandovers"
    ::= { docsRphyRpdDevTrfStatsEntry 3 } 

docsRphyRpdDevTrfStatsTunnelHandoverFailures  OBJECT-TYPE
    SYNTAX      Counter32  
    MAX-ACCESS  read-only
    STATUS      current
    DESCRIPTION
        "This attribute counts the number of tunnel handover 
        attempts by the RPD that failed to transition from 
        standby to inService HA state following reception 
        of a DTU message."
    REFERENCE 
         "Information Model Mapping: CM-SP-R-OSSI 
          RpdTrfStats::TunnelHandoverFailures"
    ::= { docsRphyRpdDevTrfStatsEntry 4 }   
    
-- ---------------------------------------------------------------------
--  RPD L2TPv3 Control Connection (LCCE) Statistics
-- ---------------------------------------------------------------------

docsRphyRpdDevLcceStatsTable OBJECT-TYPE
    SYNTAX      SEQUENCE OF DocsRphyRpdDevLcceStatsEntry
    MAX-ACCESS  not-accessible
    STATUS      current
    DESCRIPTION
        "This table is reported by the CCAP Core on behalf of the RPD 
         and is used to report on the DEPI L2TPv3 control connection 
         activity between the RPD and all the CCAP Cores with which the
         RPD has control connections. 
         The CCAP Core reads the LcceStats entries from the GCP complex
         TLV Type 100.33.1."
    REFERENCE 
         "Information Model Mapping: CM-SP-R-OSSI 
          RpdLcceStats"
    ::= { docsRphyRpdDevMibObjects 46}

docsRphyRpdDevLcceStatsEntry OBJECT-TYPE
    SYNTAX     DocsRphyRpdDevLcceStatsEntry
    MAX-ACCESS not-accessible
    STATUS     current
    DESCRIPTION
        "The conceptual row of docsRphyRpdDevLcceStatsTable."
    INDEX { docsRphyRpdDevInfoUniqueId,
            docsRphyRpdDevLcceStatsLcceIpAddrType,
            docsRphyRpdDevLcceStatsCcapLcceIpAddr,
            docsRphyRpdDevLcceStatsRpdLcceIpAddr
          }
    ::= { docsRphyRpdDevLcceStatsTable 1 }

DocsRphyRpdDevLcceStatsEntry ::= SEQUENCE
    {
     docsRphyRpdDevLcceStatsLcceIpAddrType          InetAddressType,
     docsRphyRpdDevLcceStatsCcapLcceIpAddr          InetAddress,
     docsRphyRpdDevLcceStatsRpdLcceIpAddr           InetAddress,
     docsRphyRpdDevLcceStatsCtrlConnEst             Counter32,
     docsRphyRpdDevLcceStatsCtrlConnEstFailures     Counter32,
     docsRphyRpdDevLcceStatsCtrlConnFailures        Counter32,
     docsRphyRpdDevLcceStatsCurrCtrlConn            Unsigned32
    } 
   
docsRphyRpdDevLcceStatsLcceIpAddrType   OBJECT-TYPE
    SYNTAX      InetAddressType    
    MAX-ACCESS  not-accessible
    STATUS      current
    DESCRIPTION 
        "This key attribute indicates whether the IP address
         provided in the CcapLcceIpAddr and RpdLcceIpAddr 
         attributes are IPv4 or IPv6."
    REFERENCE 
         "Information Model Mapping: CM-SP-R-OSSI 
          RpdLcceStats::LcceIpAddrType"
    ::= { docsRphyRpdDevLcceStatsEntry 1 }

docsRphyRpdDevLcceStatsCcapLcceIpAddr  OBJECT-TYPE
    SYNTAX      InetAddress (SIZE(4|16))
    MAX-ACCESS  not-accessible
    STATUS      current
    DESCRIPTION 
        "This key attribute provides the LCCE IP address
         on the CCAP Core detailed in the instance."
    REFERENCE 
         "Information Model Mapping: CM-SP-R-OSSI 
          RpdLcceStats::CcapLcceIpAddress"
    ::= { docsRphyRpdDevLcceStatsEntry 2 }

docsRphyRpdDevLcceStatsRpdLcceIpAddr OBJECT-TYPE
    SYNTAX      InetAddress  (SIZE(4|16))
    MAX-ACCESS  not-accessible
    STATUS      current
    DESCRIPTION 
        "This key attribute reports the RPD LCCE
         IP address detailed in the instance."
    REFERENCE 
         "Information Model Mapping: CM-SP-R-OSSI 
          RpdLcceStats::RpdLcceIpAddr"
    ::= { docsRphyRpdDevLcceStatsEntry 3 }
    
docsRphyRpdDevLcceStatsCtrlConnEst OBJECT-TYPE
    SYNTAX      Counter32
    MAX-ACCESS  read-only
    STATUS      current
    DESCRIPTION 
        "This attribute counts the number of DEPI control 
         connections successfully established between the 
         RPD and CCAP Core LCCEs."
    REFERENCE 
         "Information Model Mapping: CM-SP-R-OSSI 
          RpdLcceStats::ControlConnectionEstablished"
    ::= { docsRphyRpdDevLcceStatsEntry 4 }
    
docsRphyRpdDevLcceStatsCtrlConnEstFailures OBJECT-TYPE
    SYNTAX      Counter32
    MAX-ACCESS  read-only
    STATUS      current
    DESCRIPTION 
        "This attribute counts the number of DEPI control 
         connections that failed during establishment 
         between the RPD and CCAP Core LCCEs."
    REFERENCE 
         "Information Model Mapping: CM-SP-R-OSSI 
          RpdLcceStats::ControlConnectionEstablishmentFailures"
    ::= { docsRphyRpdDevLcceStatsEntry 5 }
    
docsRphyRpdDevLcceStatsCtrlConnFailures OBJECT-TYPE
    SYNTAX      Counter32
    MAX-ACCESS  read-only
    STATUS      current
    DESCRIPTION 
        "This attribute counts the number of DEPI control 
         connections between the RPD and CCAP Core LCCEs in
         which a failure was detected (after successful 
         tunnel establishment) that led to the connection
         being closed."
    REFERENCE 
         "Information Model Mapping: CM-SP-R-OSSI 
          RpdLcceStats::ControlConnectionFailures"
    ::= { docsRphyRpdDevLcceStatsEntry 6}
    
docsRphyRpdDevLcceStatsCurrCtrlConn OBJECT-TYPE
    SYNTAX      Unsigned32 (0..65535)
    MAX-ACCESS  read-only
    STATUS      current
    DESCRIPTION 
        "This attribute counts the number of DEPI control connections 
         that are currently operational between the RPD and CCAP Core
         LCCEs (i.e connections that are in an InService or Standby state).
         Connections that have been removed are not included in the count."
    REFERENCE 
         "Information Model Mapping: CM-SP-R-OSSI 
          RpdLcceStats::CurrentControlConnections"
    ::= { docsRphyRpdDevLcceStatsEntry 7}
    
-- ---------------------------------------------------------------------
--  RPD Current Control Connections
-- ---------------------------------------------------------------------

docsRphyRpdDevCurrCtrlConnTable OBJECT-TYPE
    SYNTAX      SEQUENCE OF DocsRphyRpdDevCurrCtrlConnEntry
    MAX-ACCESS  not-accessible
    STATUS      current
    DESCRIPTION
        "This table is reported by the CCAP Core on behalf of the RPD and 
         is used to report on the currently active DEPI L2TPv3 control 
         connections on the RPD. The CCAP Core reads the CurrentCtrlConn
         entries from the GCP complex TLV Type 100.33.2."
    REFERENCE 
         "Information Model Mapping: CM-SP-R-OSSI 
          RpdCurrentControlConnections"
    ::= { docsRphyRpdDevMibObjects 47}

docsRphyRpdDevCurrCtrlConnEntry OBJECT-TYPE
    SYNTAX     DocsRphyRpdDevCurrCtrlConnEntry
    MAX-ACCESS not-accessible
    STATUS     current
    DESCRIPTION
        "The conceptual row of docsRphyRpdDevCurrCtrlConnTable."
    INDEX { docsRphyRpdDevInfoUniqueId,
            docsRphyRpdDevCurrCtrlConnLcceIpAddrType,
            docsRphyRpdDevCurrCtrlConnCcapLcceIpAddr,
            docsRphyRpdDevCurrCtrlConnRpdLcceIpAddr,
            docsRphyRpdDevCurrCtrlConnRpdConnCtrlId }
    ::= { docsRphyRpdDevCurrCtrlConnTable 1 }

DocsRphyRpdDevCurrCtrlConnEntry ::= SEQUENCE
    {
     docsRphyRpdDevCurrCtrlConnLcceIpAddrType    InetAddressType,
     docsRphyRpdDevCurrCtrlConnCcapLcceIpAddr    InetAddress,
     docsRphyRpdDevCurrCtrlConnRpdLcceIpAddr     InetAddress,
     docsRphyRpdDevCurrCtrlConnRpdConnCtrlId     Unsigned32,
     docsRphyRpdDevCurrCtrlConnCoreConnCtrlId    Unsigned32,
     docsRphyRpdDevCurrCtrlConnCoreId            OCTET STRING,
     docsRphyRpdDevCurrCtrlConnUdpPort           InetPortNumber,
     docsRphyRpdDevCurrCtrlConnHaState           INTEGER,
     docsRphyRpdDevCurrCtrlConnSessEstFailures   Counter32,
     docsRphyRpdDevCurrCtrlConnSessFailed        Counter32,
     docsRphyRpdDevCurrCtrlConnCurrSess          Unsigned32
    } 
    
docsRphyRpdDevCurrCtrlConnLcceIpAddrType  OBJECT-TYPE
    SYNTAX      InetAddressType    
    MAX-ACCESS  not-accessible
    STATUS      current
    DESCRIPTION 
        "This key attribute indicates whether the IP address
         provided in the CcapLcceIpAddr and RpdLcceIpAddr 
         attributes are IPv4 or IPv6."
    ::= { docsRphyRpdDevCurrCtrlConnEntry 1 }

docsRphyRpdDevCurrCtrlConnCcapLcceIpAddr  OBJECT-TYPE
    SYNTAX      InetAddress (SIZE(4|16))
    MAX-ACCESS  not-accessible
    STATUS      current
    DESCRIPTION 
        "This key attribute provides the LCCE IP 
         address on the CCAP Core of the control 
         connection detailed in the instance."
     ::= { docsRphyRpdDevCurrCtrlConnEntry 2 }

docsRphyRpdDevCurrCtrlConnRpdLcceIpAddr OBJECT-TYPE
    SYNTAX      InetAddress  (SIZE(4|16))
    MAX-ACCESS  not-accessible
    STATUS      current
    DESCRIPTION 
        "This key attribute reports the RPD LCCE IP 
         address of the control connection detailed 
         in the instance."
    ::= { docsRphyRpdDevCurrCtrlConnEntry 3 }
    
docsRphyRpdDevCurrCtrlConnRpdConnCtrlId OBJECT-TYPE
    SYNTAX      Unsigned32
    MAX-ACCESS  not-accessible
    STATUS      current
    DESCRIPTION 
        "This key attribute reports the RPD control connection
        identifier (CCID) for this control connection."
    REFERENCE 
        "Information Model Mapping: CM-SP-R-OSSI 
         RpdCurrentControlConnections::RpdConnCtrlId"
    ::= { docsRphyRpdDevCurrCtrlConnEntry 4 }
    
docsRphyRpdDevCurrCtrlConnCoreConnCtrlId OBJECT-TYPE
    SYNTAX      Unsigned32
    MAX-ACCESS  read-only
    STATUS      current
    DESCRIPTION 
        "This attribute reports the Core control connection 
         identifier (CCID) for this control connection."
    REFERENCE 
        "Information Model Mapping: CM-SP-R-OSSI 
         RpdCurrentControlConnections::CoreConnCtrlId"
    ::= { docsRphyRpdDevCurrCtrlConnEntry 5 }
    
docsRphyRpdDevCurrCtrlConnCoreId OBJECT-TYPE
    SYNTAX      OCTET STRING (SIZE(6))
    MAX-ACCESS  read-only
    STATUS      current
    DESCRIPTION 
        "This attribute reports the unique identifier of the CCAP
         Core with which this control connection terminates. "
    REFERENCE 
        "Information Model Mapping: CM-SP-R-OSSI 
         RpdCurrentControlConnections::CoreId"
    ::= { docsRphyRpdDevCurrCtrlConnEntry 6 }
    
docsRphyRpdDevCurrCtrlConnUdpPort OBJECT-TYPE
    SYNTAX      InetPortNumber
    MAX-ACCESS  read-only
    STATUS      current
    DESCRIPTION 
        "This attribute reports the UDP Port reported by the RPD 
         when the DEPI control connection uses L2TPv3 Header Over UDP. 
         This attribute reports a value of 0 when the control connection
         is running with the L2TPv3 Session IP Header. "
    REFERENCE 
        "Information Model Mapping: CM-SP-R-OSSI 
         RpdCurrentControlConnections::UdpPort"
    ::= { docsRphyRpdDevCurrCtrlConnEntry 7 } 

docsRphyRpdDevCurrCtrlConnHaState OBJECT-TYPE
    SYNTAX      INTEGER  {
                          other(0),
                          inService(1),
                          standby(2)
                         }
    MAX-ACCESS  read-only
    STATUS      current
    DESCRIPTION 
        "This attribute indicates the current HaState of the tunnel
         for which this DEPI control connection provides the signaling. 
         If TRF is not supported by either the Core or the RPD then 
         HaState is reported as inService."
    REFERENCE 
        "Information Model Mapping: CM-SP-R-OSSI 
         RpdCurrentControlConnections::HaState"
    ::= { docsRphyRpdDevCurrCtrlConnEntry 8 }
    
 docsRphyRpdDevCurrCtrlConnSessEstFailures OBJECT-TYPE
    SYNTAX      Counter32
    MAX-ACCESS  read-only
    STATUS      current
    DESCRIPTION 
        "This attribute counts the number of DEPI sessions that 
         failed during establishment using this control connection."
    REFERENCE 
        "Information Model Mapping: CM-SP-R-OSSI 
         RpdCurrentControlConnections::SessionEstablishmentFailures"
    ::= { docsRphyRpdDevCurrCtrlConnEntry 9 }
    
docsRphyRpdDevCurrCtrlConnSessFailed OBJECT-TYPE
    SYNTAX      Counter32
    MAX-ACCESS  read-only
    STATUS      current
    DESCRIPTION 
        "This attribute counts the number of DEPI sessions in which
        a failure was detected (after successful tunnel establishment) 
        that led to the session being closed using this control connection."
    REFERENCE 
        "Information Model Mapping: CM-SP-R-OSSI 
         RpdCurrentControlConnections::SessionsFailed"
    ::= { docsRphyRpdDevCurrCtrlConnEntry 10 }

docsRphyRpdDevCurrCtrlConnCurrSess OBJECT-TYPE
    SYNTAX      Unsigned32 (0..65535)
    MAX-ACCESS  read-only
    STATUS      current
    DESCRIPTION 
        "This attribute counts the number of current DEPI sessions 
         using this control connection (i.e., sessions that are in an
         inService or standby state). Sessions that have been removed 
         are not included in the count. "
    REFERENCE 
        "Information Model Mapping: CM-SP-R-OSSI 
         RpdCurrentControlConnections::CurrentSessions"
    ::= { docsRphyRpdDevCurrCtrlConnEntry 11 }
    
-- ---------------------------------------------------------------------
-- RPD Telemetry Capabilities
-- ---------------------------------------------------------------------

docsRphyRpdDevTelemetryCapTable OBJECT-TYPE
    SYNTAX      SEQUENCE OF DocsRphyRpdDevTelemetryCapEntry
    MAX-ACCESS  not-accessible
    STATUS      current
    DESCRIPTION
        "This table reports the Telemetry Capabilities of
         the RPD."
    REFERENCE 
        "Information Model Mapping: CM-SP-R-OSSI 
         TelemetryCapabilities"
    ::= { docsRphyRpdDevMibObjects 48 }

docsRphyRpdDevTelemetryCapEntry OBJECT-TYPE
    SYNTAX     DocsRphyRpdDevTelemetryCapEntry
    MAX-ACCESS not-accessible
    STATUS     current
    DESCRIPTION
        "The conceptual row of docsRphyRpdDevTelemetryCapTable."
    INDEX { docsRphyRpdDevInfoUniqueId  }
    ::= { docsRphyRpdDevTelemetryCapTable 1 }

DocsRphyRpdDevTelemetryCapEntry::= SEQUENCE
    {
    docsRphyRpdDevTelemetryCapSupportsGnmiStreaming    TruthValue,
    docsRphyRpdDevTelemetryCapNumClientsSupported      Unsigned32
    }
    
docsRphyRpdDevTelemetryCapSupportsGnmiStreaming OBJECT-TYPE
    SYNTAX      TruthValue
    MAX-ACCESS  read-only
    STATUS      current
    DESCRIPTION 
        "This attribute reports the RPD's support for Streaming Telemetry 
         using gRPC Network Management Interface (gNMI) protocol. 
         Value 'true' indicates the RPD supports Streaming Telemetry using gNMI. 
         Value 'false' indicates the RPD does not support Streaming Telemetry
         using gNMI."
    REFERENCE 
        "Information Model Mapping: CM-SP-R-OSSI 
         TelemetryCapabilities::SupportsGnmiStreamingTelemetry"
    ::= { docsRphyRpdDevTelemetryCapEntry 1 }
    
docsRphyRpdDevTelemetryCapNumClientsSupported    OBJECT-TYPE
    SYNTAX      Unsigned32 (0..255)
    MAX-ACCESS  read-only
    STATUS      current
    DESCRIPTION 
        "This attribute reports the number of Telemetry Clients supported 
         by the RPD. This attribute should be ignored if the value 
         of SupportsStreamingTelemetry is 'false'."
    REFERENCE 
        "Information Model Mapping: CM-SP-R-OSSI 
         TelemetryCapabilities::NumTelemetryClientsSupported"
    ::= { docsRphyRpdDevTelemetryCapEntry 2 }


-- ---------------------------------------------------------------------
-- RPD Node Port Map Downstream Capabilities
-- ---------------------------------------------------------------------

docsRphyRpdDevNodePortMapDsCapTable OBJECT-TYPE
    SYNTAX      SEQUENCE OF DocsRphyRpdDevNodePortMapDsCapEntry
    MAX-ACCESS  not-accessible
    STATUS      current
    DESCRIPTION
        "The NodePortMap TLV 50.60.18 reports the topology of Node Port
         (NP) to Partial Spectrum RF port connections. The presence of
         the NodePortMap objects indicate that the RPN has Partial
         Spectrum RF ports to which channels can be configured with GCP.
         An RPN that is capable of being configured with Partial
         Spectrum RF Ports is said to be 'Partial Spectrum-capable'. An
         RPN indicates it is Partial Spectrum-capable by reporting the
         NodePortMap (TLV 50.60.18) TLV capability. Absence of the
         NodePortMap capability table indicates that the RPN is not
         Partial Spectrum-capable.
         The NodePortMap consist of separate objects for the downstream
         and upstream direction because the number of downstream RF Ports
         can differ from the number of upstream RF Ports.
         The NodePortMapDsCapabilities object reports in each instance
         the association of Node Port (NP) to a downstream Partial
         Spectrum RF port and attributes of that association."
    REFERENCE 
        "Information Model Mapping: CM-SP-R-OSSI 
         NodePortMapDsCapabilities"
    ::= { docsRphyRpdDevMibObjects 49 }

docsRphyRpdDevNodePortMapDsCapEntry OBJECT-TYPE
    SYNTAX     DocsRphyRpdDevNodePortMapDsCapEntry
    MAX-ACCESS not-accessible
    STATUS     current
    DESCRIPTION
        "The conceptual row of docsRphyRpdDevNodePortMapDsCapTable."
    INDEX { docsRphyRpdDevInfoUniqueId,
            docsRphyRpdDevNodePortMapDsCapNodePortIndex,
            docsRphyRpdDevNodePortMapDsCapDsRfPortIndex
          }
    ::= { docsRphyRpdDevNodePortMapDsCapTable 1 }

DocsRphyRpdDevNodePortMapDsCapEntry::= SEQUENCE
    {
    docsRphyRpdDevNodePortMapDsCapNodePortIndex    Unsigned32,
    docsRphyRpdDevNodePortMapDsCapDsRfPortIndex    Unsigned32,
    docsRphyRpdDevNodePortMapDsCapGainControlIndex Unsigned32
    }
    
docsRphyRpdDevNodePortMapDsCapNodePortIndex OBJECT-TYPE
    SYNTAX      Unsigned32 (0..255)
    MAX-ACCESS  not-accessible
    STATUS      current
    DESCRIPTION 
        "This attribute provides the Node Port index of an instance
         of the NodePortMapDs table."
    REFERENCE 
        "Information Model Mapping: CM-SP-R-OSSI 
         NodePortMapDsCapabilities::NodePortIndex"
    ::= { docsRphyRpdDevNodePortMapDsCapEntry 1 }

docsRphyRpdDevNodePortMapDsCapDsRfPortIndex OBJECT-TYPE
    SYNTAX      Unsigned32 (0..255)
    MAX-ACCESS  not-accessible
    STATUS      current
    DESCRIPTION 
        "This attribute provides the downstream RF port index of an
         instance of the NodePortMapDs object."
    REFERENCE 
        "Information Model Mapping: CM-SP-R-OSSI 
         NodePortMapDsCapabilities::DsRfPortIndex"
    ::= { docsRphyRpdDevNodePortMapDsCapEntry 2 }

docsRphyRpdDevNodePortMapDsCapGainControlIndex OBJECT-TYPE
    SYNTAX      Unsigned32 (0..255)
    MAX-ACCESS  read-only
    STATUS      current
    DESCRIPTION 
        "This attribute reports the downstream gain control index to
         configure in the DsPowerGainIndex (TLV 160.1.1) to configure
         the pairwise gain from Interface C power density of this
         instance's downstream Partial Spectrum RF port to the
         corresponding spectrum of this instance's Node Port."
    REFERENCE 
        "Information Model Mapping: CM-SP-R-OSSI 
         NodePortMapDsCapabilities::GainControlIndex"
    ::= { docsRphyRpdDevNodePortMapDsCapEntry 3 }


-- ---------------------------------------------------------------------
-- RPD Node Port Map Upstream Capabilities
-- ---------------------------------------------------------------------

docsRphyRpdDevNodePortMapUsCapTable OBJECT-TYPE
    SYNTAX      SEQUENCE OF DocsRphyRpdDevNodePortMapUsCapEntry
    MAX-ACCESS  not-accessible
    STATUS      current
    DESCRIPTION
        "The NodePortMap TLV 50.60.18 reports the topology of Node Port
         (NP) to Partial Spectrum RF port connections. The presence of
         the NodePortMap objects indicate that the RPN has Partial
         Spectrum RF ports to which channels can be configured with GCP.
         An RPN that is capable of being configured with Partial
         Spectrum RF Ports is said to be 'Partial Spectrum-capable'. An
         RPN indicates it is Partial Spectrum-capable by reporting the
         NodePortMap (TLV 50.60.18) TLV capability. Absence of the
         NodePortMap capability table indicates that the RPN is not
         Partial Spectrum-capable.
         The NodePortMap consist of separate objects for the downstream
         and upstream direction because the number of downstream RF Ports
         can differ from the number of upstream RF Ports.
         The NodePortMapUsCapabilities table reports in each instance the
         association of Node Port (NP) to a upstream Partial Spectrum RF
         port and attributes of that association."
    REFERENCE 
        "Information Model Mapping: CM-SP-R-OSSI 
         NodePortMapUsCapabilities"
    ::= { docsRphyRpdDevMibObjects 50 }

docsRphyRpdDevNodePortMapUsCapEntry OBJECT-TYPE
    SYNTAX     DocsRphyRpdDevNodePortMapUsCapEntry
    MAX-ACCESS not-accessible
    STATUS     current
    DESCRIPTION
        "The conceptual row of docsRphyRpdDevNodePortMapUsCapTable."
    INDEX { docsRphyRpdDevInfoUniqueId,
            docsRphyRpdDevNodePortMapUsCapNodePortIndex,
            docsRphyRpdDevNodePortMapUsCapUsRfPortIndex
          }
    ::= { docsRphyRpdDevNodePortMapUsCapTable 1 }

DocsRphyRpdDevNodePortMapUsCapEntry::= SEQUENCE
    {
    docsRphyRpdDevNodePortMapUsCapNodePortIndex    Unsigned32,
    docsRphyRpdDevNodePortMapUsCapUsRfPortIndex    Unsigned32,
    docsRphyRpdDevNodePortMapUsCapGainControlIndex Unsigned32
    }
    
docsRphyRpdDevNodePortMapUsCapNodePortIndex OBJECT-TYPE
    SYNTAX      Unsigned32 (0..255)
    MAX-ACCESS  not-accessible
    STATUS      current
    DESCRIPTION 
        "This attribute provides the Node Port index of an instance
         of the NodePortMapUs table."
    REFERENCE 
        "Information Model Mapping: CM-SP-R-OSSI 
         NodePortMapUsCapabilities::NodePortIndex"
    ::= { docsRphyRpdDevNodePortMapUsCapEntry 1 }

docsRphyRpdDevNodePortMapUsCapUsRfPortIndex OBJECT-TYPE
    SYNTAX      Unsigned32 (0..255)
    MAX-ACCESS  not-accessible
    STATUS      current
    DESCRIPTION 
        "This attribute provides the upstream RF port index of an
         instance of the NodePortMapUs object."
    REFERENCE 
        "Information Model Mapping: CM-SP-R-OSSI 
         NodePortMapUsCapabilities::UsRfPortIndex"
    ::= { docsRphyRpdDevNodePortMapUsCapEntry 2 }

docsRphyRpdDevNodePortMapUsCapGainControlIndex OBJECT-TYPE
    SYNTAX      Unsigned32 (0..255)
    MAX-ACCESS  read-only
    STATUS      current
    DESCRIPTION 
        "This attribute reports the upstream gain control index
         to configure in the UsPowerGainIndex (TLV 160.2.1) to
         set the pairwise gain from this instance's Node Port to
         the Interface C spectrum range of this instance's
         upstream Partial Spectrum RF port."
    REFERENCE 
        "Information Model Mapping: CM-SP-R-OSSI 
         NodePortMapUsCapabilities::GainControlIndex"
    ::= { docsRphyRpdDevNodePortMapUsCapEntry 3 }


-- ---------------------------------------------------------------------
-- RPD Physical Group Objects Derived from RFC 6933 ENTITY-MIB
-- RPD Interface Group Objects Derived from IF-MIB RFC 2863
-- ---------------------------------------------------------------------  

-- ---------------------------------------------------------------------
-- RPD Physical Entity Table extracted from RFC 6933 ENTITY-MIB
-- ---------------------------------------------------------------------

docsRphyRpdIfPhysEntityTable OBJECT-TYPE
    SYNTAX      SEQUENCE OF DocsRphyRpdIfPhysEntityEntry
    MAX-ACCESS  not-accessible
    STATUS      current
    DESCRIPTION
        "This table reports entities that exist within each Remote
         PHY Node that is communicating with the CCAP Core. Because
         the entities exist within the Remote PHY Nodes and not the
         CCAP Core, the RPDs communicate this information to the
         CCAP core via GCP.  This object is based on the
         entPhysicalTable object specified in the ENTITY-MIB from
         RFC 6933.

         An RPD in a shelf MUST report the Entity with EntityIndex 
         one as having a Class value of 'chassis'. This represents 
         the shelf which contains the RPDs. An RPD in a shelf MUST 
         report an Entity with Class value of 'chassis' with a ContainedIn
         value of zero and a ParentRelPos value of zero. An RPD not in a 
         shelf (i.e., an RPD in a node) MAY report an Entity with EntityIndex 
         one as having a Class value of 'chassis'. If an RPD not in a shelf 
         reports an Entity with EntityIndex one as having a Class value of 
         'chassis', the RPD SHOULD be treated as an RPD in a one-RPD shelf. 
         An RPD with an Entity with EntityIndex one that does not have a 
         Class value of 'chassis' MUST be treated as an RPD in a node.

         All RPDs in the same shelf MUST report the same chassis SerialNum
         for the chassis Entity with EntityIndex one.

         The CCAP Core reads all attributes of an Entity Object with 
         GCP complex TLV Type 100.6."
    REFERENCE 
        "Information Model Mapping: CM-SP-R-OSSI 
         Entity"
    ::= { docsRphyRpdIfMibObjects 1 }

docsRphyRpdIfPhysEntityEntry       OBJECT-TYPE
    SYNTAX      DocsRphyRpdIfPhysEntityEntry
    MAX-ACCESS  not-accessible
    STATUS      current
    DESCRIPTION
        "Information about a particular physical entity.

         Each entry provides objects (docsRphyRpdIfPhysEntityDescr,
         docsRphyRpdIfPhysEntityVendorType, and 
         docsRphyRpdIfPhysEntityClass) to help an NMS
         identify and characterize the entry and objects
         (docsRphyRpdIfPhysEntityContainedIn and 
         docsRphyRpdIfPhysEntityParentRelPos) to help
         an NMS relate the particular entry to other entries in this
         table."
    INDEX   { docsRphyRpdDevInfoUniqueId,
              docsRphyRpdIfPhysEntityIndex }
    ::= { docsRphyRpdIfPhysEntityTable 1 }

DocsRphyRpdIfPhysEntityEntry ::= SEQUENCE 
    {
    docsRphyRpdIfPhysEntityIndex          PhysicalIndex,
    docsRphyRpdIfPhysEntityDescr          SnmpAdminString,
    docsRphyRpdIfPhysEntityVendorType     SnmpAdminString,
    docsRphyRpdIfPhysEntityContainedIn    PhysicalIndexOrZero,
    docsRphyRpdIfPhysEntityClass          IANAPhysicalClass,
    docsRphyRpdIfPhysEntityParentRelPos   Integer32,
    docsRphyRpdIfPhysEntityName           SnmpAdminString,
    docsRphyRpdIfPhysEntityHardwareRev    SnmpAdminString,
    docsRphyRpdIfPhysEntityFirmwareRev    SnmpAdminString,
    docsRphyRpdIfPhysEntitySoftwareRev    SnmpAdminString,
    docsRphyRpdIfPhysEntitySerialNum      SnmpAdminString,
    docsRphyRpdIfPhysEntityMfgName        SnmpAdminString,
    docsRphyRpdIfPhysEntityModelName      SnmpAdminString,
    docsRphyRpdIfPhysEntityAlias          SnmpAdminString,
    docsRphyRpdIfPhysEntityAssetID        SnmpAdminString,
    docsRphyRpdIfPhysEntityIsFRU          TruthValue,
    docsRphyRpdIfPhysEntityMfgDate        DateAndTime,
    docsRphyRpdIfPhysEntityUris           OCTET STRING,
    docsRphyRpdIfPhysEntityUUID           UUIDorZero
    }

docsRphyRpdIfPhysEntityIndex    OBJECT-TYPE
    SYNTAX      PhysicalIndex  (1..2147483647)
    MAX-ACCESS  not-accessible
    STATUS      current
    DESCRIPTION
        "This key attribute reports an arbitrary value that uniquely 
         identifies the physical entity.  Index values for different 
         physical entities are not necessarily contiguous."
    ::= { docsRphyRpdIfPhysEntityEntry 1 }

docsRphyRpdIfPhysEntityDescr OBJECT-TYPE
    SYNTAX      SnmpAdminString
    MAX-ACCESS  read-only
    STATUS      current
    DESCRIPTION
        "A textual description of physical entity.  This object
            should contain a string that identifies the manufacturer's
            name for the physical entity and should be set to a
            distinct value for each version or model of the physical
            entity."
    ::= { docsRphyRpdIfPhysEntityEntry 2 }

docsRphyRpdIfPhysEntityVendorType OBJECT-TYPE
    SYNTAX      SnmpAdminString
    MAX-ACCESS  read-only
    STATUS      current
    DESCRIPTION
        "An indication of the vendor-specific hardware type of the
         physical entity.  Note that this is different from the
         definition of MIB-II's sysObjectID.

         An agent should set this object to an enterprise-specific
         registration identifier value indicating the specific
         equipment type in detail.  The associated instance of
         docsRphyRpdIfPhysEntityClass is used to indicate the 
         general type of hardware device.

         If no vendor-specific registration identifier exists for
         this physical entity, or the value is unknown by this agent,
         then an empty string is returned."
    ::= { docsRphyRpdIfPhysEntityEntry 3 }

docsRphyRpdIfPhysEntityContainedIn OBJECT-TYPE
    SYNTAX      PhysicalIndexOrZero
    MAX-ACCESS  read-only
    STATUS      current
    DESCRIPTION
        "The value of docsRphyRpdIfPhysEntityIndex for the physical entity that
         'contains' this physical entity.  A value of zero indicates
         this physical entity is not contained in any other physical
         entity.  Note that the set of 'containment' relationships
         define a strict hierarchy; that is, recursion is not
         allowed.

         In the event that a physical entity is contained by more
         than one physical entity (e.g., double-wide modules), this
         object should identify the containing entity with the lowest
         value of docsRphyRpdIfPhysEntityIndex."
    ::= { docsRphyRpdIfPhysEntityEntry 4 }

docsRphyRpdIfPhysEntityClass OBJECT-TYPE
    SYNTAX      IANAPhysicalClass
    MAX-ACCESS  read-only
    STATUS      current
    DESCRIPTION
        "An indication of the general hardware type of the physical
         entity.

         An agent should set this object to the standard enumeration
         value that most accurately indicates the general class of
         the physical entity, or the primary class if there is more
         than one entity.

         If no appropriate standard registration identifier exists
         for this physical entity, then the value 'other(1)' is
         returned.  If the value is unknown by this agent, then the
         value 'unknown(2)' is returned."
    ::= { docsRphyRpdIfPhysEntityEntry 5 }

docsRphyRpdIfPhysEntityParentRelPos OBJECT-TYPE
    SYNTAX      Integer32 (1..2147483647)
    MAX-ACCESS  read-only
    STATUS      current
    DESCRIPTION
        "An indication of the relative position of this 'child'
         component among all its 'sibling' components.  Sibling
         components are defined as docsRphyRpdIfPhysEntityEntries that share the
         same instance values of each of the docsRphyRpdIfPhysEntityContainedIn
         and docsRphyRpdIfPhysEntityClass objects.

         An NMS can use this object to identify the relative ordering
         for all sibling components of a particular parent
         (identified by the docsRphyRpdIfPhysEntityContainedIn instance in each
         sibling entry).

         If possible, this value should match any external labeling
         of the physical component.  For example, for a container
         (e.g., card slot) labeled as 'slot #3',
         docsRphyRpdIfPhysEntityParentRelPos should have the value '3'.  Note
         that the docsRphyRpdIfPhysEntityEntry for the module plugged in slot 3
         should have an docsRphyRpdIfPhysEntityParentRelPos value of '1'.

         If the physical position of this component does not match
         any external numbering or clearly visible ordering, then
         user documentation or other external reference material
         should be used to determine the parent-relative position.
         If this is not possible, then the agent should assign a
         consistent (but possibly arbitrary) ordering to a given set
         of 'sibling' components, perhaps based on internal
         representation of the components.

         If the agent cannot determine the parent-relative position
         for some reason, or if the associated value of
         docsRphyRpdIfPhysEntityContainedIn is '0', then the value '-1' is
         returned.  Otherwise, a non-negative integer is returned,
         indicating the parent-relative position of this physical
         entity.

         Parent-relative ordering normally starts from '1' and
         continues to 'N', where 'N' represents the highest
         positioned child entity.  However, if the physical entities
         (e.g., slots) are labeled from a starting position of zero,
         then the first sibling should be associated with an
         docsRphyRpdIfPhysEntityParentRelPos value of '0'.  Note that this
         ordering may be sparse or dense, depending on agent
         implementation.

         The actual values returned are not globally meaningful, as
         each 'parent' component may use different numbering
         algorithms.  The ordering is only meaningful among siblings
         of the same parent component.

         The agent should retain parent-relative position values
         across reboots, either through algorithmic assignment or use
         of non-volatile storage."
    ::= { docsRphyRpdIfPhysEntityEntry 6 }

docsRphyRpdIfPhysEntityName OBJECT-TYPE
    SYNTAX      SnmpAdminString
    MAX-ACCESS  read-only
    STATUS      current
    DESCRIPTION
        "The textual name of the physical entity.  The value of this
         object should be the name of the component as assigned by
         the local device and should be suitable for use in commands
         entered at the device's 'console'.  This might be a text
         name (e.g., 'console') or a simple component number (e.g.,
         port or module number, such as '1'), depending on the
         physical component naming syntax of the device.

         If there is no local name, or if this object is otherwise
         not applicable, then this object contains a zero-length
         string.

         Note that the value of docsRphyRpdIfPhysEntityName for two physical
         entities will be the same in the event that the console
         interface does not distinguish between them, e.g., slot-1
         and the card in slot-1."
    ::= { docsRphyRpdIfPhysEntityEntry 7 }

docsRphyRpdIfPhysEntityHardwareRev    OBJECT-TYPE
    SYNTAX      SnmpAdminString
    MAX-ACCESS  read-only
    STATUS      current
    DESCRIPTION
        "The vendor-specific hardware revision string for the
         physical entity.  The preferred value is the hardware
         revision identifier actually printed on the component itself
         (if present).

         Note that if revision information is stored internally in a
         non-printable (e.g., binary) format, then the agent must
         convert such information to a printable format in an
         implementation-specific manner.

         If no specific hardware revision string is associated with
         the physical component, or if this information is unknown to
         the agent, then this object will contain a zero-length
         string."
    ::= { docsRphyRpdIfPhysEntityEntry 8 }

docsRphyRpdIfPhysEntityFirmwareRev    OBJECT-TYPE
    SYNTAX      SnmpAdminString
    MAX-ACCESS  read-only
    STATUS      current
    DESCRIPTION
        "The vendor-specific firmware revision string for the
         physical entity.

         Note that if revision information is stored internally in a
         non-printable (e.g., binary) format, then the agent must
         convert such information to a printable format in an
         implementation-specific manner.

         If no specific firmware programs are associated with the
         physical component, or if this information is unknown to the
         agent, then this object will contain a zero-length string."
    ::= { docsRphyRpdIfPhysEntityEntry 9 }

docsRphyRpdIfPhysEntitySoftwareRev    OBJECT-TYPE
    SYNTAX      SnmpAdminString
    MAX-ACCESS  read-only
    STATUS      current
    DESCRIPTION
        "The vendor-specific software revision string for the
         physical entity.

         Note that if revision information is stored internally in a
         non-printable (e.g., binary) format, then the agent must
         convert such information to a printable format in an
         implementation-specific manner.

         If no specific software programs are associated with the
         physical component, or if this information is unknown to the
         agent, then this object will contain a zero-length string."
    ::= { docsRphyRpdIfPhysEntityEntry 10 }

docsRphyRpdIfPhysEntitySerialNum   OBJECT-TYPE
    SYNTAX      SnmpAdminString (SIZE (0..32))
    MAX-ACCESS  read-only
    STATUS      current
    DESCRIPTION
        "The vendor-specific serial number string for the physical
         entity.  The preferred value is the serial number string
         actually printed on the component itself (if present).

         On the first instantiation of a physical entity, the value
         of docsRphyRpdIfPhysEntitySerialNum associated with that entity is set
         to the correct vendor-assigned serial number, if this
         information is available to the agent.  If a serial number
         is unknown or non-existent, the docsRphyRpdIfPhysEntitySerialNum will be
         set to a zero-length string instead.

         Note that implementations that can correctly identify the
         serial numbers of all installed physical entities do not
         need to provide write access to the docsRphyRpdIfPhysEntitySerialNum
         object.  Agents that cannot provide non-volatile storage
         for the docsRphyRpdIfPhysEntitySerialNum strings are not required to
         implement write access for this object.

         Not every physical component will have a serial number, or
         even need one.  Physical entities for which the associated
         value of the docsRphyRpdIfPhysEntityIsFRU object is equal to 'false(2)'
         (e.g., the repeater ports within a repeater module) do not
         need their own unique serial numbers.  An agent does not
         have to provide write access for such entities and may
         return a zero-length string.

         The CCAP Core should provide the unique component serial number, 
         via the SerialNum, contained for each FRU that is a pluggable optical
         module such as an SFP, SFP+, QSFP, XFP, CXP.

         The CCAP Core should provide the unique component serial number, 
         via the SerialNum, for every FRU that is capable of causing and/or 
         generating an event, message, log, or alarm."
    ::= { docsRphyRpdIfPhysEntityEntry 11 }

docsRphyRpdIfPhysEntityMfgName   OBJECT-TYPE
    SYNTAX      SnmpAdminString
    MAX-ACCESS  read-only
    STATUS      current
    DESCRIPTION
        "The name of the manufacturer of this physical component.
         The preferred value is the manufacturer name string actually
         printed on the component itself (if present).

         Note that comparisons between instances of the
         docsRphyRpdIfPhysEntityModelName, docsRphyRpdIfPhysEntityFirmwareRev,
         docsRphyRpdIfPhysEntitySoftwareRev, and the docsRphyRpdIfPhysEntitySerialNum
         objects are only meaningful amongst docsRphyRpdIfPhysEntityEntries with
         the same value of docsRphyRpdIfPhysEntityMfgName.

         If the manufacturer name string associated with the physical
         component is unknown to the agent, then this object will
         contain a zero-length string."
    ::= { docsRphyRpdIfPhysEntityEntry 12 }

docsRphyRpdIfPhysEntityModelName   OBJECT-TYPE
    SYNTAX      SnmpAdminString
    MAX-ACCESS  read-only
    STATUS      current
    DESCRIPTION
        "The vendor-specific model name identifier string associated
         with this physical component.  The preferred value is the
         customer-visible part number, which may be printed on the
         component itself.

         If the model name string associated with the physical
         component is unknown to the agent, then this object will
         contain a zero-length string."
    ::= { docsRphyRpdIfPhysEntityEntry 13 }

docsRphyRpdIfPhysEntityAlias    OBJECT-TYPE
    SYNTAX      SnmpAdminString (SIZE (0..32))
    MAX-ACCESS  read-only
    STATUS      current
    DESCRIPTION
        "This attribute reports an 'alias' name for the physical entity, as
         specified by a network manager, and provides a non-volatile
         'handle' for the physical entity.

         On the first instantiation of a physical entity, the value
         of docsRphyRpdIfPhysEntityAlias associated with that entity is set to
         the zero-length string.  However, the agent may set the
         value to a locally unique default value, instead of a
         zero-length string.

         For the RPD module Entity, the RPD must report the same value as the 
         'DeviceAlias'reported with GCP TLV 50.19.8."
    ::= { docsRphyRpdIfPhysEntityEntry 14 }

docsRphyRpdIfPhysEntityAssetID OBJECT-TYPE
    SYNTAX      SnmpAdminString (SIZE (0..32))
    MAX-ACCESS  read-only
    STATUS      current
    DESCRIPTION
        "This object is a user-assigned asset tracking identifier
         (as specified by a network manager) for the physical entity,
         and provides non-volatile storage of this information.
         
         If the AssetId string associated with the physical component
         is not set, then this attribute will report a zero-length string.
         
         For the RPD main module Entity, the RPD should report the 
         same value for attribute AssetId as the 'AssetId'
         attribute reported with GCP TLV 50.19.17.

         On the first instantiation of a physical entity, the value
         of AssetID associated with that entity is set to
         the zero-length string.

         Not every physical component will have an asset tracking
         identifier or even need one.  Physical entities for which
         the associated value of the IfPhysEntityIsFRU object is equal
         to 'false(2)' (e.g., the repeater ports within a repeater
         module) do not need their own unique asset tracking
         identifier.  An agent does not have to provide write access
         for such entities and may instead return a zero-length
         string.
         
         For the RPD main module Entity, the RPD must report the same 
         value for attribute AssetId as the 'AssetId' attribute reported 
         with GCP TLV 50.19.17."
    ::= { docsRphyRpdIfPhysEntityEntry 15 }

docsRphyRpdIfPhysEntityIsFRU OBJECT-TYPE
    SYNTAX      TruthValue
    MAX-ACCESS  read-only
    STATUS      current
    DESCRIPTION
        "This object indicates whether or not this physical entity
         is considered a 'field replaceable unit' by the vendor.
         If this object contains the value 'true(1)', then this
         docsRphyRpdIfPhysEntityEntry identifies a field replaceable unit.  For
         all docsRphyRpdIfPhysEntityEntries that represent components
         permanently contained within a field replaceable unit, the
         value 'false(2)' should be returned for this object."
    ::= { docsRphyRpdIfPhysEntityEntry 16 }

docsRphyRpdIfPhysEntityMfgDate  OBJECT-TYPE
    SYNTAX      DateAndTime
    MAX-ACCESS  read-only
    STATUS      current
    DESCRIPTION
        "This object contains the date of manufacturing of the
         managed entity.  If the manufacturing date is unknown or
         not supported, the object is not instantiated.  The special
         value '0000000000000000'H may also be returned in this
         case."
    ::= { docsRphyRpdIfPhysEntityEntry 17 }

docsRphyRpdIfPhysEntityUris OBJECT-TYPE
    SYNTAX      OCTET STRING
    MAX-ACCESS  read-only
    STATUS      current
    DESCRIPTION
        "This object contains identification
         information about the physical entity.  The object
         contains URIs; therefore, the syntax of this object
         must conform to RFC 3986, Section 3.

         Multiple URIs may be present and are separated by white
         space characters.  Leading and trailing white space
         characters are ignored.

         If no URI identification information is known
         about the physical entity, the object is not
         instantiated.  A zero-length octet string may also be
         returned in this case."
    REFERENCE 
        "Information Model Mapping: CM-SP-R-OSSI 
         Entity::Uris"
    ::= { docsRphyRpdIfPhysEntityEntry 18 }

docsRphyRpdIfPhysEntityUUID OBJECT-TYPE
    SYNTAX      UUIDorZero
    MAX-ACCESS  read-only
    STATUS      current
    DESCRIPTION
        "This attribute contains identification information 
         about the physical entity. The object contains a 
         Universally Unique Identifier; the syntax of this
         attribute, if UUID information is known, will usually
         conform to [RFC 4122], Section 4.1. An exception is
         that the syntax of  the UUID for the module entitity
         with attributes matching the same values as 
         RpdIdentification attributes does not conform to
         [RFC 4122], Section 4.1, but rather contains just
         the RPD unique ID in the last six bytes, with zeros
         in the other bytes. A zero-length octet string is
         returned if no UUID information is known."
    REFERENCE 
        "Information Model Mapping: CM-SP-R-OSSI 
         Entity::Uuid"
    ::= { docsRphyRpdIfPhysEntityEntry 19 }
    

    
-- ---------------------------------------------------------------------
-- RPD Entity Sensor Table extracted from RFC 3433 ENTITY-SENSOR-MIB
-- ---------------------------------------------------------------------

docsRphyRpdIfPhysEntSensorTable OBJECT-TYPE
    SYNTAX        SEQUENCE OF DocsRphyRpdIfPhysEntSensorEntry
    MAX-ACCESS    not-accessible
    STATUS        current
    DESCRIPTION
        "This table contains one row per physical sensor represented
         by an associated row in the docsRphyRpdIfPhysEntityTable.
         The CCAP Core reads the attributes of an RPD's Sensor object 
         with GCP complex TLV Type 100.7. "
    REFERENCE 
        "Information Model Mapping: CM-SP-R-OSSI 
         Sensor"
    ::= { docsRphyRpdIfMibObjects 2 }

docsRphyRpdIfPhysEntSensorEntry OBJECT-TYPE
    SYNTAX        DocsRphyRpdIfPhysEntSensorEntry
    MAX-ACCESS    not-accessible
    STATUS        current
    DESCRIPTION
        "Information about a particular physical sensor.

         An entry in this table describes the present reading of a
         sensor, the measurement units and scale, and sensor
         operational status.

         Entries are created in this table by the agent.  The CCAP 
         Core SHOULD create an entry for each physical sensor at 
         the same time as the associated Entity table instance. 
         The CCAP Core SHOULD delete an entry if the associated 
         Entity table entry is deleted."          
    INDEX  { docsRphyRpdDevInfoUniqueId,
      docsRphyRpdIfPhysEntityIndex }    
    ::= { docsRphyRpdIfPhysEntSensorTable 1 }

DocsRphyRpdIfPhysEntSensorEntry ::= SEQUENCE 
    {
    docsRphyRpdIfPhysEntSensorType            EntitySensorDataType,
    docsRphyRpdIfPhysEntSensorScale           EntitySensorDataScale,
    docsRphyRpdIfPhysEntSensorPrecision       EntitySensorPrecision,
    docsRphyRpdIfPhysEntSensorValue           EntitySensorValue,
    docsRphyRpdIfPhysEntSensorOperStatus      EntitySensorStatus,
    docsRphyRpdIfPhysEntSensorUnitsDisplay    SnmpAdminString,
    docsRphyRpdIfPhysEntSensorValueTimeStamp  TimeStamp,
    docsRphyRpdIfPhysEntSensorValueUpdateRate Unsigned32
    }

docsRphyRpdIfPhysEntSensorType OBJECT-TYPE
    SYNTAX        EntitySensorDataType
    MAX-ACCESS    read-only
    STATUS        current
    DESCRIPTION
        "This attribute reports the type of data returned by the 
         associated Value attribute.

         The CCAP Core SHOULD set the value during instance creation. 
         The CCAP Core SHOULD NOT change the value during operation."
    REFERENCE 
        "Information Model Mapping: CM-SP-R-OSSI 
         Sensor::SensorType"
    ::= { docsRphyRpdIfPhysEntSensorEntry 1 }

docsRphyRpdIfPhysEntSensorScale OBJECT-TYPE
    SYNTAX        EntitySensorDataScale
    MAX-ACCESS    read-only
    STATUS        current
    DESCRIPTION
        "This attribute reports a data scaling factor, represented 
         with an International System of Units (SI) prefix.  The 
         actual data units are determined by examining this attribute 
         together with the associated SensorType attribute.
         This attribute is defined together with SensorType and 
         Precision.  
         Together, these three attributes are used to identify the 
         semantics of the Value attribute."
    REFERENCE 
        "Information Model Mapping: CM-SP-R-OSSI 
         Sensor::Scale"
    ::= { docsRphyRpdIfPhysEntSensorEntry 2 }

docsRphyRpdIfPhysEntSensorPrecision OBJECT-TYPE
    SYNTAX        EntitySensorPrecision
    MAX-ACCESS    read-only
    STATUS        current
    DESCRIPTION
        "This attribute reports the number of decimal places of 
         precision in fixed-point sensor values returned by the 
         associated Value attribute.
         This attribute should be set to '0' when the associated 
         SensorType value is not a fixed-point type: e.g., 
         'percentRH(9)', 'rpm(10)', 'cmm(11)', or 'truthvalue(12)'."
    REFERENCE 
        "Information Model Mapping: CM-SP-R-OSSI 
         Sensor::Precision"
    ::= { docsRphyRpdIfPhysEntSensorEntry 3 }

docsRphyRpdIfPhysEntSensorValue OBJECT-TYPE
    SYNTAX        EntitySensorValue
    MAX-ACCESS    read-only
    STATUS        current
    DESCRIPTION
        "This attribute reports the most recent measurement obtained 
         by the RPD for this sensor.

         To correctly interpret the value of this object, the
         associated SensorType, SensorScale, and
         SensorPrecision attributes must also be examined."
    REFERENCE 
        "Information Model Mapping: CM-SP-R-OSSI 
         Sensor::Value"
    ::= { docsRphyRpdIfPhysEntSensorEntry 4 }

docsRphyRpdIfPhysEntSensorOperStatus OBJECT-TYPE
    SYNTAX        EntitySensorStatus
    MAX-ACCESS    read-only
    STATUS        current
    DESCRIPTION
        "The operational status of the sensor."
    REFERENCE 
        "Information Model Mapping: CM-SP-R-OSSI 
         Sensor::OperStatus"
    ::= { docsRphyRpdIfPhysEntSensorEntry 5 }

docsRphyRpdIfPhysEntSensorUnitsDisplay OBJECT-TYPE
    SYNTAX      SnmpAdminString
    MAX-ACCESS  read-only
    STATUS      current
    DESCRIPTION
        "A textual description of the data units that should be used
         in the display of SensorValue."
    REFERENCE 
        "Information Model Mapping: CM-SP-R-OSSI 
         Sensor::UnitsDisplay"
    ::= { docsRphyRpdIfPhysEntSensorEntry 6 }

docsRphyRpdIfPhysEntSensorValueTimeStamp OBJECT-TYPE
    SYNTAX        TimeStamp
    MAX-ACCESS    read-only
    STATUS        current
    DESCRIPTION
        "This attribute reports the value of RpdSysUpTime at the 
         time the status and/or value of this sensor was last 
         obtained by the RPD."
    REFERENCE 
        "Information Model Mapping: CM-SP-R-OSSI 
         Sensor::ValueTimeStamp"
    ::= { docsRphyRpdIfPhysEntSensorEntry 7 }

docsRphyRpdIfPhysEntSensorValueUpdateRate  OBJECT-TYPE
    SYNTAX        Unsigned32
    UNITS         "milliseconds"
    MAX-ACCESS    read-only
    STATUS        current
    DESCRIPTION
        "This attribute reports an indication of the frequency that 
         the CCAP Core updates the associated Value object, 
         represented in milliseconds.

         The value zero indicates:
            - the sensor value is updated on demand 
            - the sensor value is updated when the sensor
              value changes (event-driven)
            - the RPD does not know the update rate."
    REFERENCE 
        "Information Model Mapping: CM-SP-R-OSSI 
         Sensor::ValueUpdateRate"
    ::= { docsRphyRpdIfPhysEntSensorEntry 8 }
  
-- ---------------------------------------------------------------------
-- RPD Ethernet Interface Table Objects
-- ---------------------------------------------------------------------
docsRphyRpdIfEnetTable OBJECT-TYPE
    SYNTAX      SEQUENCE OF DocsRphyRpdIfEnetEntry
    MAX-ACCESS  not-accessible
    STATUS      current
    DESCRIPTION
        "This table provides details about the Ethernet interfaces 
         on the RPD. The attributes of this object are based on the 
         ifTable/ifXTable specified in RFC 2863.
         The CCAP Core must create a row in this table for 
         every Ethernet interface on the RPD.
         The CCAP Core reads the IfEnet object with GCP TLV 
         Type 100.8."
    REFERENCE 
        "Information Model Mapping: CM-SP-R-OSSI 
         IfEnet"
    ::= { docsRphyRpdIfMibObjects 3 }

docsRphyRpdIfEnetEntry OBJECT-TYPE
    SYNTAX      DocsRphyRpdIfEnetEntry
    MAX-ACCESS  not-accessible
    STATUS      current
    DESCRIPTION
        "An entry containing management information applicable to a
         particular interface.
         The Ethernet IfIndex is chosen by the RPD."
    INDEX   { docsRphyRpdDevInfoUniqueId,
              docsRphyRpdIfEnetPortIndex }
    ::= { docsRphyRpdIfEnetTable 1 }

DocsRphyRpdIfEnetEntry ::= SEQUENCE 
    {
    docsRphyRpdIfEnetPortIndex             Unsigned32,
    docsRphyRpdIfEnetDescr                 SnmpAdminString,
    docsRphyRpdIfEnetName                  SnmpAdminString,
    docsRphyRpdIfEnetAlias                 SnmpAdminString,
    docsRphyRpdIfEnetType                  IANAifType,
    docsRphyRpdIfEnetMtu                   Integer32,
    docsRphyRpdIfEnetPhysAddress           MacAddress,
    docsRphyRpdIfEnetAdminStatus           INTEGER,
    docsRphyRpdIfEnetOperStatus            INTEGER,
    docsRphyRpdIfEnetLastChange            TimeStamp,
    docsRphyRpdIfEnetLinkUpDownTrapEnable  TruthValue,
    docsRphyRpdIfEnetHighSpeed             Gauge32,
    docsRphyRpdIfEnetPromiscuousMode       TruthValue,
    docsRphyRpdIfEnetConnectorPresent      TruthValue,
    docsRphyRpdIfEnetNetworkAuthStatus     INTEGER
    }

docsRphyRpdIfEnetPortIndex OBJECT-TYPE
    SYNTAX      Unsigned32 (0..255)
    MAX-ACCESS  not-accessible
    STATUS      current
    DESCRIPTION
        "This key attribute reports a unique index for this 
         Ethernet port interface. This attribute is mapped to
         two RCP TLVs. TLV 87.2.1 is used when reading 
         NetworkAuthStatus (TLV 87.2.2) from the RPD. 
         In all other cases, this attribute maps to
         TLV 100.8.1."
    ::= { docsRphyRpdIfEnetEntry 1 }

docsRphyRpdIfEnetDescr OBJECT-TYPE
    SYNTAX      SnmpAdminString (SIZE (0..255))
    MAX-ACCESS  read-only
    STATUS      current
    DESCRIPTION
        "A textual string containing information about the
         interface.  This string should include the name of the
         manufacturer, the product name and the version of the
         interface hardware/software."
    ::= { docsRphyRpdIfEnetEntry 2 }
    
docsRphyRpdIfEnetName OBJECT-TYPE
    SYNTAX      SnmpAdminString
    MAX-ACCESS  read-only
    STATUS      current
    DESCRIPTION
        "This attribute reports a textual string representing a 
         name that describes the interface. The CCAP Core must 
         populate this object with the ID that is used in GCP for 
         this port."
    ::= { docsRphyRpdIfEnetEntry 3 }

docsRphyRpdIfEnetAlias   OBJECT-TYPE
    SYNTAX      SnmpAdminString (SIZE (0..64))
    MAX-ACCESS  read-only
    STATUS      current
    DESCRIPTION
        "This attribute reports an Alias for the interface. On the 
         first instantiation of an interface, the value of Alias 
         associated with that interface is the zero-length string. 
         As and when a value is written into an instance of Alias 
         through a network management operation, then the RPD 
         retains the supplied value in the Alias instance 
         associated with the same interface for as long as that 
         interface remains instantiated, including across all 
         re-initializations/reboots of the network management 
         system, including those which result in a change of the 
         interface's EnetPortIndex value."
    ::= { docsRphyRpdIfEnetEntry 4 }

docsRphyRpdIfEnetType OBJECT-TYPE
    SYNTAX      IANAifType
    MAX-ACCESS  read-only
    STATUS      current
    DESCRIPTION
        "This attribute reports the type of interface. Additional 
         values for Type are assigned by the Internet Assigned 
         Numbers Authority (IANA), through updating the syntax of 
         the IANAifType textual convention. The types are defined 
         in the IANAifType-MIB. The value reported by this 
         attribute is ethernetCsmacd."
    ::= { docsRphyRpdIfEnetEntry 5 }

docsRphyRpdIfEnetMtu OBJECT-TYPE
    SYNTAX      Integer32
    MAX-ACCESS  read-only
    STATUS      current
    DESCRIPTION
        "This attribute reports the size of the largest packet which 
         can be sent/received on the interface, specified in octets. 
         For interfaces that are used for transmitting network 
         datagrams, this is the size of the largest network datagram 
         that can be sent on the interface."
    ::= { docsRphyRpdIfEnetEntry 6 }

docsRphyRpdIfEnetPhysAddress OBJECT-TYPE
    SYNTAX      MacAddress
    MAX-ACCESS  read-only
    STATUS      current
    DESCRIPTION
        "This attribute reports the interface's address at its 
         protocol sub-layer. For example, for an 802.x interface, 
         this attribute normally contains a MAC address. The 
         interface's media-specific MIB defines the bit and byte 
         ordering and the format of the value of this attribute. 
         For interfaces which do not have such an address (e.g., a 
         serial line), this attribute reports an octet string of 
         zero length."
    ::= { docsRphyRpdIfEnetEntry 7 }

docsRphyRpdIfEnetAdminStatus OBJECT-TYPE
    SYNTAX      INTEGER {
                         up(1),       
                         down(2),
                         testing(3)   
                        }
    MAX-ACCESS  read-only
    STATUS      current
    DESCRIPTION
        "This attribute reports the state of the interface. The 
         testing(3) state indicates that no operational packets can
         be passed. When a managed system initializes, all 
         interfaces start with AdminStatus in the down(2) state. 
         As a result of either explicit management action or per 
         configuration information retained by the managed system, 
         AdminStatus is then changed to either the up(1) or 
         testing(3) states (or remains in the down(2) state)."
    ::= { docsRphyRpdIfEnetEntry 8 }

docsRphyRpdIfEnetOperStatus OBJECT-TYPE
    SYNTAX      INTEGER {
                         up(1),        
                         down(2),
                         testing(3),  
                         unknown(4),   
                         dormant(5),
                         notPresent(6),    
                         lowerLayerDown(7) 
                        }
    MAX-ACCESS  read-only
    STATUS      current
    DESCRIPTION
        "This attribute reports the current operational state of 
         the interface. The testing(3) state indicates that no 
         operational packets can be passed.  If AdminStatus is 
         down(2) then ifOperStatus should be down(2).  If 
         AdminStatus is changed to up(1), then OperStatus should 
         change to up(1) if the interface is ready to transmit and 
         receive network traffic; it should change to dormant(5) if 
         the interface is waiting for external actions (such as a 
         serial line waiting for an incoming connection); it should 
         remain in the down(2) state if and only if there is a fault 
         that prevents it from going to the up(1) state; it should 
         remain in the notPresent(6) state if the interface has 
         missing (typically, hardware) components."
    ::= { docsRphyRpdIfEnetEntry 9 }

docsRphyRpdIfEnetLastChange OBJECT-TYPE
    SYNTAX      TimeStamp
    MAX-ACCESS  read-only
    STATUS      current
    DESCRIPTION
        "This attribute reports the value of RpdSysUpTime at the 
         time the interface entered its current operational state.  
         If the current state was entered prior to the last 
         re-initialization of the local network management 
         subsystem, then this attribute reports a zero value."
    ::= { docsRphyRpdIfEnetEntry 10 }

docsRphyRpdIfEnetLinkUpDownTrapEnable  OBJECT-TYPE
    SYNTAX      TruthValue
    MAX-ACCESS  read-only
    STATUS      current
    DESCRIPTION
        "This attribute reports whether linkup/linkdown traps are 
         generated for this interface.
         A value of true indicates that traps are enabled.
         A value of false indicates that traps are disabled."
    ::= { docsRphyRpdIfEnetEntry 11 }

docsRphyRpdIfEnetHighSpeed OBJECT-TYPE
    SYNTAX      Gauge32
    MAX-ACCESS  read-only
    STATUS      current
    DESCRIPTION
        "This attribute reports an estimate of the interface's 
         current bandwidth in units of 1,000,000 bits per second.  
         If this attribute reports a value of 'n' then the speed of 
         the interface is somewhere in the range of 'n-500,000' to 
         'n+499,999'.  For interfaces which do not vary in bandwidth 
         or for those where no accurate estimation can be made, this 
         attribute reports the nominal bandwidth."
    ::= { docsRphyRpdIfEnetEntry 12 }

docsRphyRpdIfEnetPromiscuousMode  OBJECT-TYPE
    SYNTAX      TruthValue
    MAX-ACCESS  read-only
    STATUS      current
    DESCRIPTION
        "This attribute reports a value of '2' (false) if this 
         interface only accepts packets/frames that are addressed 
         to this interface.
         This attribute reports a value of '1' (true) when the 
         station accepts all packets/frames transmitted on the media.  
         The value of PromiscuousMode does not affect the reception 
         of broadcast and multicast packets/frames by the interface."
    ::= { docsRphyRpdIfEnetEntry 13 }

docsRphyRpdIfEnetConnectorPresent   OBJECT-TYPE
    SYNTAX      TruthValue
    MAX-ACCESS  read-only
    STATUS      current
    DESCRIPTION
        "This attribute reports the value 'true' if the interface 
         sublayer has a physical connector and the value 'false' 
         otherwise."
    ::= { docsRphyRpdIfEnetEntry 14 }

docsRphyRpdIfEnetNetworkAuthStatus OBJECT-TYPE
    SYNTAX      INTEGER {
                         other(0),
                         waitForEapReq(1),       
                         execute802dot1x(2),
                         sleepAfterFailure(3),
                         operationalAuthenticated(4),
                         operationalNotAuthenticated(5)
                        }
    MAX-ACCESS  read-only
    STATUS      current
    DESCRIPTION
        "This attribute reports the network authentication 
         status of this interface.
         
         other: The interface is in a state not listed below.

         waitForEapReq: The interface is waiting for a reply
         to its EAP request.

         execute8021x:  The interface is in the process of 
         completing 802.1x network authentication.

         sleepAfterFailure: 802.1x authentication failed on 
         this interface and the interface is down.

         operationalAuthenticated: The interface is operational
         and authenticated to the network.

         operationalNotAuthenticated:  The interface is operational, 
         but not authenticated to the network 
         (i.e., 802.1x was not required on the network)."

    ::= { docsRphyRpdIfEnetEntry 15 }

    
-- ---------------------------------------------------------------------
-- RPD Ethernet Interface Stats Table Objects 
-- ---------------------------------------------------------------------
docsRphyRpdIfEnetStatsTable        OBJECT-TYPE
    SYNTAX      SEQUENCE OF DocsRphyRpdIfEnetStatsEntry
    MAX-ACCESS  not-accessible
    STATUS      current
    DESCRIPTION
        "This table reports statistics for the Ethernet interfaces 
         on the RPD. The attributes of this table are based on the 
         ifTable/ifXTable specified in RFC 2863. The CCAP Core must 
         create an entry in this table for every row in the IfEnet table.

         Discontinuities in the value of these counters can occur at 
         reinitialization of the managed system, and at other times as 
         indicated by the value of CounterDiscontinuityTime.
         The CCAP Core reads the attributes of an IfEnetStats 
         object with the complex TLV Type 100.9."
    REFERENCE 
        "Information Model Mapping: CM-SP-R-OSSI 
         IfEnetStats"
    ::= { docsRphyRpdIfMibObjects 4 }

docsRphyRpdIfEnetStatsEntry        OBJECT-TYPE
    SYNTAX      DocsRphyRpdIfEnetStatsEntry
    MAX-ACCESS  not-accessible
    STATUS      current
    DESCRIPTION
        "An entry containing statistical information
         applicable to a particular RPD ethernet interface."
    AUGMENTS    { docsRphyRpdIfEnetEntry }
    ::= { docsRphyRpdIfEnetStatsTable 1 }

DocsRphyRpdIfEnetStatsEntry ::= SEQUENCE 
    {
    docsRphyRpdIfEnetStatsInOctets                 Counter64,
    docsRphyRpdIfEnetStatsOutOctets                Counter64,
    docsRphyRpdIfEnetStatsInFrames                 Counter64,
    docsRphyRpdIfEnetStatsOutFrames                Counter64,
    docsRphyRpdIfEnetStatsInUnicastOctets          Counter64,
    docsRphyRpdIfEnetStatsOutUnicastOctets         Counter64,
    docsRphyRpdIfEnetStatsInUnicastFrames          Counter64,
    docsRphyRpdIfEnetStatsOutUnicastFrames         Counter64,
    docsRphyRpdIfEnetStatsInMulticastOctets        Counter64,
    docsRphyRpdIfEnetStatsOutMulticastOctets       Counter64,
    docsRphyRpdIfEnetStatsInMulticastFrames        Counter64,
    docsRphyRpdIfEnetStatsOutMulticastFrames       Counter64,
    docsRphyRpdIfEnetStatsInBroadcastOctets        Counter64,
    docsRphyRpdIfEnetStatsOutBroadcastOctets       Counter64,
    docsRphyRpdIfEnetStatsInBroadcastFrames        Counter64,
    docsRphyRpdIfEnetStatsOutBroadcastFrames       Counter64,
    docsRphyRpdIfEnetStatsInDiscards               Counter64,
    docsRphyRpdIfEnetStatsOutDiscards              Counter64,
    docsRphyRpdIfEnetStatsInErrors                 Counter64,
    docsRphyRpdIfEnetStatsOutErrors                Counter64,
    docsRphyRpdIfEnetStatsInUnknownProtos          Counter64,
    docsRphyRpdIfEnetStatsCounterDiscontinuityTime DateAndTime
    }

docsRphyRpdIfEnetStatsInOctets OBJECT-TYPE
    SYNTAX      Counter64
    MAX-ACCESS  read-only
    STATUS      current
    DESCRIPTION
        "The total number of octets received on the interface,
         including framing characters."
    ::= { docsRphyRpdIfEnetStatsEntry 1 }
    
docsRphyRpdIfEnetStatsOutOctets OBJECT-TYPE
    SYNTAX      Counter64
    MAX-ACCESS  read-only
    STATUS      current
    DESCRIPTION
        "The total number of octets transmitted out of the
         interface, including framing characters."
    ::= { docsRphyRpdIfEnetStatsEntry 2 }
    
docsRphyRpdIfEnetStatsInFrames OBJECT-TYPE
    SYNTAX      Counter64
    MAX-ACCESS  read-only
    STATUS      current
    DESCRIPTION
        "The total number of frames received on the interface,
         including framing characters."
    ::= { docsRphyRpdIfEnetStatsEntry 3 }
    
docsRphyRpdIfEnetStatsOutFrames OBJECT-TYPE
    SYNTAX      Counter64
    MAX-ACCESS  read-only
    STATUS      current
    DESCRIPTION
        "The total number of frames transmitted out of the
         interface, including framing characters."
    ::= { docsRphyRpdIfEnetStatsEntry 4 }
    
docsRphyRpdIfEnetStatsInUnicastOctets OBJECT-TYPE
    SYNTAX      Counter64
    MAX-ACCESS  read-only
    STATUS      deprecated
    DESCRIPTION
        "The number of octets, delivered by this sub-layer to a
         higher (sub-)layer, which were not addressed to a multicast
         or broadcast address at this sub-layer."
    ::= { docsRphyRpdIfEnetStatsEntry 5 }
   
docsRphyRpdIfEnetStatsOutUnicastOctets OBJECT-TYPE
    SYNTAX      Counter64
    MAX-ACCESS  read-only
    STATUS      deprecated
    DESCRIPTION
        "The total number of octets that higher-level protocols
         requested be transmitted, and which were not addressed to a
         multicast or broadcast address at this sub-layer, including
         those that were discarded or not sent."
    ::= { docsRphyRpdIfEnetStatsEntry 6 }
     
docsRphyRpdIfEnetStatsInUnicastFrames OBJECT-TYPE
    SYNTAX      Counter64
    MAX-ACCESS  read-only
    STATUS      current
    DESCRIPTION
        "The number of frames, delivered by this sub-layer to a
         higher (sub-)layer, which were not addressed to a multicast
         or broadcast address at this sub-layer."
    ::= { docsRphyRpdIfEnetStatsEntry 7 }
    
docsRphyRpdIfEnetStatsOutUnicastFrames OBJECT-TYPE
    SYNTAX      Counter64
    MAX-ACCESS  read-only
    STATUS      current
    DESCRIPTION
        "The total number of frames that higher-level protocols
         requested be transmitted, and which were not addressed to a
         multicast or broadcast address at this sub-layer, including
         those that were discarded or not sent."
    ::= { docsRphyRpdIfEnetStatsEntry 8 }
    
docsRphyRpdIfEnetStatsInMulticastOctets OBJECT-TYPE
    SYNTAX      Counter64
    MAX-ACCESS  read-only
    STATUS      deprecated
    DESCRIPTION
        "The number of octets, delivered by this sub-layer to a
         higher (sub-)layer, which were addressed to a multicast
         address at this sub-layer.  For a MAC layer protocol, this
         includes both Group and Functional addresses."
    ::= { docsRphyRpdIfEnetStatsEntry 9 }
    
docsRphyRpdIfEnetStatsOutMulticastOctets OBJECT-TYPE
    SYNTAX      Counter64
    MAX-ACCESS  read-only
    STATUS      deprecated
    DESCRIPTION
        "The total number of octets that higher-level protocols
         requested be transmitted, and which were addressed to a
         multicast address at this sub-layer, including those that
         were discarded or not sent.  For a MAC layer protocol, this
         includes both Group and Functional addresses."
    ::= { docsRphyRpdIfEnetStatsEntry 10 }
    
docsRphyRpdIfEnetStatsInMulticastFrames OBJECT-TYPE
    SYNTAX      Counter64
    MAX-ACCESS  read-only
    STATUS      current
    DESCRIPTION
        "The number of frames, delivered by this sub-layer to a
         higher (sub-)layer, which were addressed to a multicast
         address at this sub-layer.  For a MAC layer protocol, this
         includes both Group and Functional addresses."
    ::= { docsRphyRpdIfEnetStatsEntry 11 }

docsRphyRpdIfEnetStatsOutMulticastFrames OBJECT-TYPE
    SYNTAX      Counter64
    MAX-ACCESS  read-only
    STATUS      current
    DESCRIPTION
        "The total number of frames that higher-level protocols
         requested be transmitted, and which were addressed to a
         multicast address at this sub-layer, including those that
         were discarded or not sent.  For a MAC layer protocol, this
         includes both Group and Functional addresses."
    ::= { docsRphyRpdIfEnetStatsEntry 12 }
    
docsRphyRpdIfEnetStatsInBroadcastOctets OBJECT-TYPE
    SYNTAX      Counter64
    MAX-ACCESS  read-only
    STATUS      deprecated
    DESCRIPTION
        "The number of octets, delivered by this sub-layer to a
         higher (sub-)layer, which were addressed to a broadcast
         address at this sub-layer."
    ::= { docsRphyRpdIfEnetStatsEntry 13 }

docsRphyRpdIfEnetStatsOutBroadcastOctets OBJECT-TYPE
    SYNTAX      Counter64
    MAX-ACCESS  read-only
    STATUS      deprecated
    DESCRIPTION
        "The total number of octets that higher-level protocols
         requested be transmitted, and which were addressed to a
         broadcast address at this sub-layer, including those that
         were discarded or not sent."
    ::= { docsRphyRpdIfEnetStatsEntry 14 }

docsRphyRpdIfEnetStatsInBroadcastFrames OBJECT-TYPE
    SYNTAX      Counter64
    MAX-ACCESS  read-only
    STATUS      current
    DESCRIPTION
        "The number of frames, delivered by this sub-layer to a
         higher (sub-)layer, which were addressed to a broadcast
         address at this sub-layer."
    ::= { docsRphyRpdIfEnetStatsEntry 15 }

docsRphyRpdIfEnetStatsOutBroadcastFrames OBJECT-TYPE
    SYNTAX      Counter64
    MAX-ACCESS  read-only
    STATUS      current
    DESCRIPTION
        "The total number of frames that higher-level protocols
         requested be transmitted, and which were addressed to a
         broadcast address at this sub-layer, including those that
         were discarded or not sent."
    ::= { docsRphyRpdIfEnetStatsEntry 16 }

docsRphyRpdIfEnetStatsInDiscards OBJECT-TYPE
    SYNTAX      Counter64
    MAX-ACCESS  read-only
    STATUS      current
    DESCRIPTION
        "The number of inbound packets which were chosen to be
         discarded even though no errors had been detected to prevent
         their being deliverable to a higher-layer protocol.  One
         possible reason for discarding such a packet could be to
         free up buffer space."
    ::= { docsRphyRpdIfEnetStatsEntry 17 }

docsRphyRpdIfEnetStatsOutDiscards OBJECT-TYPE
    SYNTAX      Counter64
    MAX-ACCESS  read-only
    STATUS      current
    DESCRIPTION
        "The number of outbound packets which were chosen to be
         discarded even though no errors had been detected to prevent
         their being transmitted.  One possible reason for discarding
         such a packet could be to free up buffer space."
    ::= { docsRphyRpdIfEnetStatsEntry 18 }
    
docsRphyRpdIfEnetStatsInErrors OBJECT-TYPE
    SYNTAX      Counter64
    MAX-ACCESS  read-only
    STATUS      current
    DESCRIPTION
        "For packet-oriented interfaces, the number of inbound
         packets that contained errors preventing them from being
         deliverable to a higher-layer protocol.  For character-
         oriented or fixed-length interfaces, the number of inbound
         transmission units that contained errors preventing them
         from being deliverable to a higher-layer protocol."
    ::= { docsRphyRpdIfEnetStatsEntry 19 }

docsRphyRpdIfEnetStatsOutErrors OBJECT-TYPE
    SYNTAX      Counter64
    MAX-ACCESS  read-only
    STATUS      current
    DESCRIPTION
        "For packet-oriented interfaces, the number of outbound
         packets that could not be transmitted because of errors.
         For character-oriented or fixed-length interfaces, the
         number of outbound transmission units that could not be
         transmitted because of errors."
    ::= { docsRphyRpdIfEnetStatsEntry 20 }
    
docsRphyRpdIfEnetStatsInUnknownProtos OBJECT-TYPE
    SYNTAX      Counter64
    MAX-ACCESS  read-only
    STATUS      current
    DESCRIPTION
        "For packet-oriented interfaces, the number of packets
         received via the interface which were discarded because of
         an unknown or unsupported protocol.  For character-oriented
         or fixed-length interfaces that support protocol
         multiplexing the number of transmission units received via
         the interface which were discarded because of an unknown or
         unsupported protocol.  For any interface that does not
         support protocol multiplexing, this counter will always be
         0."
    ::= { docsRphyRpdIfEnetStatsEntry 21 }

docsRphyRpdIfEnetStatsCounterDiscontinuityTime OBJECT-TYPE
    SYNTAX      DateAndTime
    MAX-ACCESS  read-only
    STATUS      current
    DESCRIPTION
        "This attribute reports the date and time at which any 
         one or more of the counters in this group were created or 
         last reset to zero. If the RPD does not acquire time of day 
         it can report an initial CounterDiscontinuityTime of Jan 1 1970. 
         If the value returned by the RPD is the initial Epoch of Jan 1 1970, 
         the CCAP Core can convert this value to the real time of day based 
         on a calculation using the RPD's reported sysUpTime."
    ::= { docsRphyRpdIfEnetStatsEntry 22 }
    
-- ---------------------------------------------------------------------
-- RPD Ethernet Interface to CCAP Core Entity Map Table Objects 
-- ---------------------------------------------------------------------
docsRphyRpdIfRpdEnetToCoreEntityMapTable        OBJECT-TYPE
    SYNTAX      SEQUENCE OF DocsRphyRpdIfRpdEnetToCoreEntityMapEntry
    MAX-ACCESS  not-accessible
    STATUS      current
    DESCRIPTION
        "If the RPD implements an Entity for an Ethernet port 
         (which is optional), this table provides the mapping 
         between the RPD's EnetPortIndex as signaled in GCP and 
         the corresponding docsRphyRpdIfPhysEntityIndex assigned
         by the CCAP Core to report that entity.
         The CCAP Core reads RpdEnetToCoreEntityMap attributes with    
          complex GCP TLV Type 100.10."
     REFERENCE    
        "Information Model Mapping: CM-SP-R-OSSI    
         RpdEnetToCoreEntityMap"
    ::= { docsRphyRpdIfMibObjects 5 }

docsRphyRpdIfRpdEnetToCoreEntityMapEntry        OBJECT-TYPE
    SYNTAX      DocsRphyRpdIfRpdEnetToCoreEntityMapEntry
    MAX-ACCESS  not-accessible
    STATUS      current
    DESCRIPTION
        "An entry in docsRphyRpdIfRpdEnetToCoreEntityMapTable."
    INDEX    { docsRphyRpdDevInfoUniqueId,
        docsRphyRpdIfEnetPortIndex }
    ::= { docsRphyRpdIfRpdEnetToCoreEntityMapTable 1 }

DocsRphyRpdIfRpdEnetToCoreEntityMapEntry ::= SEQUENCE 
    {
    docsRphyRpdIfRpdEnetToCoreEntityMapEntityIndex           Unsigned32
    }

docsRphyRpdIfRpdEnetToCoreEntityMapEntityIndex OBJECT-TYPE
    SYNTAX      Unsigned32
    MAX-ACCESS  read-only
    STATUS      current
    DESCRIPTION
        "The value of this attribute matches the value of the 
         EntityIndex for the instance of Entity that reports the 
         RPD Ethernet port signaled in GCP with EnetPortIndex."
    REFERENCE    
        "Information Model Mapping: CM-SP-R-OSSI    
         RpdEnetToCoreEntityMap::EntityIndex"
    ::= { docsRphyRpdIfRpdEnetToCoreEntityMapEntry 1 }
    
-- ---------------------------------------------------------------------
-- CCAP Core ifTable Interface to RPD Interface Map Table Objects 
-- ---------------------------------------------------------------------
docsRphyRpdIfCoreToRpdMapTable        OBJECT-TYPE
    SYNTAX      SEQUENCE OF DocsRphyRpdIfCoreToRpdMapEntry
    MAX-ACCESS  not-accessible
    STATUS      current
    DESCRIPTION
        "This table maps certain CCAP Core ifTable interfaces 
         identified with an ifIndex to an RPD interface identified 
         in GCP.
         See the reference for additional requirements."
    REFERENCE    
        "Information Model Mapping: CM-SP-R-OSSI    
         CoreToRpdMap"
    ::= { docsRphyRpdIfMibObjects 6 }

docsRphyRpdIfCoreToRpdMapEntry        OBJECT-TYPE
    SYNTAX      DocsRphyRpdIfCoreToRpdMapEntry
    MAX-ACCESS  not-accessible
    STATUS      current
    DESCRIPTION
        "An entry in docsRphyRpdIfCoreToRpdMapTable.
         An entry exists for each RPD interface directly represented 
         in the CCAP ifTable. The IfIndex corresponds to 
         a CCAP Core ifIndex for one of the following interface 
         types implemented on an RPD:

         - docsCableDownstream(128)
         - docsCableUpstreamChannel(205)
         - docsCableUpstreamRfPort(256)
         - cableDownstreamRfPort(257)
         - docsCableDownstreamOfdm(277)
         - docsCableUpstreamOfdma(278)
         - mpegTransport(214)
         - docsCableScte55d1FwdOob (283) 
         - docsCableScte55d1RetOob (284) 
         - docsCableScte55d2DsOob (285) 
         - docsCableScte55d2UsOob (286) 
         - docsCableNdf (287) 
         - docsCableNdr (288) 

         Note that this table does not contain an instance for 
         ifType ethernetCsmacd(6) because the Ethernet ports of 
         the RPD are considered internal to a logical CCAP and 
         are not reported in the CCAP ifTable."
    INDEX    { docsRphyRpdIfCoreToRpdMapRpdCoreIndex, docsRphyRpdIfCoreToRpdMapRpdUniqueId,
        docsRphyRpdIfCoreToRpdMapRpdRfPortDirection, docsRphyRpdIfCoreToRpdMapRpdRfPortIndex}
    ::= { docsRphyRpdIfCoreToRpdMapTable 1 }

DocsRphyRpdIfCoreToRpdMapEntry ::= SEQUENCE   
    {
    docsRphyRpdIfCoreToRpdMapRpdCoreIndex          InterfaceIndex,
    docsRphyRpdIfCoreToRpdMapRpdUniqueId           MacAddress,
    docsRphyRpdIfCoreToRpdMapRpdRfPortDirection    IfDirection,
    docsRphyRpdIfCoreToRpdMapRpdRfPortIndex        Unsigned32,
    docsRphyRpdIfCoreToRpdMapRpdRfChanType         RphyChannelType,
    docsRphyRpdIfCoreToRpdMapRpdRfChanIndex        Unsigned32
    }
    
docsRphyRpdIfCoreToRpdMapRpdCoreIndex OBJECT-TYPE
    SYNTAX      InterfaceIndex
    MAX-ACCESS  not-accessible
    STATUS      current
    DESCRIPTION
        "This key attribute selects the CCAP 
         Core IfIndex for the RPD Interface identified in GCP."
    REFERENCE    
        "Information Model Mapping: CM-SP-R-OSSI    
         CoreToRpdMap::CoreIfIndex"
    ::= { docsRphyRpdIfCoreToRpdMapEntry 1 }

docsRphyRpdIfCoreToRpdMapRpdUniqueId OBJECT-TYPE
    SYNTAX      MacAddress
    MAX-ACCESS  not-accessible
    STATUS      current
    DESCRIPTION
        "This key attribute is the MAC address 
         selecting a particular CIN facing Ethernet port. The value 
         of this attribute matches the value of the RpdUniqueId 
         attribute of the RpdInfo object."
    REFERENCE    
        "Information Model Mapping: CM-SP-R-OSSI    
         CoreToRpdMap::RpdUniqueId"
    ::= { docsRphyRpdIfCoreToRpdMapEntry 2 }
    
docsRphyRpdIfCoreToRpdMapRpdRfPortDirection OBJECT-TYPE
    SYNTAX      IfDirection
    MAX-ACCESS  not-accessible
    STATUS      current
    DESCRIPTION
        "This key attribute selects the direction of an RF port, 
         which together with RpdRfPortIndex uniquely identifies 
         an RF port on the RPD. The RF port direction is signaled 
         in the GCP RfPortType TLV 13.2 for an RF port interface or 
         implied by the value of the GCP RfChannelType 
         TLV 12.2 for an RF channel interface."
    REFERENCE    
        "Information Model Mapping: CM-SP-R-OSSI    
         CoreToRpdMap::RpdRfPortDirection"
    ::= { docsRphyRpdIfCoreToRpdMapEntry 3 }
    
docsRphyRpdIfCoreToRpdMapRpdRfPortIndex OBJECT-TYPE
    SYNTAX      Unsigned32 (0..253)
    MAX-ACCESS  not-accessible
    STATUS      current
    DESCRIPTION
        "This key attribute selects a specific RF port on an RPD, 
         which together with RpdRfPortDirection uniquely 
         identifies an RF port on the RPD. The value matches the 
         value signaled in GCP RfPortIndex TLV 12.1 or the GCP 
         RfPortIndex1 TLV 13.1. Values 254 and 255 are 
         reserved for future use."
    REFERENCE    
        "Information Model Mapping: CM-SP-R-OSSI    
         CoreToRpdMap::RpdRfPortIndex"
    ::= { docsRphyRpdIfCoreToRpdMapEntry 4 }
    
docsRphyRpdIfCoreToRpdMapRpdRfChanType OBJECT-TYPE
    SYNTAX      RphyChannelType
    MAX-ACCESS  read-only
    STATUS      current
    DESCRIPTION
        "For RF channel interfaces, This attribute reports the type 
         of the channel as signaled in the GCP RfChannelType 
         TLV 12.2. For RF port interfaces, this attribute must be 
         set to other(0). Each value of this attribute corresponds 
         to a separate sequence of channel indices."
    REFERENCE    
        "Information Model Mapping: CM-SP-R-OSSI    
         CoreToRpdMap::RpdRfChannelType"
    ::= { docsRphyRpdIfCoreToRpdMapEntry 5 }
    
docsRphyRpdIfCoreToRpdMapRpdRfChanIndex OBJECT-TYPE
    SYNTAX      Unsigned32 (0..255)
    MAX-ACCESS  read-only
    STATUS      current
    DESCRIPTION
        "For interfaces corresponding to RF channels, this attribute 
         reports the channel of the type specified in 
         RpdRfChannelType, and matches the value signaled in the GCP 
         RfChannelIndex TLV 12.3. For RF port interfaces, this 
         attribute reports 0."
    REFERENCE    
        "Information Model Mapping: CM-SP-R-OSSI    
         CoreToRpdMap::RpdRfChannelIndex"
    ::= { docsRphyRpdIfCoreToRpdMapEntry 6 }
    
-- ---------------------------------------------------------------------
-- RPD Interface to CCAP Core ifTable Interface Map Table Objects 
-- ---------------------------------------------------------------------
docsRphyRpdIfRpdToCoreMapTable        OBJECT-TYPE
    SYNTAX      SEQUENCE OF DocsRphyRpdIfRpdToCoreMapEntry
    MAX-ACCESS  not-accessible
    STATUS      current
    DESCRIPTION
        "This table maps certain RPD interface identified via GCP 
         integers to an ifIndex reported by the CCAP Core. This 
         table instruments the same information as the 
         docsRphyRpdIfCoreToRpdMapTable, but with different indexing 
         than that table.
         See the reference for additional requirements."
    REFERENCE    
        "Information Model Mapping: CM-SP-R-OSSI    
         RpdToCoreMap"
    ::= { docsRphyRpdIfMibObjects 7 }

docsRphyRpdIfRpdToCoreMapEntry        OBJECT-TYPE
    SYNTAX      DocsRphyRpdIfRpdToCoreMapEntry
    MAX-ACCESS  not-accessible
    STATUS      current
    DESCRIPTION
        "An entry in docsRphyRpdIfRpdToCoreMapTable.
         An entry exists for each RPD interface directly represented 
         in the CCAP ifTable. The index 'CoreIfIndex' corresponds to 
         a CCAP core ifIndex for one of the following interface 
         types implemented on an RPD:

         - docsCableDownstream(128)
         - docsCableUpstreamChannel(205)
         - docsCableUpstreamRfPort(256)
         - cableDownstreamRfPort(257)
         - docsCableDownstreamOfdm(277)
         - docsCableUpstreamOfdma(278)
         - mpegTransport(214)
         - docsCableScte55d1FwdOob (283) 
         - docsCableScte55d1RetOob (284) 
         - docsCableScte55d2DsOob (285) 
         - docsCableScte55d2UsOob (286) 
         - docsCableNdf (287) 
         - docsCableNdr (288) 

         Note that this table does not contain an instance for 
         ifType ethernetCsmacd(6) because the Ethernet ports of 
         the RPD are considered internal to a logical CCAP and 
         are not reported in the CCAP ifTable."
    INDEX    { docsRphyRpdDevInfoUniqueId,
               docsRphyRpdIfRpdToCoreMapRpdRfPortDirection,
               docsRphyRpdIfRpdToCoreMapRpdRfPortIndex,
               docsRphyRpdIfRpdToCoreMapRpdRfChanType,
               docsRphyRpdIfRpdToCoreMapRpdRfChanIndex }
    ::= { docsRphyRpdIfRpdToCoreMapTable 1 }

DocsRphyRpdIfRpdToCoreMapEntry ::= SEQUENCE 
    {
    docsRphyRpdIfRpdToCoreMapRpdRfPortDirection    IfDirection,
    docsRphyRpdIfRpdToCoreMapRpdRfPortIndex        Unsigned32,
    docsRphyRpdIfRpdToCoreMapRpdRfChanType         RphyChannelType,
    docsRphyRpdIfRpdToCoreMapRpdRfChanIndex        Unsigned32,
    docsRphyRpdIfRpdToCoreMapCoreIfIndex           InterfaceIndex
    }
    
docsRphyRpdIfRpdToCoreMapRpdRfPortDirection OBJECT-TYPE
    SYNTAX      IfDirection
    MAX-ACCESS  not-accessible
    STATUS      current
    DESCRIPTION
        "This attribute reports the direction of an RF port, which 
         together with RpdRfPortIndex uniquely identifies an RF 
         port on the RPD. The RF port direction is signalled in the 
         GCP 'RfPortType' TLV 13.2 for an RF port interface or 
         implied by the value of the GCP 'RfChannelType' TLV 12.2 
         for an RF channel interface."
    REFERENCE    
        "Information Model Mapping: CM-SP-R-OSSI    
         RpdToCoreMap::RpdRfPortDirection"
    ::= { docsRphyRpdIfRpdToCoreMapEntry 1 }
    
docsRphyRpdIfRpdToCoreMapRpdRfPortIndex OBJECT-TYPE
    SYNTAX      Unsigned32 (0..255)
    MAX-ACCESS  not-accessible
    STATUS      current
    DESCRIPTION
        "This attribute reports the Index of an RF port on an RPD, 
         which together with RpdRfPortDirection uniquely 
         identifies an RF port on the RPD. The value matches the 
         value signaled in GCP 'RfPortIndex' TLV 12.1 or the GCP 
         'RfPortIndex1' TLV 13.1."
    REFERENCE    
        "Information Model Mapping: CM-SP-R-OSSI    
         RpdToCoreMap::RpdRfPortIndex"
    ::= { docsRphyRpdIfRpdToCoreMapEntry 2 }
    
docsRphyRpdIfRpdToCoreMapRpdRfChanType OBJECT-TYPE
    SYNTAX      RphyChannelType
    MAX-ACCESS  not-accessible
    STATUS      current
    DESCRIPTION
        "For RF channel interfaces, This attribute reports the type 
         of the channel as signaled in the GCP 'RfChannelType' 
         TLV 12.2. For RF port interfaces, this attribute must be 
         set to other(0). Each value of this attribute corresponds 
         to a separate sequence of channel indices."
    REFERENCE    
        "Information Model Mapping: CM-SP-R-OSSI    
         RpdToCoreMap::RpdRfChannelType"
    ::= { docsRphyRpdIfRpdToCoreMapEntry 3 }
    
docsRphyRpdIfRpdToCoreMapRpdRfChanIndex OBJECT-TYPE
    SYNTAX      Unsigned32 (0..255)
    MAX-ACCESS  not-accessible
    STATUS      current
    DESCRIPTION
        "For interfaces corresponding to RF channels, this attribute 
         reports the channel of the type specified in 
         RpdRfChannelType, and matches the value signaled in the GCP 
         'RfChannelIndex' TLV 12.3. For RF port interfaces, this 
         attribute reports 0."
    REFERENCE    
        "Information Model Mapping: CM-SP-R-OSSI    
         RpdToCoreMap::RpdRfChannelIndex"
    ::= { docsRphyRpdIfRpdToCoreMapEntry 4 }
    
docsRphyRpdIfRpdToCoreMapCoreIfIndex OBJECT-TYPE
    SYNTAX      InterfaceIndex
    MAX-ACCESS  read-only
    STATUS      current
    DESCRIPTION
        "This key attribute reports the CCAP Core IfIndex for the 
         RPD Interface identified in GCP."
    REFERENCE    
        "Information Model Mapping: CM-SP-R-OSSI    
         RpdToCoreMap::CoreIfIndex"
    ::= { docsRphyRpdIfRpdToCoreMapEntry 5 }

-- ---------------------------------------------------------------------
-- RPD Ethernet Interface SFP+ Status
-- ---------------------------------------------------------------------
docsRphyRpdIfEnetSfpPlusStatusTable OBJECT-TYPE
    SYNTAX      SEQUENCE OF DocsRphyRpdIfEnetSfpPlusStatusEntry
    MAX-ACCESS  not-accessible
    STATUS      current
    DESCRIPTION
        "This table provides detailed information about the SFP+ 
         transceivers on the RPD Ethernet Interfaces. It is intended 
         to convey information available from Digital Diagnostic Memory 
         Map of the transceiver.
         The CCAP Core MUST create an entry in SfpPlusStatus table
         for every Ethernet interface on the RPD.
         The CCAP Core reads the SfpPlusStatus object with GCP    
          TLV Type 100.18."
    REFERENCE    
        "Information Model Mapping: CM-SP-R-OSSI    
         SfpPlusStatus"
    ::= { docsRphyRpdIfMibObjects 8 }

docsRphyRpdIfEnetSfpPlusStatusEntry OBJECT-TYPE
    SYNTAX      DocsRphyRpdIfEnetSfpPlusStatusEntry
    MAX-ACCESS  not-accessible
    STATUS      current
    DESCRIPTION
        "An entry containing information about the SFP+ pluggable
         transceiver on an RPD Ethernet Interface."
    INDEX   { docsRphyRpdDevInfoUniqueId,
              docsRphyRpdIfEnetPortIndex }
    ::= { docsRphyRpdIfEnetSfpPlusStatusTable 1 }

DocsRphyRpdIfEnetSfpPlusStatusEntry ::= SEQUENCE 
    {
    docsRphyRpdIfEnetSfpPlusStatusStatus                      BITS,
    docsRphyRpdIfEnetSfpPlusStatusIdentifier                  INTEGER,
    docsRphyRpdIfEnetSfpPlusStatusExtendedIdentifier          OCTET STRING,
    docsRphyRpdIfEnetSfpPlusStatusConnectorType               INTEGER,
    docsRphyRpdIfEnetSfpPlusStatusTransceiverComplianceCodes  OCTET STRING,
    docsRphyRpdIfEnetSfpPlusStatusTransceiverComplianceCode36 OCTET STRING,
    docsRphyRpdIfEnetSfpPlusStatusEncoding                    INTEGER,
    docsRphyRpdIfEnetSfpPlusStatusBitRateNominal              Unsigned32,
    docsRphyRpdIfEnetSfpPlusStatusRateIdentifier              INTEGER,
    docsRphyRpdIfEnetSfpPlusStatusLengthKm                    Unsigned32,
    docsRphyRpdIfEnetSfpPlusStatusLength100M                  Unsigned32,
    docsRphyRpdIfEnetSfpPlusStatusLength50Mi10M               Unsigned32,
    docsRphyRpdIfEnetSfpPlusStatusLength62Pt5Mi10M            Unsigned32,
    docsRphyRpdIfEnetSfpPlusStatusLengthCopperM               Unsigned32,
    docsRphyRpdIfEnetSfpPlusStatusLength50MiOm3               Unsigned32,
    docsRphyRpdIfEnetSfpPlusStatusVendorName                  SnmpAdminString,
    docsRphyRpdIfEnetSfpPlusStatusVendorOui                   OCTET STRING,
    docsRphyRpdIfEnetSfpPlusStatusVendorPartNum               SnmpAdminString,
    docsRphyRpdIfEnetSfpPlusStatusVendorSerialNum             SnmpAdminString,
    docsRphyRpdIfEnetSfpPlusStatusVendorRev                   SnmpAdminString,
    docsRphyRpdIfEnetSfpPlusStatusLaserWavelength             Unsigned32,
    docsRphyRpdIfEnetSfpPlusStatusOptions                     BITS,
    docsRphyRpdIfEnetSfpPlusStatusBitRateMax                  Unsigned32,
    docsRphyRpdIfEnetSfpPlusStatusBitRateMin                  Unsigned32,
    docsRphyRpdIfEnetSfpPlusStatusVendorDate                  SnmpAdminString,
    docsRphyRpdIfEnetSfpPlusStatusVendorSpecificLotCode       SnmpAdminString,
    docsRphyRpdIfEnetSfpPlusStatusDiagMonitorType             BITS,
    docsRphyRpdIfEnetSfpPlusStatusEnhancedOptions             BITS,
    docsRphyRpdIfEnetSfpPlusStatusSff8472Compliance           Unsigned32,
    docsRphyRpdIfEnetSfpPlusStatusVendorSpecificData          OCTET STRING,
    docsRphyRpdIfEnetSfpPlusStatusMeasuredTxOutputPwr         Unsigned32,
    docsRphyRpdIfEnetSfpPlusStatusMeasuredRxInputPwr          Unsigned32,
    docsRphyRpdIfEnetSfpPlusStatusDigitalDiagA2Info           OCTET STRING,
    docsRphyRpdIfEnetSfpPlusStatusMeasuredTxBiasCurrent       Unsigned32,
    docsRphyRpdIfEnetSfpPlusStatusMeasuredTemperature         Integer32,
    docsRphyRpdIfEnetSfpPlusStatusMeasuredSupplyVoltage       Unsigned32
     }

docsRphyRpdIfEnetSfpPlusStatusStatus OBJECT-TYPE
    SYNTAX      BITS {
                      unknown(0),
                      notInstalled(1),
                      installed(2),
                      faulty(3),
                      operational(4),
                      enabled(5),
                      disabled(6),
                      invalidCcBase(7),
                      invalidCcExt(8)
                     }
    MAX-ACCESS  read-only
    STATUS      current
    DESCRIPTION
        "This attribute reports the current state of the 
         SFP+ transceiver. The following state information can be 
         reported:
         unknown: The state is unknown.
         notInstalled: The SFP+ transceiver is not installed.
         installed: The SFP+ transceiver has been installed.
         faulty: The SFP+ transceiver is faulty.
         operational: The SFP+ transceiver is working properly.
         enabled: The SFP+ transceiver has been enabled.
         disabled: The SFP+ transceiver has been diabled.
         invalidCcBase: indicates that the first 64 bytes of 
         serial information in the SFP+ transceiver is invalid. 
         The check is done by comparing the 64-th byte with the 
         sum of the contents of the first 63 bytes (bytes 0 to 62, inclusive).
         invalidCcExt: indicates that the first 32 bytes of the extended
         serial information in the SFP+ transceiver is invalid. 
         The check is done by comparing the 95-th byte with the sum
         of the contents of the first 32 bytes (bytes 64 to 94, inclusive)."
    ::= { docsRphyRpdIfEnetSfpPlusStatusEntry 1 }

docsRphyRpdIfEnetSfpPlusStatusIdentifier OBJECT-TYPE
    SYNTAX     INTEGER {
                         unknown(0),
                         gbic(1),
                         sff(2),
                         sfpOrSfpPlus(3),
                         sbi(4),
                         xenpack(5),
                         xfp(6),
                         xff(7),
                         xfpE(8),
                         xPak(9),
                         x2(10),
                         dwdmSfp(11),
                         qsfp(12)
                        }
    MAX-ACCESS  read-only
    STATUS      current
    DESCRIPTION
        "This attribute is used to report the type of the serial 
         transceiver. The following identifier types can be reported:
         unknown: unknown identifier
         gbic: Gigabit Interface Converter
         sff:  Module soldered to motherboard
         sfpOrSfpPlus: small form factor pluggable or SFP+
         sbi: 300 pin XBI
         xenpack: 10 gigabit Ethernet transceiver package
         xfp:  10 G form factor pluggable
         xff: obsolete
         xfpE: 10 G small form factor pluggable extended
         xPak: 10 G form factor pluggable transceiver package
         x2: 10 G form factor pluggable
         dwdmSfp: Dense Wavelength Division Multiplexing SFP
         qsfp: quad small form factor pluggable
         Enum values 128 - 255 are reserved for vendor specific    
          serial transceiver type identifiers."
    ::= { docsRphyRpdIfEnetSfpPlusStatusEntry 2 }

docsRphyRpdIfEnetSfpPlusStatusExtendedIdentifier  OBJECT-TYPE
    SYNTAX      OCTET STRING (SIZE (1))
    MAX-ACCESS  read-only
    STATUS      current
    DESCRIPTION
        "This attribute reports the extended identifier
         of the type of serial transceiver."
    ::= { docsRphyRpdIfEnetSfpPlusStatusEntry 3 }

docsRphyRpdIfEnetSfpPlusStatusConnectorType  OBJECT-TYPE
    SYNTAX      INTEGER {
                        unknown(0),
                        sc(1),
                        fcscc1(2),
                        fcscc2(3),
                        bnctnc(4),
                        fcch(5),
                        fiberJack(6),
                        lc(7),
                        mtrj(8),
                        mu(9),
                        sg(10),
                        opticalPigtail(11),
                        mpoParallel(12),
                        hssdc2(32),
                        copperPigtail(33),
                        rj45(34)
                       }
    MAX-ACCESS  read-only
    STATUS      current
    DESCRIPTION
        "This attribute reports the code for 
         connector type of the transceiver.
         Enum values 128 - 255 are reserved for 
         vendor specific connector types."
    ::= { docsRphyRpdIfEnetSfpPlusStatusEntry 4 }

docsRphyRpdIfEnetSfpPlusStatusTransceiverComplianceCodes  OBJECT-TYPE
    SYNTAX      OCTET STRING (SIZE (8))
    MAX-ACCESS  read-only
    STATUS      current
    DESCRIPTION
        "This attribute reports bit significant indicators 
         which define the electronic or optical interfaces 
         that are supported by the transceiver.
         Reference [SFF 8472]"
    ::= { docsRphyRpdIfEnetSfpPlusStatusEntry 5 }

docsRphyRpdIfEnetSfpPlusStatusTransceiverComplianceCode36  OBJECT-TYPE
    SYNTAX      OCTET STRING (SIZE (1))
    MAX-ACCESS  read-only
    STATUS      current
    DESCRIPTION
        "This attribute reports the code for 
         electronic or optical compatibility.
         
         Reference [SFF 8472], Transceiver Compliance Codes
         table."
    ::= { docsRphyRpdIfEnetSfpPlusStatusEntry 6 }

docsRphyRpdIfEnetSfpPlusStatusEncoding  OBJECT-TYPE
    SYNTAX      INTEGER {
                         unspecified(0),
                         eightTenB(1),
                         fourFiveB(2),
                         nrz(3),
                         manchester(4),
                         sonetScrambled(5),
                         sixtyFourSixtySixB(6)
                        }
    MAX-ACCESS  read-only
    STATUS      current
    DESCRIPTION
        "This attribute reports the code for high
         speed serial encoding algorithm.
         Reference  [SFF 8024]."
    ::= { docsRphyRpdIfEnetSfpPlusStatusEntry 7 }

docsRphyRpdIfEnetSfpPlusStatusBitRateNominal  OBJECT-TYPE
    SYNTAX      Unsigned32 (0..255)
    UNITS       "100 MBd"
    MAX-ACCESS  read-only
    STATUS      current
    DESCRIPTION
        "This attribute reports nominal signaling 
         rate in units of 100s of Mega Baud."
    ::= { docsRphyRpdIfEnetSfpPlusStatusEntry 8 }

docsRphyRpdIfEnetSfpPlusStatusRateIdentifier   OBJECT-TYPE
    SYNTAX      INTEGER {
                         unspecified(0),
                         sff8079(1),
                         sff8431Rx(2),
                         unspecified3(3),
                         sff8431Tx(4),
                         unspecified5(5),
                         sff8431indepRxTx(6),
                         unspecified7(7),
                         fcpi5Rx(8),
                         unspecified9(9),
                         fcpi5Tx(10),
                         unspecified11(11),
                         fcpi6(12),
                         unspecified13(13),
                         rxTx10or8g(14),
                         unspecified15(15),
                         fcpi7(16),
                         unspecified17(17),
                         reserved18(18),
                         reserved19(19),
                         reserved20(20),
                         reserved21(21),
                         reserved22(22),
                         reserved23(23),
                         reserved24(24),
                         reserved25(25),
                         reserved26(26),
                         reserved27(27),
                         reserved28(28),
                         reserved29(29),
                         reserved30(30),
                         reserved31(31),
                         pmdRateSelect(32)
                        }
    MAX-ACCESS  read-only
    STATUS      current
    DESCRIPTION
        "This attribute refers to several (optional) industry
         standard definitions of Rate Select or Application 
         Select control behaviors, intended to manage transceiver 
         optimization for multiple operating rates.
         
         The following rate identifier types can be reported:
         unspecified: unspecified rate identifier type
         sff8079: SFF-8079 (4/2/1G rate select and AS0/AS1)
         
         sff8431Rx: SFF-8431 (8/4/2G receive rate select only)
         unspecified3: unspecified rate identifier type. To support 
         legacy, the LSB is reserved for Unspecified or INF-8074 (value = 0) 
         or 4/2/1G selection per SFF-8079 (value = 1). 
         Other rate selection functionalities are not allowed to depend on the LSB.
         
         sff8431Tx: SFF-8431 (8/4/2G transmit rate select only)
         
         unspecified5: unspecified rate identifier type. To support 
         legacy, the LSB is reserved for Unspecified or INF-8074 
         (value = 0) or 4/2/1G selection per SFF-8079 (value = 1). 
         Other rate selection functionalities are not allowed to depend on the LSB.
         
         sff8431indepRxTx: SFF-8431 (8/4/2G Independent receive and transmit rate select)
         
         unspecified7: unspecified rate identifier type. To support 
         legacy, the LSB is reserved for Unspecified or INF-8074 (value = 0) 
         or 4/2/1G selection per SFF-8079 (value = 1). Other rate selection 
         functionalities are not allowed to depend on the LSB.
         
         fcpi5Rx: FC-PI-5 (16/8/4G receive rate select only) High=16G only, Low=8G/4G.
         
         unspecified9: unspecified rate identifier type. To support 
         legacy, the LSB is reserved for Unspecified or INF-8074 (value = 0)
         or 4/2/1G selection per SFF-8079 (value = 1). Other rate selection 
         functionalities are not allowed to depend on the LSB.
         
         fcpi5Tx: FC-PI-5 (16/8/4G Independent receive, transmit rate select)
         High=16G only, Low=8G/4G
         
         unspecified11: unspecified rate identifier type. To support 
         legacy, the LSB is reserved for Unspecified or INF-8074 (value = 0)
         or 4/2/1G selection per SFF-8079 (value = 1). Other rate selection 
         functionalities are not allowed to depend on the LSB.
         
         fcpi6: FC-PI-6 (32/16/8G Independent receive, transmit rate select).
         High=32G only, Low = 16G/8G.
         
         unspecified13: unspecified rate identifier type. To support legacy,
         the LSB is reserved for Unspecified or INF-8074 (value = 0) or 4/2/1G
         selection per SFF-8079 (value = 1). Other rate selection functionalities
         are not allowed to depend on the LSB.
         
         rxTx10or8g: 10/8G Rx and Tx Rate_Select controlling the operation or 
         locking modes of the internal signal conditioner, retimer or CDR, 
         according to the logic table defined in Table 10-2, High Bit Rate 
         (10G) =9.95-11.3 Gb/s; Low Bit Rate (8G) = 8.5 Gb/s. In this mode, 
         the default value of bit 110.3 (Soft Rate Select RS(0), Table 9-16 )
         and of bit 118.3 (Soft Rate Select RS(1), Table 10-1) is 1.
         
         unspecified15: unspecified rate identifier type. To support 
         legacy, the LSB is reserved for Unspecified or INF-8074 (value = 0)
         or 4/2/1G selection per SFF-8079 (value = 1). Other rate selection 
         functionalities are not allowed to depend on the LSB.
         
         fcpi7: FC-PI-7 (64/32/16G Independent receive, transmit rate select)
         High = 32GFC and 64GFC. Low = 16GFC.
         
         unspecified17: unspecified rate identifier type. To support 
         legacy, the LSB is reserved for Unspecified or INF-8074 (value = 0)
         or 4/2/1G selection per SFF-8079 (value = 1). Other rate selection
         functionalities are not allowed to depend on the LSB.
         
         reserved18: rate identifier type reserved by [SFF 8472]
         reserved19: rate identifier type reserved by [SFF 8472]
         reserved20: rate identifier type reserved by [SFF 8472]
         reserved21: rate identifier type reserved by [SFF 8472]
         reserved22: rate identifier type reserved by [SFF 8472]
         reserved23: rate identifier type reserved by [SFF 8472]
         reserved24: rate identifier type reserved by [SFF 8472]
         reserved25: rate identifier type reserved by [SFF 8472]
         reserved26: rate identifier type reserved by [SFF 8472]
         reserved27: rate identifier type reserved by [SFF 8472]
         reserved28: rate identifier type reserved by [SFF 8472]
         reserved29: rate identifier type reserved by [SFF 8472]
         reserved30: rate identifier type reserved by [SFF 8472]
         reserved31: rate identifier type reserved by [SFF 8472]
         
         pmdRateSelect: Rate select based on PMDs as defined by A0h,
         byte 36 and A2h, byte 67 (receive, transmit rate select). 
         High = A0h, Byte 36 PMD, Low = A2h, Byte 67 PMD.
         
         Reference  [SFF 8079], [SFF 8431], [SFF 8472]"
    ::= { docsRphyRpdIfEnetSfpPlusStatusEntry 9 }

docsRphyRpdIfEnetSfpPlusStatusLengthKm   OBJECT-TYPE
    SYNTAX      Unsigned32 (0..255)
    UNITS       "km"
    MAX-ACCESS  read-only
    STATUS      current
    DESCRIPTION
        "This attribute reports the link length that is 
         supported by the transceiver while operating in 
         compliance with the applicable standards using single 
         mode fiber. The value is in units of kilometers. 
         A value of 255 means that the transceiver supports a 
         link length greater than 254 km. A value of zero means
         that the transceiver does not support single mode fiber 
         or that the length information has to be determined from 
         the transceiver technology."
    ::= { docsRphyRpdIfEnetSfpPlusStatusEntry 10 }

docsRphyRpdIfEnetSfpPlusStatusLength100M  OBJECT-TYPE
    SYNTAX      Unsigned32 (0..255)
    UNITS       "100s of meters"
    MAX-ACCESS  read-only
    STATUS      current
    DESCRIPTION
        "This attribute reports the link length that is 
         supported by the transceiver while operating in 
         compliance with the applicable standards using single
         mode fiber. The value is in units of 100s of meters. 
         A value of 255 means that the transceiver supports a link 
         length greater than 25.4 km. A value of zero means that 
         the transceiver does not support single mode fiber or 
         that the length information has to be determined from 
         the transceiver technology."
    ::= { docsRphyRpdIfEnetSfpPlusStatusEntry 11 }

docsRphyRpdIfEnetSfpPlusStatusLength50Mi10M OBJECT-TYPE
    SYNTAX      Unsigned32 (0..255)
    UNITS       "10s of meters"
    MAX-ACCESS  read-only
    STATUS      current
    DESCRIPTION
        "This attribute reports link length that is supported by
         the transceiver while operating in compliance with 
         applicable standards using 50 micron multimode OM2 
         [500MHz*km at 850nm] fiber. The value is in units of 
         10 meters. A value of 255 means that the transceiver 
         supports a link length greater than 2.54 km. A value of 
         zero means that the transceiver does not support 50 micron 
         multimode fiber or that the length information has to be 
         determined from the transceiver technology."
    ::= { docsRphyRpdIfEnetSfpPlusStatusEntry 12 }

docsRphyRpdIfEnetSfpPlusStatusLength62Pt5Mi10M  OBJECT-TYPE
    SYNTAX      Unsigned32 (0..255)
    UNITS       "10s of meters"
    MAX-ACCESS  read-only
    STATUS      current
    DESCRIPTION
        "This attribute reports link length that is supported 
         by the transceiver while operating in compliance with 
         applicable standards using 62.5 micron multimode OM1 
         [200 MHz*km at 850nm, 500 MHz*km at 1310nm] fiber. 
         The value is in units of 10 meters. A value of 255 
         means that the transceiver supports a link length greater 
         than 2.54 km. A value of zero means that the transceiver 
         does not support 62.5 micron multimode fiber or that the 
         length information needs to be determined from the 
         transceiver technology."
    ::= { docsRphyRpdIfEnetSfpPlusStatusEntry 13 }

docsRphyRpdIfEnetSfpPlusStatusLengthCopperM  OBJECT-TYPE
    SYNTAX      Unsigned32 (0..255)
    UNITS       "meters"
    MAX-ACCESS  read-only
    STATUS      current
    DESCRIPTION
        "This attribute reports minimum link length supported 
         by the transceiver while operating in compliance with 
         applicable standards using copper cable. For active cable,
         this value represents actual length. The value is in units
         of 1 meter. A value of 255 means the transceiver supports 
         a link length greater than 254 meters. A value of zero means
         the transceiver does not support copper or active cables or 
         the length information has to be determined from transceiver 
         technology."
    ::= { docsRphyRpdIfEnetSfpPlusStatusEntry 14 }

docsRphyRpdIfEnetSfpPlusStatusLength50MiOm3  OBJECT-TYPE
    SYNTAX      Unsigned32 (0..255)
    UNITS       "10s of meters"
    MAX-ACCESS  read-only
    STATUS      current
    DESCRIPTION
        "This attribute reports link length that is supported
         by the transceiver while operating in compliance with 
         applicable standards using 50 micron multimode OM3 
         [2000 MHz*km] fiber. The value is in units of 10 meters. 
         A value of 255 means that the transceiver supports a link
         length greater than 2.54 km. A value of zero means that 
         the transceiver does not support 50 micron multimode fiber
         or that the length information has to be determined from
         the transceiver technology."
    ::= { docsRphyRpdIfEnetSfpPlusStatusEntry 15 }

docsRphyRpdIfEnetSfpPlusStatusVendorName  OBJECT-TYPE
     SYNTAX      SnmpAdminString (SIZE (16))
     MAX-ACCESS  read-only
     STATUS      current
     DESCRIPTION
        "The vendor name is a 16 character string that contains
         ASCII characters, left-aligned and padded on the right
         with ASCII spaces (0x20)."
    ::= { docsRphyRpdIfEnetSfpPlusStatusEntry 16 }

docsRphyRpdIfEnetSfpPlusStatusVendorOui  OBJECT-TYPE
    SYNTAX      OCTET STRING (SIZE (3))
    MAX-ACCESS  read-only
    STATUS      current
    DESCRIPTION
        "The vendor organizationally unique identifier (vendor OUI)
         is a 3-byte hexbinary string that contains the IEEE Company 
         Identifier for the vendor. A value of all zero in the 3-byte 
         string indicates that the Vendor OUI is unspecified."
    ::= { docsRphyRpdIfEnetSfpPlusStatusEntry 17 }

docsRphyRpdIfEnetSfpPlusStatusVendorPartNum  OBJECT-TYPE
    SYNTAX      SnmpAdminString (SIZE (16))
    MAX-ACCESS  read-only
    STATUS      current
    DESCRIPTION
        "The vendor part number is a 16-byte ASCII string, 
         left-aligned and padded on the right with ASCII 
         spaces (0x20), defining the vendor part number or
         product name. A value of all zero in the 16-byte field
         indicates that the vendor part number is unspecified."
    ::= { docsRphyRpdIfEnetSfpPlusStatusEntry 18 }

docsRphyRpdIfEnetSfpPlusStatusVendorSerialNum  OBJECT-TYPE
    SYNTAX      SnmpAdminString (SIZE (16))
    MAX-ACCESS  read-only
    STATUS      current
    DESCRIPTION
        "The vendor serial number is a 16-character ASCII string,
         left-aligned and padded on the right with ASCII spaces (0x20),
         defining the vendor's serial number for the transceiver. 
         A value of all zero in the 16-byte field indicates that 
         the vendor serial number is unspecified."
    ::= { docsRphyRpdIfEnetSfpPlusStatusEntry 19 }

docsRphyRpdIfEnetSfpPlusStatusVendorRev  OBJECT-TYPE
    SYNTAX      SnmpAdminString (SIZE (4))
    MAX-ACCESS  read-only
    STATUS      current
    DESCRIPTION
        "The vendor revision number is a 4-byte ASCII string,
         left-aligned and padded on the right with ASCII 
         spaces (0x20), defining the vendor's product 
         revision number. A value of all zero in the 4-byte field
         indicates that the vendor revision is unspecified."
    ::= { docsRphyRpdIfEnetSfpPlusStatusEntry 20 }

docsRphyRpdIfEnetSfpPlusStatusLaserWavelength  OBJECT-TYPE
    SYNTAX      Unsigned32 (0..65535)
    UNITS       "Nanometers"
    MAX-ACCESS  read-only
    STATUS      current
    DESCRIPTION
        "For optical variants, as defined by TransceiverComplianceCodes
         attribute, this attribute denotes nominal transmitter output 
         wavelength at room temperature."
    ::= { docsRphyRpdIfEnetSfpPlusStatusEntry 21 }

docsRphyRpdIfEnetSfpPlusStatusOptions  OBJECT-TYPE
    SYNTAX      BITS {
                      unallocated0(0),
                      rxlosNormal(1),
                      rxlosInverted(2),
                      txFault(3),
                      txDisable(4),
                      rateSelect(5),
                      unallocated6(6),
                      unallocated7(7),
                      linearOutput(8),
                      powerLevel(9),
                      cooledTransceiver(10),
                      reserved11(11),
                      reserved12(12),
                      reserved13(13),
                      reserved14(14),
                      reserved15(15)
                     }
    MAX-ACCESS  read-only
    STATUS      current
    DESCRIPTION
        "This attribute reports options implemented in the transceiver 
        as described in the Options Values table of [SFF 8472]. 
        The following rate identifier types can be reported:
        unallocated: unallocated options value
        
        rxlosNormal: Loss of Signal implemented, behavior as defined in 
        [SFF 8419] (often called Rx_LOS)
        
        rxlosInverted: Loss of Signal implemented, signal inverted from
        standard definition in SFP MSA (often called Signal Detect)
        
        txFault: TX_FAULT signal implemented. Reference  [SFF 8419]        
        txDisable: TX_DISABLE is implemented and disables the high speed serial output.
        rateSelect: RATE_SELECT functionality is implemented.
        unallocated6: unallocated options value
        unallocated7: unallocated options value
        
        powerLevel: Power Level Declaration. Value of zero identifies Power 
        Level 1 (or unspecified) requirements. Value of one identifies Power
        Level 2 requirement. See [SFF 8472] I/O Timing for Soft Control and 
        Status Functions table and Extended Module Control/Status Bytes table 
        for control, status, timing. See [SFF 8472] Option Values table Address
        A0h byte 64, Bit 5 for Power Level 3 declaration. See [SFF 8472] Option 
        Values table Address A0h byte 64, Bit 6 for Power Level 4 declaration.
        Reference  [SFF 8431].
        
        cooledTransceiver: Cooled Transceiver Declaration. Value of zero identifies 
        a conventional uncooled (or unspecified) laser implementation. Value of one
        identifies a cooled laser transmitter implementation. Reference [SFF 8431].
        
        Reference [SFF 8472]"
    ::= { docsRphyRpdIfEnetSfpPlusStatusEntry 22 }

docsRphyRpdIfEnetSfpPlusStatusBitRateMax  OBJECT-TYPE
    SYNTAX      Unsigned32 (0..255)
    UNITS       "percent"
    MAX-ACCESS  read-only
    STATUS      current
    DESCRIPTION
        "This attribute reports the upper bit rate limit at 
         which the transceiver will still meet its specifications.
         This attribute is specified in units of 1% above the nominal
         bit rate. A value of zero indicates that this field is not
         specified."
    ::= { docsRphyRpdIfEnetSfpPlusStatusEntry 23 }

docsRphyRpdIfEnetSfpPlusStatusBitRateMin   OBJECT-TYPE
    SYNTAX      Unsigned32 (0..255)
    UNITS       "percent"
    MAX-ACCESS  read-only
    STATUS      current
    DESCRIPTION
        "This attribute reports the lower bit rate limit at 
         which the transceiver will still meet its specifications 
         and is specified in units of 1% below the nominal bit rate. 
         A value of zero indicates that this field is not specified."
    ::= { docsRphyRpdIfEnetSfpPlusStatusEntry 24 }
         
docsRphyRpdIfEnetSfpPlusStatusVendorDate    OBJECT-TYPE
    SYNTAX      SnmpAdminString (SIZE (6))
    MAX-ACCESS  read-only
    STATUS      current
    DESCRIPTION
        "This attribute is a 6-byte field that contains the vendor's 
         date code in ASCII characters. The date code is specified
         in the following format:
         Bytes 0, 1 - ASCII code, two low order digits of year. (00 = 2000).
         Bytes 2, 3 - ASCII code, digits of month (01 = Jan through 12 = Dec)
         Bytes 4, 5 - ASCII code, day of month (01 - 31)"
    ::= { docsRphyRpdIfEnetSfpPlusStatusEntry 25 }

docsRphyRpdIfEnetSfpPlusStatusVendorSpecificLotCode   OBJECT-TYPE
    SYNTAX      SnmpAdminString (SIZE (2))
    MAX-ACCESS  read-only
    STATUS      current
    DESCRIPTION
        "This attribute reports a vendor specific lot code."
    ::= { docsRphyRpdIfEnetSfpPlusStatusEntry 26 }

docsRphyRpdIfEnetSfpPlusStatusDiagMonitorType    OBJECT-TYPE
    SYNTAX      BITS {
                      unallocated0(0),
                      unallocated1(1),
                      addrChangeReq(2),
                      recPwrMeasType(3),
                      externCalibrated(4),
                      internCalibrated(5),
                      digDiagImpl(6),
                      legacyImpl(7)
                     }
    MAX-ACCESS  read-only
    STATUS      current
    DESCRIPTION
        "This attribute reports how diagnostic monitoring
         is implemented in the selected transceiver.
         The following diagnostic monitoring types can be reported:
         unallocated: unallocated diagnostic monitoring type
         unallocated1: unallocated diagnostic monitoring type
         addrChangeReq: Address change required
         recPwrMeasType: Received power measurement type. 0 = OMA, 1 = average power.
         externCalibrated: externally calibrated
         internCalibrated: internally calibrated
         digDiagImpl: digital diagnostic monitoring implemented
         legacyImpl: Reserved for legacy diagnostic implementations. 
         Must be '0' for compliance with [SFF 8472].
         Reference [SFF 8472]"
    ::= { docsRphyRpdIfEnetSfpPlusStatusEntry 27 }
      
docsRphyRpdIfEnetSfpPlusStatusEnhancedOptions  OBJECT-TYPE
    SYNTAX      BITS {
                      unknown(0),
                      rateCtrlImpl(1),
                      appSelCtrlImpl(2),
                      rateSelectCtrlImpl(3),
                      rxLosMonImpl(4),
                      txFaultMonImpl(5),
                      txDisableMonImpl(6),
                      allAlarmsImpl(7) 
                     }
    MAX-ACCESS  read-only
    STATUS      current
    DESCRIPTION
        "This attribute reports the optional digital diagnostic
         features implemented in the transceiver.
         The following values enhanced options types can be reported:
         
         unknown: unknown enhanced option type
         rateCtrlImpl: Soft Rate Select control implemented per [SFF- 8431].
         appSelCtrlImpl: Application Select control implemented per [SFF- 8079].
         rateSelectCtrlImpl: Soft RATE_SELECT control and monitoring implemented.
         rxLosMonImpl: Soft RX_LOS monitoring implemented.
         txFaultMonImpl: Soft TX_FAULT monitoring implemented.
         txDisableMonImpl: Soft TX_DISABLE control and monitoring implemented.
         allAlarmsImpl: Alarm/warning flags implemented for all monitored quantities.
         Reference [SFF 8472]"
    ::= { docsRphyRpdIfEnetSfpPlusStatusEntry 28 }
          
docsRphyRpdIfEnetSfpPlusStatusSff8472Compliance  OBJECT-TYPE
    SYNTAX      Unsigned32 (0..255)
    MAX-ACCESS  read-only
    STATUS      current
    DESCRIPTION
        "This attribute reports which feature set(s)
         are implemented in the transceiver."
    ::= { docsRphyRpdIfEnetSfpPlusStatusEntry 29 }         

docsRphyRpdIfEnetSfpPlusStatusVendorSpecificData  OBJECT-TYPE
    SYNTAX      OCTET STRING (SIZE (32))
    MAX-ACCESS  read-only
    STATUS      current
    DESCRIPTION
        "This attribute reports a 32-byte long hexbinary 
         string with content of Vendor Specific 
         EEPROM (address 0xA0, bytes 96-127)."
    ::= { docsRphyRpdIfEnetSfpPlusStatusEntry 30 }
       
docsRphyRpdIfEnetSfpPlusStatusMeasuredTxOutputPwr OBJECT-TYPE
    SYNTAX      Unsigned32 (0..65535)
    UNITS       "0.1 Micro Watts"
    MAX-ACCESS  read-only
    STATUS      current
    DESCRIPTION
        "This attribute reports measured transmit 
         output power in units of 0.1 micro Watts."
    ::= { docsRphyRpdIfEnetSfpPlusStatusEntry 31 }          

docsRphyRpdIfEnetSfpPlusStatusMeasuredRxInputPwr OBJECT-TYPE
    SYNTAX      Unsigned32 (0..65535)
    UNITS       "0.1 Micro Watts"
    MAX-ACCESS  read-only
    STATUS      current
    DESCRIPTION
        "This attribute reports measured received optical power
         in units of 0.1 micro Watts. The reported value can 
         represent either average received power or OMA 
         (Optical Modulation Amplitude) depending upon how 
         bit recPwrMeasType of DiagMonitorType is reported. 
         When recPwrMeasType is '0' then the measured received 
         optical power is reported as OMA, otherwise it is 
         reported as average received power."
    ::= { docsRphyRpdIfEnetSfpPlusStatusEntry 32 } 
         
docsRphyRpdIfEnetSfpPlusStatusDigitalDiagA2Info  OBJECT-TYPE
    SYNTAX      OCTET STRING (SIZE (256))
    MAX-ACCESS  read-only
    STATUS      current
    DESCRIPTION
        "This attribute reports diagnostics data fields from 
         Address 0xA2 of the transceiver's two wire serial bus.
         The data is provided undecoded."
    ::= { docsRphyRpdIfEnetSfpPlusStatusEntry 33 }
    
docsRphyRpdIfEnetSfpPlusStatusMeasuredTxBiasCurrent OBJECT-TYPE
    SYNTAX      Unsigned32 (0..65535)
    UNITS       "2 Micro Amps"
    MAX-ACCESS  read-only
    STATUS      current
    DESCRIPTION
        "This attribute, which is optional for SFP+ pluggable transceivers,
         reports measured transmit bias current in units of 2 micro Amps. 
         If this attribute is not supported by the RPD's transceivers, 
         the RPD will return a value of zero."
    ::= { docsRphyRpdIfEnetSfpPlusStatusEntry 34 } 
    
docsRphyRpdIfEnetSfpPlusStatusMeasuredTemperature OBJECT-TYPE
    SYNTAX      Integer32 (-32768..32767)
    UNITS       "1/256 degree celsius"
    MAX-ACCESS  read-only
    STATUS      current
    DESCRIPTION
        "This attribute, which is optional for SFP+ pluggable transceivers,
         reports internally measured transceiver temperature as a signed 
         twos compliment value in increments of 1/256 degrees Celsius. 
         If this attribute is not supported by the RPD's transceivers,
         the RPD will return a value of zero."
    ::= { docsRphyRpdIfEnetSfpPlusStatusEntry 35 }

docsRphyRpdIfEnetSfpPlusStatusMeasuredSupplyVoltage OBJECT-TYPE
    SYNTAX      Unsigned32 (0..65535)
    UNITS       "100 micro Volts"
    MAX-ACCESS  read-only
    STATUS      current
    DESCRIPTION
        "This attribute, which is optional for SFP+ pluggable transceivers,
         reports internally measured transceiver supply voltage in units 
         of 100 micro Volts. If this attribute is not supported by the RPD's 
         transceivers, the RPD will return a value of zero."
    ::= { docsRphyRpdIfEnetSfpPlusStatusEntry 36 }    
    


-- ---------------------------------------------------------------------
-- RPD Ethernet Interface SyncE Port Status
-- ---------------------------------------------------------------------
docsRphyRpdIfEnetSyncEPortStatusTable OBJECT-TYPE
    SYNTAX      SEQUENCE OF DocsRphyRpdIfEnetSyncEPortStatusEntry
    MAX-ACCESS  not-accessible
    STATUS      current
    DESCRIPTION
        "The SyncEPortStatus provides the status of one RPD Ethernet port
        being used for SyncE. The CCAP Core MUST create a row in the SyncEPortStatus 
        table for every IfEnet object instance that has SyncE enabled 
        The SyncEPortStatus TLV Type is 100.36."
    REFERENCE 
        "Information Model Mapping: CM-SP-R-OSSI 
         SyncEPortStatus"
    ::= { docsRphyRpdIfMibObjects 9 }

docsRphyRpdIfEnetSyncEPortStatusEntry OBJECT-TYPE
    SYNTAX      DocsRphyRpdIfEnetSyncEPortStatusEntry
    MAX-ACCESS  not-accessible
    STATUS      current
    DESCRIPTION
        "An entry for a port being used for SyncE"
    INDEX   { docsRphyRpdDevInfoUniqueId,
              docsRphyRpdIfEnetPortIndex }
    ::= { docsRphyRpdIfEnetSyncEPortStatusTable 1 }

DocsRphyRpdIfEnetSyncEPortStatusEntry ::= SEQUENCE 
    {
    docsRphyRpdIfEnetSyncEPortStatusSignalQualified        TruthValue,
    docsRphyRpdIfEnetSyncEPortStatusReceivedSsm            SyncEQLType
    }
        
 docsRphyRpdIfEnetSyncEPortStatusSignalQualified   OBJECT-TYPE
     SYNTAX     TruthValue
     MAX-ACCESS read-only
     STATUS     current
     DESCRIPTION
         "This attribute is true if the signal on this Ethernet port
          is qualified for SyncE. It is false otherwise."
     REFERENCE 
        "Information Model Mapping: CM-SP-R-OSSI 
         SyncEPortStatus::SignalQualified"
     ::= { docsRphyRpdIfEnetSyncEPortStatusEntry 1 } 

 docsRphyRpdIfEnetSyncEPortStatusReceivedSsm   OBJECT-TYPE
     SYNTAX     SyncEQLType
     MAX-ACCESS read-only
     STATUS     current
     DESCRIPTION
         "This attribute contains the SSM value received
          for the interface."
     REFERENCE 
        "Information Model Mapping: CM-SP-R-OSSI 
         SyncEPortStatus::ReceivedSsm"
     ::= { docsRphyRpdIfEnetSyncEPortStatusEntry 2 }  
     
-- ---------------------------------------------------------------------
-- RPD RFM Status
-- ---------------------------------------------------------------------
docsRphyRpdIfRfmStatusTable OBJECT-TYPE
    SYNTAX      SEQUENCE OF DocsRphyRpdIfRfmStatusEntry
    MAX-ACCESS  not-accessible
    STATUS      current
    DESCRIPTION
        "The RfmStatus table provides the status of one RPD RF
         module (RFM) of an optical node-based RPD. Shelf RPDs
         do not have RF modules. See the Remote PHY Node 
         Architecture section of [R-PHY] for more information
         about RFM.     
         The CCAP Core reads all attributes of an RfmStatus object
         with complex GCP TLV 161.1.1"
    REFERENCE 
        "Information Model Mapping: CM-SP-R-OSSI 
         RfmStatus"
    ::= { docsRphyRpdIfMibObjects 10 }

docsRphyRpdIfRfmStatusEntry OBJECT-TYPE
    SYNTAX      DocsRphyRpdIfRfmStatusEntry
    MAX-ACCESS  not-accessible
    STATUS      current
    DESCRIPTION
        "A row in the docsRphyRpdIfRfmStatusTable."
    INDEX   { docsRphyRpdDevInfoUniqueId,
              docsRphyRpdIfRfmStatusNodePortIndex }
    ::= { docsRphyRpdIfRfmStatusTable 1 }

DocsRphyRpdIfRfmStatusEntry ::= SEQUENCE 
    {
    docsRphyRpdIfRfmStatusNodePortIndex                Unsigned32,
    docsRphyRpdIfRfmStatusReportedDsGain               TenthdB,
    docsRphyRpdIfRfmStatusReportedDsGainStatus         RfmStatusType,
    docsRphyRpdIfRfmStatusReportedUsGain               TenthdB,
    docsRphyRpdIfRfmStatusReportedUsGainStatus         RfmStatusType,
    docsRphyRpdIfRfmStatusReportedRfmDsTilt            TenthdB,
    docsRphyRpdIfRfmStatusReportedRfmDsTiltStatus      RfmStatusType,
    docsRphyRpdIfRfmStatusDsOutputPower                TenthdBmV,
    docsRphyRpdIfRfmStatusUsExpectedRxPower            TenthdBmV,
    docsRphyRpdIfRfmStatusTotalDsTilt                  TenthdB
    }
    
docsRphyRpdIfRfmStatusNodePortIndex  OBJECT-TYPE
    SYNTAX      Unsigned32 (0..255)
    MAX-ACCESS  not-accessible
    STATUS      current
    DESCRIPTION
        "This attribute contains the RPD's RF module index
        (i.e., the node RF port). Numbers range from 0 to N-1,
        where N is the number reported by the RPD through the
        NumNodeRfPorts (TLV 50.60.2) attribute."
    REFERENCE 
        "Information Model Mapping: CM-SP-R-OSSI 
         RfmStatus::NodePortIndex"
    ::= { docsRphyRpdIfRfmStatusEntry 1 }
    
docsRphyRpdIfRfmStatusReportedDsGain OBJECT-TYPE
    SYNTAX      TenthdB (-32768..32767)
    UNITS       "dB"
    MAX-ACCESS  read-only
    STATUS      current
    DESCRIPTION
        "This attribute is used to report DS gain in the 
         RFM. RPDs with locally configured downstream gain
         (i.e., physical pads) can report the gain though
         this attribute when the RPD has information how 
         the pads are configured. This attribute needs to
         be used in conjunction with ReportedDsGainStatus
         (TLV 161.1.3) attribute which reports additional
         information about the reported value. RPDs with 
         unknown DS RFM gain report a value of 0."
    REFERENCE 
        "Information Model Mapping: CM-SP-R-OSSI 
         RfmStatus::ReportedDsGain"
    ::= { docsRphyRpdIfRfmStatusEntry 2 }
    
docsRphyRpdIfRfmStatusReportedDsGainStatus OBJECT-TYPE
    SYNTAX      RfmStatusType
    MAX-ACCESS  read-only
    STATUS      current
    DESCRIPTION
        "This attribute is used to report additional 
        qualifying information about the value reported
        through ReportedDsGain (TLV 161.1.2) attribute."
    REFERENCE 
        "Information Model Mapping: CM-SP-R-OSSI 
         RfmStatus::ReportedDsGainStatus"
    ::= { docsRphyRpdIfRfmStatusEntry 3 }
    
docsRphyRpdIfRfmStatusReportedUsGain OBJECT-TYPE
    SYNTAX      TenthdB (-32768..32767)
    UNITS       "dB"
    MAX-ACCESS  read-only
    STATUS      current
    DESCRIPTION
        "This attribute is used to report upstream gain 
        in the RFM. RPDs with locally configured upstream 
        gain (i.e., physical pads) can report the gain 
        though this attribute when the RPD has information
        how the pads are configured. This attribute needs
        to be used in conjunction with ReportedUsGainStatus
        (TLV 161.1.5) attribute which reports additional 
        qualifying information about the reported value. 
        RPDs with unknown US RFM gain report a value of 0."
    REFERENCE 
        "Information Model Mapping: CM-SP-R-OSSI 
         RfmStatus::ReportedUsGain"
    ::= { docsRphyRpdIfRfmStatusEntry 4 }
    
docsRphyRpdIfRfmStatusReportedUsGainStatus OBJECT-TYPE
    SYNTAX      RfmStatusType
    MAX-ACCESS  read-only
    STATUS      current
    DESCRIPTION
        "This attribute is used to report addition qualifying
        information about the value reported through 
        ReportedUsGain (TLV 161.1.4) attribute."
    REFERENCE 
        "Information Model Mapping: CM-SP-R-OSSI 
         RfmStatus::ReportedUsGainStatus"
    ::= { docsRphyRpdIfRfmStatusEntry 5 }
    
docsRphyRpdIfRfmStatusReportedRfmDsTilt OBJECT-TYPE
    SYNTAX      TenthdB (0..65535)
    UNITS       "dB"
    MAX-ACCESS  read-only
    STATUS      current
    DESCRIPTION
        "This attribute is used to report DS tilt in the RFM. 
        RPDs with locally configured downstream tilt 
        (i.e., physical pads) report the tilt though 
        this attribute when the RPD has information 
        how the pads are configured. This attribute 
        needs to be used in conjunction with 
        ReportedRfmTiltStatus (TLV 161.1.7) attribute
        which reports additional qualifying information
        about the reported value. RPDs with unknown 
        DS RFM tilt report a value of 0. This attribute is
        reported in the same fashion for the Full Spectrum
        and Partial Spectrum RF ports."
    REFERENCE 
        "Information Model Mapping: CM-SP-R-OSSI 
         RfmStatus::TotalDsTilt"
    ::= { docsRphyRpdIfRfmStatusEntry 6 }

docsRphyRpdIfRfmStatusReportedRfmDsTiltStatus OBJECT-TYPE
    SYNTAX      RfmStatusType
    MAX-ACCESS  read-only
    STATUS      current
    DESCRIPTION
        "This attribute is used to report addition qualifying
        information about the value reported through 
        ReportedRfmDsTilt (TLV 161.1.6) attribute. This
        attribute is reported in the same fashion for the
        Full Spectrum and Partial Spectrum RF ports."
    REFERENCE 
        "Information Model Mapping: CM-SP-R-OSSI 
         RfmStatus::ReportedRfmDsTiltStatus"
    ::= { docsRphyRpdIfRfmStatusEntry 7 }  

docsRphyRpdIfRfmStatusDsOutputPower OBJECT-TYPE
    SYNTAX      TenthdBmV (0..65535)
    UNITS       "dBmV/6MHz"
    MAX-ACCESS  read-only
    STATUS      current
    DESCRIPTION
        "This attribute is used to report the output power 
        for the selected node RF port of the RFM. RPDs with 
        unknown DS RFM output power report a value of 0."
    REFERENCE 
        "Information Model Mapping: CM-SP-R-OSSI 
         RfmStatus::DsOutputPower"
    ::= { docsRphyRpdIfRfmStatusEntry 8 }  

docsRphyRpdIfRfmStatusUsExpectedRxPower OBJECT-TYPE
    SYNTAX      TenthdBmV (-32768..32767)
    UNITS       "dBmV/1.6MHz"
    MAX-ACCESS  read-only
    STATUS      current
    DESCRIPTION
        "This attribute is used to report the expected input
        power for the selected node RF port of the RFM. 
        RPDs with unknown upstream receive power level
        report a value of 0."
    REFERENCE 
        "Information Model Mapping: CM-SP-R-OSSI 
         RfmStatus::UsExpectedRxPower"
    ::= { docsRphyRpdIfRfmStatusEntry 9 }  

docsRphyRpdIfRfmStatusTotalDsTilt OBJECT-TYPE
    SYNTAX      TenthdB (0..65535)
    UNITS       "dB"
    MAX-ACCESS  read-only
    STATUS      current
    DESCRIPTION
        "This attribute is used to report the combined 
        tilt value for the selected node RF port of the
        RFM. RPDs with unknown DS RFM tilt report a 
        value of 0."
    REFERENCE 
        "Information Model Mapping: CM-SP-R-OSSI 
         RfmStatus::TotalDsTilt"
    ::= { docsRphyRpdIfRfmStatusEntry 10 }    

    
-- ---------------------------------------------------------------------
-- RPD IP Group Objects Derived from IP-MIB RFC 4293
-- ---------------------------------------------------------------------

-- ---------------------------------------------------------------------
-- IPv4 Scalar Group Objects
-- ---------------------------------------------------------------------
docsRphyRpdIpv4GrpTable OBJECT-TYPE
    SYNTAX     SEQUENCE OF DocsRphyRpdIpv4GrpEntry
    MAX-ACCESS not-accessible
    STATUS     current
    DESCRIPTION
        "The table containing per-RPD IPv4-specific
         information."
    ::= { docsRphyRpdIpMibObjects 1 }

docsRphyRpdIpv4GrpEntry OBJECT-TYPE
    SYNTAX     DocsRphyRpdIpv4GrpEntry
    MAX-ACCESS not-accessible
    STATUS     current
    DESCRIPTION
        "An entry containing IPv4-specific information for a specific
         RPD."
    INDEX { docsRphyRpdDevInfoUniqueId }
    ::= { docsRphyRpdIpv4GrpTable 1 }

DocsRphyRpdIpv4GrpEntry ::= SEQUENCE 
    {
    docsRphyRpdIpv4GrpDefaultTTL                 Integer32,
    docsRphyRpdIpv4GrpInterfaceTableLastChange   TimeStamp
    }

docsRphyRpdIpv4GrpDefaultTTL OBJECT-TYPE
    SYNTAX     Integer32 (1..255)
    MAX-ACCESS read-only
    STATUS     current
    DESCRIPTION
        "The default value inserted into the Time-To-Live field of
         the IPv4 header of datagrams originated at this entity,
         whenever a TTL value is not supplied by the transport layer
         protocol."
    ::= { docsRphyRpdIpv4GrpEntry 1 }
    
docsRphyRpdIpv4GrpInterfaceTableLastChange OBJECT-TYPE
    SYNTAX     TimeStamp
    MAX-ACCESS read-only
    STATUS     current
    DESCRIPTION
        "This attribute reports the value of RpdSysUpTime on the 
         most recent occasion at which an instance of the 
         Ipv4Interface object was added or deleted, or when a 
         ReasmMaxSize or an EnableStatus attribute of the 
         Ipv4Interface object was modified."
    ::= { docsRphyRpdIpv4GrpEntry 2 }

-- ---------------------------------------------------------------------
-- IPv6 Scalar Group Objects
-- ---------------------------------------------------------------------
docsRphyRpdIpv6GrpTable OBJECT-TYPE
    SYNTAX     SEQUENCE OF DocsRphyRpdIpv6GrpEntry
    MAX-ACCESS not-accessible
    STATUS     current
    DESCRIPTION
        "The table containing per-RPD IPv6-specific
         information."
    ::= { docsRphyRpdIpMibObjects 2 }

docsRphyRpdIpv6GrpEntry OBJECT-TYPE
    SYNTAX     DocsRphyRpdIpv6GrpEntry
    MAX-ACCESS not-accessible
    STATUS     current
    DESCRIPTION
        "An entry containing IPv6-specific information for a specific
         RPD."
    INDEX { docsRphyRpdDevInfoUniqueId }
    ::= { docsRphyRpdIpv6GrpTable 1 }

DocsRphyRpdIpv6GrpEntry ::= SEQUENCE 
    {
    docsRphyRpdIpv6GrpIpDefaultHopLimit        Integer32, 
    docsRphyRpdIpv6GrpInterfaceTableLastChange TimeStamp,
    docsRphyRpdIpv6GrpIfStatsTableLastChange   TimeStamp
    }

docsRphyRpdIpv6GrpIpDefaultHopLimit OBJECT-TYPE
    SYNTAX     Integer32 (0..255)
    MAX-ACCESS read-only
    STATUS     current
    DESCRIPTION
        "The default value inserted into the Hop Limit field of the
         IPv6 header of datagrams originated at this entity whenever
         a Hop Limit value is not supplied by the transport layer
         protocol."
    REFERENCE "RFC 2461 Section 6.3.2"
    ::= { docsRphyRpdIpv6GrpEntry 1 }
    
docsRphyRpdIpv6GrpInterfaceTableLastChange OBJECT-TYPE
    SYNTAX     TimeStamp
    MAX-ACCESS read-only
    STATUS     current
    DESCRIPTION
        "This attribute reports the value of RpdSysUpTime on the 
         most recent occasion at which an instance of the 
         Ipv6Interface object was added or deleted or when a 
         ReasmMaxSize, InterfaceIdentifier, EnableStatus, 
         ReachableTime, RetransmitTime, or Forwarding attribute 
         of the Ipv6Interface object was modified."
    ::= { docsRphyRpdIpv6GrpEntry 2 }
    
docsRphyRpdIpv6GrpIfStatsTableLastChange OBJECT-TYPE
    SYNTAX     TimeStamp
    MAX-ACCESS read-only
    STATUS     current
    DESCRIPTION
        "This attribute reports the value of RpdSysUpTime on the most 
         recent occasion at which an instance of the ipIfStats object 
         was added or deleted."
    ::= { docsRphyRpdIpv6GrpEntry 3 }
    
-- ---------------------------------------------------------------------
-- IPv4 Interface Table
-- ---------------------------------------------------------------------

docsRphyRpdIpv4InterfaceTable OBJECT-TYPE
    SYNTAX     SEQUENCE OF DocsRphyRpdIpv4InterfaceEntry
    MAX-ACCESS not-accessible
    STATUS     current
    DESCRIPTION
        "The table containing per-interface IPv4-specific
         information. The CCAP Core reads the attributes of the 
         Ipv4Interface table in the complex GCP TLV 100.12"
    REFERENCE 
        "Information Model Mapping: CM-SP-R-OSSI 
         IpInterface"
    ::= { docsRphyRpdIpMibObjects 3 }

docsRphyRpdIpv4InterfaceEntry OBJECT-TYPE
    SYNTAX     DocsRphyRpdIpv4InterfaceEntry
    MAX-ACCESS not-accessible
    STATUS     current
    DESCRIPTION
           "An entry containing IPv4-specific information for an RPD's
            ethernet port."
    INDEX { docsRphyRpdDevInfoUniqueId,
            docsRphyRpdIfEnetPortIndex }
    ::= { docsRphyRpdIpv4InterfaceTable 1 }

DocsRphyRpdIpv4InterfaceEntry ::= SEQUENCE 
    {
    docsRphyRpdIpv4InterfaceEnableStatus    INTEGER,
    docsRphyRpdIpv4InterfaceRetransmitTime  Unsigned32
    }

docsRphyRpdIpv4InterfaceEnableStatus OBJECT-TYPE
    SYNTAX     INTEGER {
                        up(1),
                        down(2)
                      }
    MAX-ACCESS read-only
    STATUS     current
    DESCRIPTION
        "The indication of whether IPv4 is enabled (up) or disabled
         (down) on this interface.  This object does not affect the
         state of the interface itself, only its connection to an
         IPv4 stack.  The IF-MIB should be used to control the state
         of the interface."
    REFERENCE 
        "Information Model Mapping: CM-SP-R-OSSI 
         IpInterface::EnableStatus"
    ::= { docsRphyRpdIpv4InterfaceEntry 1 }

docsRphyRpdIpv4InterfaceRetransmitTime OBJECT-TYPE
    SYNTAX     Unsigned32
    UNITS      "milliseconds"
    MAX-ACCESS read-only
    STATUS     current
    DESCRIPTION
        "The time between retransmissions of ARP requests to a
         neighbor when resolving the address or when probing the
         reachability of a neighbor."
    REFERENCE 
        "Information Model Mapping: CM-SP-R-OSSI 
         IpInterface::RetransmitTime"
    ::= { docsRphyRpdIpv4InterfaceEntry 2 }

-- ---------------------------------------------------------------------
-- IPv6 Interface Table
-- ---------------------------------------------------------------------

docsRphyRpdIpv6InterfaceTable OBJECT-TYPE
    SYNTAX     SEQUENCE OF DocsRphyRpdIpv6InterfaceEntry
    MAX-ACCESS not-accessible
    STATUS     current
    DESCRIPTION
        "The table containing per-interface IPv6-specific
         information. The CCAP core reads the attributes of
         of an IPv6Interface object in GCP TLV 100.13. "
    REFERENCE 
        "Information Model Mapping: CM-SP-R-OSSI 
         IpV6Interface"
    ::= { docsRphyRpdIpMibObjects 4 }

docsRphyRpdIpv6InterfaceEntry OBJECT-TYPE
    SYNTAX     DocsRphyRpdIpv6InterfaceEntry
    MAX-ACCESS not-accessible
    STATUS     current
    DESCRIPTION
        "An entry containing IPv6-specific information for an RPD's
         ethernet port."
    INDEX { docsRphyRpdDevInfoUniqueId,
            docsRphyRpdIfEnetPortIndex }
    ::= { docsRphyRpdIpv6InterfaceTable 1 }

DocsRphyRpdIpv6InterfaceEntry ::= SEQUENCE 
    {
    docsRphyRpdIpv6InterfaceIdentifier      Ipv6AddressIfIdentifierTC,
    docsRphyRpdIpv6InterfaceEnableStatus    INTEGER,
    docsRphyRpdIpv6InterfaceReachableTime   Unsigned32,
    docsRphyRpdIpv6InterfaceRetransmitTime  Unsigned32
    }

docsRphyRpdIpv6InterfaceIdentifier OBJECT-TYPE
    SYNTAX     Ipv6AddressIfIdentifierTC
    MAX-ACCESS read-only
    STATUS     current
    DESCRIPTION
        "The Interface Identifier for this interface.  The Interface
         Identifier is combined with an address prefix to form an
         interface address.

         By default, the Interface Identifier is auto-configured
         according to the rules of the link type to which this
         interface is attached.

         A zero length identifier may be used where appropriate."
    REFERENCE 
        "Information Model Mapping: CM-SP-R-OSSI 
         IpV6Interface::InterfaceIdentifier"
    ::= { docsRphyRpdIpv6InterfaceEntry 1 }

docsRphyRpdIpv6InterfaceEnableStatus OBJECT-TYPE
    SYNTAX     INTEGER {
                        up(1),
                        down(2)
                       }
    MAX-ACCESS read-only
    STATUS     current
    DESCRIPTION
        "The indication of whether IPv6 is enabled (up) or disabled
         (down) on this interface.  This object does not affect the
         state of the interface itself, only its connection to an
         IPv6 stack.  The IF-MIB should be used to control the state
         of the interface."
    REFERENCE 
        "Information Model Mapping: CM-SP-R-OSSI 
         IpInterface::EnableStatus"
    ::= { docsRphyRpdIpv6InterfaceEntry 2 }

docsRphyRpdIpv6InterfaceReachableTime OBJECT-TYPE
    SYNTAX     Unsigned32
    UNITS      "milliseconds"
    MAX-ACCESS read-only
    STATUS     current
    DESCRIPTION
        "The time a neighbor is considered reachable after receiving
         a reachability confirmation."
    REFERENCE 
        "Information Model Mapping: CM-SP-R-OSSI 
         IpV6Interface::ReachableTime"
    ::= { docsRphyRpdIpv6InterfaceEntry 3 }

docsRphyRpdIpv6InterfaceRetransmitTime OBJECT-TYPE
    SYNTAX     Unsigned32
    UNITS      "milliseconds"
    MAX-ACCESS read-only
    STATUS     current
    DESCRIPTION
        "The time between retransmissions of Neighbor Solicitation
         messages to a neighbor when resolving the address or when
         probing the reachability of a neighbor."
    REFERENCE 
        "Information Model Mapping: CM-SP-R-OSSI 
         IpInterface::RetransmitTime"
    ::= { docsRphyRpdIpv6InterfaceEntry 4 }

-- ---------------------------------------------------------------------
-- Per-Interface IP Statistics Table
-- ---------------------------------------------------------------------

docsRphyRpdIpIfStatsTable OBJECT-TYPE
    SYNTAX     SEQUENCE OF DocsRphyRpdIpIfStatsEntry
    MAX-ACCESS not-accessible
    STATUS     current
    DESCRIPTION
        "This table provides statistics for IP Packets sent or 
         received by an RPD's own IP Address.
         It is modeled after the IP-MIB IpIfStatsTable described in 
         RFC 4293; however, all counters are 64 bit.
         Discontinuities in the value of these counters can occur at 
         re-initialization of the management system, and at other 
         times as indicated by the value of the DiscontinuityTime 
         attribute in this table.
         The CCAP Core reads all attributes of an IpIfStats object 
         with complex GCP TLV Type 100.14."
    REFERENCE 
        "Information Model Mapping: CM-SP-R-OSSI 
         IpIfStats"
    ::= { docsRphyRpdIpMibObjects 5 }

docsRphyRpdIpIfStatsEntry OBJECT-TYPE
    SYNTAX     DocsRphyRpdIpIfStatsEntry
    MAX-ACCESS not-accessible
    STATUS     current
    DESCRIPTION
        "An interface statistics entry containing objects for a
         particular interface and version of IP."
    INDEX { docsRphyRpdDevInfoUniqueId,
            docsRphyRpdIpIfStatsIPVersion, 
            docsRphyRpdIfEnetPortIndex }
    ::= { docsRphyRpdIpIfStatsTable 1 }

DocsRphyRpdIpIfStatsEntry ::= SEQUENCE 
    {
    docsRphyRpdIpIfStatsIPVersion           InetVersion,
    docsRphyRpdIpIfStatsInReceives          Counter64,
    docsRphyRpdIpIfStatsInOctets            Counter64,
    docsRphyRpdIpIfStatsInHdrErrors         Counter64,
    docsRphyRpdIpIfStatsInNoRoutes          Counter64,
    docsRphyRpdIpIfStatsInAddrErrors        Counter64,
    docsRphyRpdIpIfStatsInUnknownProtos     Counter64,
    docsRphyRpdIpIfStatsInTruncatedPkts     Counter64,
    docsRphyRpdIpIfStatsInDiscards          Counter64,      
    docsRphyRpdIpIfStatsInDelivers          Counter64,        
    docsRphyRpdIpIfStatsOutRequests         Counter64,      
    docsRphyRpdIpIfStatsOutDiscards         Counter64,
    docsRphyRpdIpIfStatsOutTransmits        Counter64,  
    docsRphyRpdIpIfStatsOutOctets           Counter64,    
    docsRphyRpdIpIfStatsInMcastPkts         Counter64,   
    docsRphyRpdIpIfStatsInMcastOctets       Counter64,  
    docsRphyRpdIpIfStatsOutMcastPkts        Counter64,
    docsRphyRpdIpIfStatsOutMcastOctets      Counter64,
    docsRphyRpdIpIfStatsDiscontinuityTime   DateAndTime,
    docsRphyRpdIpIfStatsRefreshRate         Unsigned32
    }

docsRphyRpdIpIfStatsIPVersion OBJECT-TYPE
    SYNTAX     InetVersion
    MAX-ACCESS not-accessible
    STATUS     current
    DESCRIPTION
        "This key attribute reports the IP version of this entry."
    ::= { docsRphyRpdIpIfStatsEntry 1 }

docsRphyRpdIpIfStatsInReceives OBJECT-TYPE
    SYNTAX     Counter64
    MAX-ACCESS read-only
    STATUS     current
    DESCRIPTION
        "The total number of input IP datagrams received, including
         those received in error."
    ::= { docsRphyRpdIpIfStatsEntry 2 }

docsRphyRpdIpIfStatsInOctets OBJECT-TYPE
    SYNTAX     Counter64
    MAX-ACCESS read-only
    STATUS     current
    DESCRIPTION
        "The total number of octets received in input IP datagrams,
         including those received in error."
    ::= { docsRphyRpdIpIfStatsEntry 3 }

docsRphyRpdIpIfStatsInHdrErrors OBJECT-TYPE
    SYNTAX     Counter64
    MAX-ACCESS read-only
    STATUS     current
    DESCRIPTION
        "The number of input IP datagrams discarded due to errors in
         their IP headers, including version number mismatch, other
         format errors, hop count exceeded, errors discovered in
         processing their IP options, etc."
    ::= { docsRphyRpdIpIfStatsEntry 4 }

docsRphyRpdIpIfStatsInNoRoutes OBJECT-TYPE
    SYNTAX     Counter64
    MAX-ACCESS read-only
    STATUS     current
    DESCRIPTION
        "The number of input IP datagrams discarded because no route
         could be found to transmit them to their destination."
    ::= { docsRphyRpdIpIfStatsEntry 5 }

docsRphyRpdIpIfStatsInAddrErrors OBJECT-TYPE
    SYNTAX     Counter64
    MAX-ACCESS read-only
    STATUS     current
    DESCRIPTION
        "The number of input IP datagrams discarded because the IP
         address in their IP header's destination field was not a
         valid address to be received at this entity.  This count
         includes invalid addresses (e.g., ::0).  For entities that
         are not IP routers and therefore do not forward datagrams,
         this counter includes datagrams discarded because the
         destination address was not a local address."
    ::= { docsRphyRpdIpIfStatsEntry 6 }

docsRphyRpdIpIfStatsInUnknownProtos OBJECT-TYPE
    SYNTAX     Counter64
    MAX-ACCESS read-only
    STATUS     current
    DESCRIPTION
        "The number of locally-addressed IP datagrams received
         successfully but discarded because of an unknown or
         unsupported protocol.

         When tracking interface statistics, the counter of the
         interface to which these datagrams were addressed is
         incremented.  This interface might not be the same as the
         input interface for some of the datagrams."
    ::= { docsRphyRpdIpIfStatsEntry 7 }

docsRphyRpdIpIfStatsInTruncatedPkts OBJECT-TYPE
    SYNTAX     Counter64
    MAX-ACCESS read-only
    STATUS     current
    DESCRIPTION
        "The number of input IP datagrams discarded because the
         datagram frame didn't carry enough data."
    ::= { docsRphyRpdIpIfStatsEntry 8 }

docsRphyRpdIpIfStatsInDiscards OBJECT-TYPE
    SYNTAX     Counter64
    MAX-ACCESS read-only
    STATUS     current
    DESCRIPTION
        "The number of input IP datagrams for which no problems were
         encountered to prevent their continued processing, but
         were discarded (e.g., for lack of buffer space).  Note that
         this counter does not include any datagrams discarded while
         awaiting re-assembly."
    ::= { docsRphyRpdIpIfStatsEntry 9 }

docsRphyRpdIpIfStatsInDelivers OBJECT-TYPE
    SYNTAX     Counter64
    MAX-ACCESS read-only
    STATUS     current
    DESCRIPTION
        "The total number of datagrams successfully delivered to IP
         user-protocols (including ICMP)."
    ::= { docsRphyRpdIpIfStatsEntry 10 }

docsRphyRpdIpIfStatsOutRequests OBJECT-TYPE
    SYNTAX     Counter64
    MAX-ACCESS read-only
    STATUS     current
    DESCRIPTION
        "The total number of IP datagrams that local IP user-
         protocols (including ICMP) supplied to IP in requests for
         transmission."
    ::= { docsRphyRpdIpIfStatsEntry 11 }

docsRphyRpdIpIfStatsOutDiscards OBJECT-TYPE
    SYNTAX     Counter64
    MAX-ACCESS read-only
    STATUS     current
    DESCRIPTION
        "The number of output IP datagrams for which no problem was
         encountered to prevent their transmission to their
         destination, but were discarded (e.g., for lack of
         buffer space).  Note that this counter would include
         datagrams counted in docsRphyRpdIpIfStatsOutForwDatagrams if any such
         datagrams met this (discretionary) discard criterion."
    ::= { docsRphyRpdIpIfStatsEntry 12 }

docsRphyRpdIpIfStatsOutTransmits OBJECT-TYPE
    SYNTAX     Counter64
    MAX-ACCESS read-only
    STATUS     current
    DESCRIPTION
        "The total number of IP datagrams that this entity supplied
         to the lower layers for transmission."
    ::= { docsRphyRpdIpIfStatsEntry 13 }

docsRphyRpdIpIfStatsOutOctets OBJECT-TYPE
    SYNTAX     Counter64
    MAX-ACCESS read-only
    STATUS     current
    DESCRIPTION
        "The total number of octets in IP datagrams delivered to the
         lower layers for transmission."
    ::= { docsRphyRpdIpIfStatsEntry 14 }

docsRphyRpdIpIfStatsInMcastPkts OBJECT-TYPE
    SYNTAX     Counter64
    MAX-ACCESS read-only
    STATUS     current
    DESCRIPTION
           "The number of IP multicast datagrams received."
    ::= { docsRphyRpdIpIfStatsEntry 15 }

docsRphyRpdIpIfStatsInMcastOctets OBJECT-TYPE
    SYNTAX     Counter64
    MAX-ACCESS read-only
    STATUS     current
    DESCRIPTION
        "The total number of octets received in IP multicast
         datagrams."
    ::= { docsRphyRpdIpIfStatsEntry 16 }

docsRphyRpdIpIfStatsOutMcastPkts OBJECT-TYPE
    SYNTAX     Counter64
    MAX-ACCESS read-only
    STATUS     current
    DESCRIPTION
           "The number of IP multicast datagrams transmitted."
    ::= { docsRphyRpdIpIfStatsEntry 17 }

docsRphyRpdIpIfStatsOutMcastOctets OBJECT-TYPE
    SYNTAX     Counter64
    MAX-ACCESS read-only
    STATUS     current
    DESCRIPTION
        "The total number of octets transmitted in IP multicast
         datagrams."
    ::= { docsRphyRpdIpIfStatsEntry 18 }

docsRphyRpdIpIfStatsDiscontinuityTime OBJECT-TYPE
    SYNTAX     DateAndTime
    MAX-ACCESS read-only
    STATUS     current
    DESCRIPTION
        "This attribute reports the date and time at which any 
         one or more of the counters in this group were created or 
         last reset to zero. If the RPD does not acquire time of day 
         it can report an initial CounterDiscontinuityTime of Jan 1 1970. 
         If the value returned by the RPD is the initial Epoch of Jan 1 1970, 
         the CCAP Core can convert this value to the real time of day based 
         on a calculation using the RPD's reported sysUpTime."
    ::= { docsRphyRpdIpIfStatsEntry 19 }

docsRphyRpdIpIfStatsRefreshRate OBJECT-TYPE
    SYNTAX     Unsigned32
    UNITS "milli-seconds"
    MAX-ACCESS read-only
    STATUS     current
    DESCRIPTION
        "The minimum reasonable polling interval for this entry.
         This object provides an indication of the minimum amount of
         time required to update the counters in this entry."
    ::= { docsRphyRpdIpIfStatsEntry 20 }


-- ---------------------------------------------------------------------
-- Internet Address Table
-- ---------------------------------------------------------------------

docsRphyRpdIpAddressTable OBJECT-TYPE
    SYNTAX     SEQUENCE OF DocsRphyRpdIpAddressEntry
    MAX-ACCESS not-accessible
    STATUS     current
    DESCRIPTION
        "This table contains addressing information relevant to the
         RPD's interfaces.

         This table does not contain multicast address information.

         Note well: When instantiating IPv6 link-local addresses for 
         this table, the instance uses an InetAddressType of 'ipv6z' and
         GCP TLV 100.15.2 with value field length of 20 in order to 
         differentiate between the possible interfaces.
         The CCAP Core reads all attributes of an IpAddress object 
         with complex GCP TLV Type 100.15."
    REFERENCE 
        "Information Model Mapping: CM-SP-R-OSSI 
         IpAddress"
    ::= { docsRphyRpdIpMibObjects 6 }

docsRphyRpdIpAddressEntry OBJECT-TYPE
    SYNTAX     DocsRphyRpdIpAddressEntry
    MAX-ACCESS not-accessible
    STATUS     current
    DESCRIPTION
           "An address mapping for a particular interface."
    INDEX { docsRphyRpdDevInfoUniqueId,
            docsRphyRpdIpAddressAddrType, 
            docsRphyRpdIpAddressAddr }
    ::= { docsRphyRpdIpAddressTable 1 }

DocsRphyRpdIpAddressEntry ::= SEQUENCE 
    {
    docsRphyRpdIpAddressAddrType       InetAddressType,
    docsRphyRpdIpAddressAddr           InetAddress,
    docsRphyRpdIpAddressEnetPortIndex  Unsigned32,
    docsRphyRpdIpAddressType           INTEGER,
    docsRphyRpdIpAddressPrefixLen      InetAddressPrefixLength,
    docsRphyRpdIpAddressOrigin         IpAddressOriginTC,
    docsRphyRpdIpAddressStatus         IpAddressStatusTC,
    docsRphyRpdIpAddressCreated        TimeStamp,
    docsRphyRpdIpAddressLastChanged    TimeStamp
    }

docsRphyRpdIpAddressAddrType OBJECT-TYPE
    SYNTAX     InetAddressType    
    MAX-ACCESS not-accessible
    STATUS     current
    DESCRIPTION
        "The address type of docsRphyRpdIpAddressAddr."
    REFERENCE 
        "Information Model Mapping: CM-SP-R-OSSI 
         IpAddress::AddrType"
    ::= { docsRphyRpdIpAddressEntry 1 }

docsRphyRpdIpAddressAddr OBJECT-TYPE
    SYNTAX     InetAddress  (SIZE (4|16))
    MAX-ACCESS not-accessible
    STATUS     current
    DESCRIPTION
        "The IP address to which this entry's addressing information
         pertains.  The address type of this object is specified in
         AddrType."
    REFERENCE 
        "Information Model Mapping: CM-SP-R-OSSI 
         IpAddress::IpAddress"
    ::= { docsRphyRpdIpAddressEntry 2 }

docsRphyRpdIpAddressEnetPortIndex OBJECT-TYPE
    SYNTAX     Unsigned32 (0..255)
    MAX-ACCESS read-only
    STATUS     current
    DESCRIPTION
        "This attribute reports a unique index for this 
         Ethernet port interface."
    REFERENCE 
        "Information Model Mapping: CM-SP-R-OSSI 
         IpAddress::EnetPortIndex"
    ::= { docsRphyRpdIpAddressEntry 3 }

docsRphyRpdIpAddressType OBJECT-TYPE
    SYNTAX     INTEGER {
             unicast(1),
             anycast(2),
             broadcast(3)
    }
    MAX-ACCESS read-only
    STATUS     current
    DESCRIPTION
        "The type of address.  broadcast(3) is not a valid value for
         IPv6 addresses (RFC 3513)."
    REFERENCE 
        "Information Model Mapping: CM-SP-R-OSSI 
         IpAddress::Type"
    ::= { docsRphyRpdIpAddressEntry 4 }

docsRphyRpdIpAddressPrefixLen OBJECT-TYPE
    SYNTAX     InetAddressPrefixLength
    MAX-ACCESS read-only
    STATUS     current
    DESCRIPTION
        "This attribute reports the prefix length associated 
         with this address."
    REFERENCE 
        "Information Model Mapping: CM-SP-R-OSSI 
         IpAddress::PrefixLen"
    ::= { docsRphyRpdIpAddressEntry 5 }

docsRphyRpdIpAddressOrigin OBJECT-TYPE
    SYNTAX     IpAddressOriginTC
    MAX-ACCESS read-only
    STATUS     current
    DESCRIPTION
           "The origin of the address."
    REFERENCE 
        "Information Model Mapping: CM-SP-R-OSSI 
         IpAddress::Origin"
    ::= { docsRphyRpdIpAddressEntry 6 }

docsRphyRpdIpAddressStatus OBJECT-TYPE
    SYNTAX     IpAddressStatusTC
    MAX-ACCESS read-only
    STATUS     current
    DESCRIPTION
        "The status of the address, describing if the address can be
         used for communication.

         In the absence of other information, an IPv4 address is
         always preferred(1)."
    REFERENCE 
        "Information Model Mapping: CM-SP-R-OSSI 
         IpAddress::Status"
    ::= { docsRphyRpdIpAddressEntry 7 }

docsRphyRpdIpAddressCreated OBJECT-TYPE
    SYNTAX     TimeStamp
    MAX-ACCESS read-only
    STATUS     current
    DESCRIPTION
        "The value of sysUpTime at the time this entry was created.
         If this entry was created prior to the last re-
         initialization of the local network management subsystem,
         then this object contains a zero value."
    REFERENCE 
        "Information Model Mapping: CM-SP-R-OSSI 
         IpAddress::Created"
    ::= { docsRphyRpdIpAddressEntry 8 }

docsRphyRpdIpAddressLastChanged OBJECT-TYPE
    SYNTAX     TimeStamp
    MAX-ACCESS read-only
    STATUS     current
    DESCRIPTION
        "The value of sysUpTime at the time this entry was last
         updated.  If this entry was updated prior to the last re-
         initialization of the local network management subsystem,
         then this object contains a zero value."
    REFERENCE 
        "Information Model Mapping: CM-SP-R-OSSI 
         IpAddress::LastChanged"
    ::= { docsRphyRpdIpAddressEntry 9 }
    

-- ---------------------------------------------------------------------
-- Internet Address Translation Table
-- ---------------------------------------------------------------------

docsRphyRpdIpNetToPhysicalTable OBJECT-TYPE
    SYNTAX     SEQUENCE OF DocsRphyRpdIpNetToPhysicalEntry
    MAX-ACCESS not-accessible
    STATUS     current
    DESCRIPTION
        "The IP Address Translation table used for mapping from IP
         addresses to physical addresses.

         The Address Translation tables contain the IP address to
         'physical' address equivalences.  Some interfaces do not use
         translation tables for determining address equivalences
         (e.g., DDN-X.25 has an algorithmic method); if all
         interfaces are of this type, then the Address Translation
         table is empty, i.e., has zero entries.

         While many protocols may be used to populate this table, ARP
         and Neighbor Discovery are the most likely
         options.  The CCAP Core reads all attributes of an 
         IpNetToPhysical object with complex GCP TLV Type 100.16."
    REFERENCE 
        "Information Model Mapping: CM-SP-R-OSSI 
         IpNetToPhysical"
    ::= { docsRphyRpdIpMibObjects 7 }

docsRphyRpdIpNetToPhysicalEntry OBJECT-TYPE
    SYNTAX     DocsRphyRpdIpNetToPhysicalEntry
    MAX-ACCESS not-accessible
    STATUS     current
    DESCRIPTION
        "Each entry contains one IP address to 'physical' address
         equivalence."
    INDEX    { docsRphyRpdDevInfoUniqueId,
               docsRphyRpdIfEnetPortIndex,
               docsRphyRpdIpNetToPhysicalNetAddressType,
               docsRphyRpdIpNetToPhysicalNetAddress }
    ::= { docsRphyRpdIpNetToPhysicalTable 1 }

DocsRphyRpdIpNetToPhysicalEntry ::= SEQUENCE 
    {
    docsRphyRpdIpNetToPhysicalNetAddressType  InetAddressType,
    docsRphyRpdIpNetToPhysicalNetAddress      InetAddress,
    docsRphyRpdIpNetToPhysicalPhysAddress     PhysAddress,
    docsRphyRpdIpNetToPhysicalLastUpdated     TimeStamp,
    docsRphyRpdIpNetToPhysicalType            INTEGER,
    docsRphyRpdIpNetToPhysicalState           INTEGER
    }

docsRphyRpdIpNetToPhysicalNetAddressType OBJECT-TYPE
    SYNTAX     InetAddressType   
    MAX-ACCESS not-accessible
    STATUS     current
    DESCRIPTION
        "The type of NetAddress."
    REFERENCE 
        "Information Model Mapping: CM-SP-R-OSSI 
         IpNetToPhysical::AddrType"
    ::= { docsRphyRpdIpNetToPhysicalEntry 1 }

docsRphyRpdIpNetToPhysicalNetAddress OBJECT-TYPE
    SYNTAX     InetAddress  (SIZE(4|16))
    MAX-ACCESS not-accessible
    STATUS     current
    DESCRIPTION
        "The IP Address corresponding to the media-dependent
         'physical' address.  The address type of this object is
         specified in AddressType."
    REFERENCE 
        "Information Model Mapping: CM-SP-R-OSSI 
         IpNetToPhysical::IpAddress"
    ::= { docsRphyRpdIpNetToPhysicalEntry 2 }

docsRphyRpdIpNetToPhysicalPhysAddress OBJECT-TYPE
    SYNTAX     PhysAddress (SIZE(0..65535))
    MAX-ACCESS read-only
    STATUS     current
    DESCRIPTION
        "The media-dependent 'physical' address."
    REFERENCE 
        "Information Model Mapping: CM-SP-R-OSSI 
         IpNetToPhysical::PhyAddress"
    ::= { docsRphyRpdIpNetToPhysicalEntry 3 }

docsRphyRpdIpNetToPhysicalLastUpdated OBJECT-TYPE
    SYNTAX     TimeStamp
    MAX-ACCESS read-only
    STATUS     current
    DESCRIPTION
        "This attribute reports the value of RpdSysUpTime at the time
         this entry was last updated.  If this entry was updated 
         prior to the last re-initialization of the local network 
         management subsystem, then this attribute contains a 
         zero value."
    REFERENCE 
        "Information Model Mapping: CM-SP-R-OSSI 
         IpNetToPhysical::LastUpdated"
    ::= { docsRphyRpdIpNetToPhysicalEntry 4 }

docsRphyRpdIpNetToPhysicalType OBJECT-TYPE
    SYNTAX     INTEGER {
                        other(1),        -- none of the following
                        invalid(2),      -- an invalidated mapping
                        dynamic(3),
                        static(4),
                        local(5)         -- local interface
                       }
    MAX-ACCESS read-only
    STATUS     current
    DESCRIPTION
        "The type of mapping. It is an
         implementation-specific matter as to whether the agent
         removes an invalidated entry from the table.  Accordingly,
         management stations must be prepared to receive tabular
         information from agents that corresponds to entries not
         currently in use.  Proper interpretation of such entries
         requires examination of the relevant Type
         attribute.

         The 'dynamic(3)' type indicates that the IP address to
         physical addresses mapping has been dynamically resolved
         using e.g., IPv4 ARP or the IPv6 Neighbor Discovery
         protocol.

         The 'static(4)' type indicates that the mapping has been
         statically configured.  Both of these refer to entries that
         provide mappings for other entities addresses.

         The 'local(5)' type indicates that the mapping is provided
         for an entity's own interface address."
    REFERENCE 
        "Information Model Mapping: CM-SP-R-OSSI 
         IpNetToPhysical::Type"
    ::= { docsRphyRpdIpNetToPhysicalEntry 5 }

docsRphyRpdIpNetToPhysicalState OBJECT-TYPE
    SYNTAX     INTEGER {
                        reachable(1), -- confirmed reachability

                        stale(2),     -- unconfirmed reachability

                        delay(3),     -- waiting for reachability
                                      -- confirmation before entering
                                      -- the probe state

                        probe(4),     -- actively probing

                        invalid(5),   -- an invalidated mapping

                        unknown(6),   -- state can not be determined
                                      -- for some reason.

                        incomplete(7) -- address resolution is being
                                      -- performed.
                        }
    MAX-ACCESS read-only
    STATUS     current
    DESCRIPTION
        "The Neighbor Unreachability Detection state for the
         interface when the address mapping in this entry is used.
         If Neighbor Unreachability Detection is not in use (e.g. for
         IPv4), this object is always unknown(6)."
    REFERENCE 
        "Information Model Mapping: CM-SP-R-OSSI 
         IpNetToPhysical::State"
    ::= { docsRphyRpdIpNetToPhysicalEntry 6 }

-- ---------------------------------------------------------------------
-- Default Router Table
-- ---------------------------------------------------------------------

docsRphyRpdIpDefaultRouterTable OBJECT-TYPE
    SYNTAX     SEQUENCE OF DocsRphyRpdIpDefaultRouterEntry
    MAX-ACCESS not-accessible
    STATUS     current
    DESCRIPTION
        "The table used to describe the default routers known to the
         RPD. The CCAP Core reads all attributes of an IpDefaultRouter 
         object with complex GCP TLV Type 100.17."
    REFERENCE 
        "Information Model Mapping: CM-SP-R-OSSI 
         IpDefaultRouter"
    ::= { docsRphyRpdIpMibObjects 8 }

docsRphyRpdIpDefaultRouterEntry OBJECT-TYPE
    SYNTAX     DocsRphyRpdIpDefaultRouterEntry
    MAX-ACCESS not-accessible
    STATUS     current
    DESCRIPTION
        "Each entry contains information about a default router known
         to the RPD."
    INDEX { docsRphyRpdDevInfoUniqueId,
            docsRphyRpdIpDefaultRouterAddressType, 
            docsRphyRpdIpDefaultRouterAddress,
            docsRphyRpdIfEnetPortIndex }
    ::= { docsRphyRpdIpDefaultRouterTable 1 }

DocsRphyRpdIpDefaultRouterEntry ::= SEQUENCE 
    {
    docsRphyRpdIpDefaultRouterAddressType  InetAddressType,
    docsRphyRpdIpDefaultRouterAddress      InetAddress,
    docsRphyRpdIpDefaultRouterLifetime     Unsigned32,
    docsRphyRpdIpDefaultRouterPreference   INTEGER
    }

docsRphyRpdIpDefaultRouterAddressType OBJECT-TYPE
    SYNTAX     InetAddressType    
    MAX-ACCESS not-accessible
    STATUS     current
    DESCRIPTION
        "This key attribute reports the type of IP address in the 
         Address attribute."
    REFERENCE 
        "Information Model Mapping: CM-SP-R-OSSI 
         IpDefaultRouter::AddrType"
    ::= { docsRphyRpdIpDefaultRouterEntry 1 }

docsRphyRpdIpDefaultRouterAddress OBJECT-TYPE
    SYNTAX     InetAddress  (SIZE (4|16))
    MAX-ACCESS not-accessible
    STATUS     current
    DESCRIPTION
        "The IP address of the default router represented by this
         row.  The address type of this object is specified in
         AddressType."
    REFERENCE 
        "Information Model Mapping: CM-SP-R-OSSI 
         IpDefaultRouter::IpAddress"
    ::= { docsRphyRpdIpDefaultRouterEntry 2 }

docsRphyRpdIpDefaultRouterLifetime OBJECT-TYPE
    SYNTAX     Unsigned32 (0..65535)
    UNITS      "seconds"
    MAX-ACCESS read-only
    STATUS     current
    DESCRIPTION
        "The remaining length of time, in seconds, that this router
         will continue to be useful as a default router.  A value of
         zero indicates that it is no longer useful as a default
         router.  It is left to the implementer of the MIB as to
         whether a router with a lifetime of zero is removed from the
         list.

         For IPv6, this value should be extracted from the router
         advertisement messages."
    REFERENCE 
        "Information Model Mapping: CM-SP-R-OSSI 
         IpDefaultRouter::Lifetime"
    ::= { docsRphyRpdIpDefaultRouterEntry 3 }

docsRphyRpdIpDefaultRouterPreference OBJECT-TYPE
    SYNTAX      INTEGER {
                         reserved(-2),
                         low(-1),
                         medium(0),
                         high(1)
                        }
    MAX-ACCESS read-only
    STATUS     current
    DESCRIPTION
        "An indication of preference given to this router as a
         default router as described in the Default Router
         Preferences document.  Treating the value as a
         2 bit signed integer allows for simple arithmetic
         comparisons.

         For IPv4 routers or IPv6 routers that are not using the
         updated router advertisement format, this object is set to
         medium (0)."
    REFERENCE 
        "Information Model Mapping: CM-SP-R-OSSI 
         IpDefaultRouter::Preference"
    ::= { docsRphyRpdIpDefaultRouterEntry 4 }


-- ---------------------------------------------------------------------
-- ICMP per-version, per-message type ICMP counters Table
-- ---------------------------------------------------------------------

docsRphyRpdIpIcmpMsgStatsTable OBJECT-TYPE
    SYNTAX     SEQUENCE OF DocsRphyRpdIpIcmpMsgStatsEntry
    MAX-ACCESS not-accessible
    STATUS     current
    DESCRIPTION
        "The table of system-wide per-version, per-message type ICMP
         counters. The CCAP Core reads all attributes of an IcmpMsgStats
         object with complex GCP TLV 100.19."
    REFERENCE 
        "Information Model Mapping: CM-SP-R-OSSI 
         IcmpMsgStats"
    ::= { docsRphyRpdIpIcmpMibObjects 1 }

docsRphyRpdIpIcmpMsgStatsEntry OBJECT-TYPE
    SYNTAX     DocsRphyRpdIpIcmpMsgStatsEntry
    MAX-ACCESS not-accessible
    STATUS     current
    DESCRIPTION
        "A conceptual row in the docsRphyRpdIpIcmpMsgStatsTable.

         The system should track each ICMP type value, even if that
         ICMP type is not supported by the system.  However, a
         given row need not be instantiated unless a message of that
         type has been processed, i.e., the row for
         Type=X MAY be instantiated before but is required to be
         instantiated after the first message with Type=X is
         received or transmitted.  After receiving or transmitting
         any succeeding messages with Type=X, the relevant counter
         must be incremented."
    INDEX { docsRphyRpdDevInfoUniqueId,
            docsRphyRpdIpIcmpMsgStatsIPVersion, 
            docsRphyRpdIpIcmpMsgStatsType }
    ::= { docsRphyRpdIpIcmpMsgStatsTable 1 }

DocsRphyRpdIpIcmpMsgStatsEntry ::= SEQUENCE 
    {
    docsRphyRpdIpIcmpMsgStatsIPVersion  InetVersion,
    docsRphyRpdIpIcmpMsgStatsType       Integer32,
    docsRphyRpdIpIcmpMsgStatsInPkts     Counter64,
    docsRphyRpdIpIcmpMsgStatsOutPkts    Counter64
    }

docsRphyRpdIpIcmpMsgStatsIPVersion OBJECT-TYPE
    SYNTAX     InetVersion
    MAX-ACCESS not-accessible
    STATUS     current
    DESCRIPTION
        "The IP version of the statistics. 
         Statistics are provided for 
         each IP version supported."
    REFERENCE 
        "Information Model Mapping: CM-SP-R-OSSI 
         IcmpMsgStats::IpVersion"
    ::= { docsRphyRpdIpIcmpMsgStatsEntry 1 }

docsRphyRpdIpIcmpMsgStatsType OBJECT-TYPE
    SYNTAX     Integer32 (0..255)
    MAX-ACCESS not-accessible
    STATUS     current
    DESCRIPTION
        "The ICMP type field of the message type being counted by
         this row.

         Note that ICMP message types are scoped by the address type
         in use."
    REFERENCE 
        "Information Model Mapping: CM-SP-R-OSSI 
         IcmpMsgStats::IpType"
    ::= { docsRphyRpdIpIcmpMsgStatsEntry 2 }

docsRphyRpdIpIcmpMsgStatsInPkts OBJECT-TYPE
    SYNTAX     Counter64
    MAX-ACCESS read-only
    STATUS     current
    DESCRIPTION
        "The number of input packets for this AF and type."
    REFERENCE 
        "Information Model Mapping: CM-SP-R-OSSI 
         IcmpMsgStats::InPkts"
    ::= { docsRphyRpdIpIcmpMsgStatsEntry 3 }

docsRphyRpdIpIcmpMsgStatsOutPkts OBJECT-TYPE
    SYNTAX     Counter64
    MAX-ACCESS read-only
    STATUS     current
    DESCRIPTION
        "The number of output packets for this AF and type."
    REFERENCE 
        "Information Model Mapping: CM-SP-R-OSSI 
         IcmpMsgStats::OutPkts"
    ::= { docsRphyRpdIpIcmpMsgStatsEntry 4 }

-- ---------------------------------------------------------------------
-- CCAP Core Group Objects
-- ---------------------------------------------------------------------
             
-- ---------------------------------------------------------
-- Core L2TP Session Info Table 
-- ---------------------------------------------------------
             
docsRphyCcapL2tpSessionInfoTable OBJECT-TYPE
    SYNTAX      SEQUENCE OF DocsRphyCcapL2tpSessionInfoEntry
    MAX-ACCESS  not-accessible
    STATUS      current
    DESCRIPTION
        "This table provides details for every session that 
         terminates at the CCAP Core from the CCAP Core's point 
         of view. There will be multiple sessions for each RPD 
         with which the CCAP Core is associated.

         The CCAP Core must create an entry in this table for
         each DEPI, UEPI, OOB, NDF, and NDR pseudowire that it 
         terminates."
    ::= { docsRphyCcapMibObjects 1 }

docsRphyCcapL2tpSessionInfoEntry OBJECT-TYPE
    SYNTAX      DocsRphyCcapL2tpSessionInfoEntry
    MAX-ACCESS  not-accessible
    STATUS      current
    DESCRIPTION
        "The conceptual row of docsRphyCcapL2tpSessionInfoTable.
        
         A row entry is created for every session the CCAP-Core 
         terminates."
    INDEX { docsRphyCcapL2tpSessionInfoSessionIpAddrType,
            docsRphyCcapL2tpSessionInfoCcapLcceIpAddr,
            docsRphyCcapL2tpSessionInfoRpdLcceIpAddr,
            docsRphyCcapL2tpSessionInfoDirection,
            docsRphyCcapL2tpSessionInfoL2tpSessionId }
    ::= { docsRphyCcapL2tpSessionInfoTable 1 }

DocsRphyCcapL2tpSessionInfoEntry ::= SEQUENCE
    {
    docsRphyCcapL2tpSessionInfoSessionIpAddrType     InetAddressType,
    docsRphyCcapL2tpSessionInfoCcapLcceIpAddr        InetAddress,
    docsRphyCcapL2tpSessionInfoRpdLcceIpAddr         InetAddress,
    docsRphyCcapL2tpSessionInfoDirection             INTEGER,
    docsRphyCcapL2tpSessionInfoL2tpSessionId         Unsigned32,
    docsRphyCcapL2tpSessionInfoCoreId                OCTET STRING,
    docsRphyCcapL2tpSessionInfoConnCtrlID            Unsigned32,
    docsRphyCcapL2tpSessionInfoUdpPort               InetPortNumber,
    docsRphyCcapL2tpSessionInfoDescr                 SnmpAdminString,
    docsRphyCcapL2tpSessionInfoSessionType           INTEGER,
    docsRphyCcapL2tpSessionInfoSessionSubType        INTEGER,
    docsRphyCcapL2tpSessionInfoMaxPayload            Unsigned32,
    docsRphyCcapL2tpSessionInfoPathPayload           Unsigned32,
    docsRphyCcapL2tpSessionInfoRpdIfMtu              Unsigned32,
    docsRphyCcapL2tpSessionInfoCoreIfMtu             Unsigned32,
    docsRphyCcapL2tpSessionInfoIncludeDOCSISMsgs     TruthValue,
    docsRphyCcapL2tpSessionInfoErrorCode             INTEGER,
    docsRphyCcapL2tpSessionInfoCreationTime          TimeStamp,
    docsRphyCcapL2tpSessionInfoOperStatus            OperStatusType,
    docsRphyCcapL2tpSessionInfoLocalStatus           BITS,
    docsRphyCcapL2tpSessionInfoLastChange            TimeStamp,
    docsRphyCcapL2tpSessionInfoExtendedRemoteEndId   OCTET STRING
    }

docsRphyCcapL2tpSessionInfoSessionIpAddrType OBJECT-TYPE
    SYNTAX      InetAddressType    
    MAX-ACCESS  not-accessible
    STATUS      current
    DESCRIPTION 
        "This key attribute indicates whether the IP address
         provided in the CcapLcceIpAddress and RpdLcceIpAddr 
         attributes are IPv4 or IPv6."
    ::= { docsRphyCcapL2tpSessionInfoEntry 1 }

docsRphyCcapL2tpSessionInfoCcapLcceIpAddr OBJECT-TYPE
    SYNTAX      InetAddress (SIZE(4|16))
    MAX-ACCESS  not-accessible
    STATUS      current
    DESCRIPTION 
        "This key attribute provides the LCCE IP address on the
         CCAP Core of the session detailed in the instance. As
         reported by the RPD for a static multicast session, 
         this attribute is zero for an any source multicast and 
         the source IP for Source Specific Multicast (SSM)."
    ::= { docsRphyCcapL2tpSessionInfoEntry 2 }

docsRphyCcapL2tpSessionInfoRpdLcceIpAddr OBJECT-TYPE
    SYNTAX      InetAddress  (SIZE(4|16))
    MAX-ACCESS  not-accessible
    STATUS      current
    DESCRIPTION 
        "This key attribute reports the remote-side
         RPD LCCE IP address of the session detailed
         in the instance."
    ::= { docsRphyCcapL2tpSessionInfoEntry 3 }
    
docsRphyCcapL2tpSessionInfoDirection OBJECT-TYPE
    SYNTAX      INTEGER {
                         forward(0),
                         return(1)
                        }
    MAX-ACCESS  not-accessible
    STATUS      current
    DESCRIPTION 
        "This key attribute reports the direction of the session detailed in the instance.  
         Valid values include:
         'forward' - Forward (downstream) direction toward the RPD.
         'return' -  Return (upstream) direction toward the CCAP Core."
    ::= { docsRphyCcapL2tpSessionInfoEntry 4 }

docsRphyCcapL2tpSessionInfoL2tpSessionId OBJECT-TYPE
    SYNTAX      Unsigned32
    MAX-ACCESS  not-accessible
    STATUS      current
    DESCRIPTION 
        "This key attribute reports the value of the 
         L2TPv3 session ID transmitted or received on 
         the session. "
    ::= { docsRphyCcapL2tpSessionInfoEntry 5 }

    
docsRphyCcapL2tpSessionInfoCoreId OBJECT-TYPE
    SYNTAX      OCTET STRING (SIZE (6))
    MAX-ACCESS  read-only
    STATUS      current
    DESCRIPTION 
        "This attribute reports the unique identifier, for 
         example a MAC address, of the CCAP Core with which 
         this session terminates. The CCAP Core sends its unique 
         identifier to the RPD periodically via the 
         DOCSIS SYNC MAC Message in the Source Address field."
    ::= { docsRphyCcapL2tpSessionInfoEntry 6 }
    
docsRphyCcapL2tpSessionInfoConnCtrlID OBJECT-TYPE
    SYNTAX      Unsigned32
    MAX-ACCESS  read-only
    STATUS      current
    DESCRIPTION 
        "This attribute indicates the control connection
         identifier (CCID) for this session. This attribute is 
         zero for static sessions, since static sessions are not
         part of an L2TPv3 tunnel. Zero is not a legal CCID for
         established tunnels, so a non-zero value means this is
         a dynamic session."
    ::= { docsRphyCcapL2tpSessionInfoEntry 7 }
    
docsRphyCcapL2tpSessionInfoUdpPort OBJECT-TYPE
    SYNTAX      InetPortNumber
    MAX-ACCESS  read-only
    STATUS      current
    DESCRIPTION 
        "This attribute provides the UDP Port reported by the 
         CCAP Core when the DEPI session uses L2TPv3 Header Over
         UDP. This attribute reports a value of 0 when the session 
         is running with the L2TPv3 Session IP Header. 
         This port number is negotiated between the CCAP Core and 
         the RPD according to the L2TPv3 RFC."
    ::= { docsRphyCcapL2tpSessionInfoEntry 8 }
    
docsRphyCcapL2tpSessionInfoDescr OBJECT-TYPE
    SYNTAX      SnmpAdminString
    MAX-ACCESS  read-only
    STATUS      current
    DESCRIPTION 
        "This attribute provides an ASCII string constructed with
         the form:
         
         RemoteEndId=(pp:mmm:ccc), ... 
           { repeated for multiple endpoints } 

         where
         pp is the 0-based port num signaled in the RemoteEndId AVP
         mmm is the channel-type enum value from the RemoteEndId AVP 
         ccc is the channel number from the RemoteEndId AVP.

         In cases when the complete length of the description attribute
         exceeds 255 characters, the RPD MUST truncate the length to 255."
    ::= { docsRphyCcapL2tpSessionInfoEntry 9 }
    
docsRphyCcapL2tpSessionInfoSessionType OBJECT-TYPE
    SYNTAX      INTEGER {
                         psp(1),
                         mpt(2)
                        }
    MAX-ACCESS  read-only
    STATUS      current
    DESCRIPTION 
        "This attribute specifies whether the session is an MPT 
         session or PSP session."
    ::= { docsRphyCcapL2tpSessionInfoEntry 10 }
    
docsRphyCcapL2tpSessionInfoSessionSubType OBJECT-TYPE
    SYNTAX      INTEGER {
                         mptLegacy(1),
                         pspLegacy(2),
                         mcm(3),
                         pspDepiMultichannel(4),
                         pspUepiScQam(5),
                         pspUepiOfdma(6),
                         pspBwReqScQam(7),
                         pspBwReqOfdma(8),
                         pspProbe(9),
                         pspRngReqScQam(10),
                         pspRngReqOfdma(11),
                         pspMapScQam(12),
                         pspMapOfdma(13),
                         pspSpecman(14),
                         pspPnm(15),
                         psp551Fwd(16),
                         psp551Ret(17),
                         psp552Fwd(18),
                         psp552Ret(19),
                         pspNdf(20),
                         pspNdr(21),
                         pspEc(22),
                         pspZbl(23)
                        }
    MAX-ACCESS  read-only
    STATUS      current
    DESCRIPTION 
        "This attribute specifies the type of DEPI MPT or DEPI 
         PSP session."
    ::= { docsRphyCcapL2tpSessionInfoEntry 11 }

docsRphyCcapL2tpSessionInfoMaxPayload OBJECT-TYPE
    SYNTAX      Unsigned32
    MAX-ACCESS  read-only
    STATUS      current
    DESCRIPTION 
        "This attribute indicates the maximum MTU negotiated between
         the CCAP Core and the RPD during the session establishment 
         process. The MTU is the layer 3 payload of a layer 2 
         frame."
    REFERENCE
        "DEPI specification, Signaling Annex A."
    ::= { docsRphyCcapL2tpSessionInfoEntry 12 }

docsRphyCcapL2tpSessionInfoPathPayload OBJECT-TYPE
    SYNTAX      Unsigned32
    MAX-ACCESS  read-only
    STATUS      current
    DESCRIPTION 
        "This attribute indicates the maximum MTU traversing the CIN
         from CCAP Core to the RPD. This is calculated by the CCAP 
         Core by procedures such as MTU discovery as described in 
         the DEPI specification."
    REFERENCE
        "DEPI specification, Network MTU"
    ::= { docsRphyCcapL2tpSessionInfoEntry 13 }
    
docsRphyCcapL2tpSessionInfoRpdIfMtu OBJECT-TYPE
    SYNTAX      Unsigned32
    MAX-ACCESS  read-only
    STATUS      current
    DESCRIPTION 
        "This attribute provides the RPD's CIN interface MTU and is
         read as the value of the following L2TPV3 AVP transmitted 
         by the RPD during session setup:
         
         DEPI Downstream PW          UEPI Upstream PW
         DEPI Remote MTU AVP (ICRP)  UEPI Remote MTU AVP (ICRP)."
    ::= { docsRphyCcapL2tpSessionInfoEntry 14 }
    
docsRphyCcapL2tpSessionInfoCoreIfMtu OBJECT-TYPE
    SYNTAX      Unsigned32
    MAX-ACCESS  read-only
    STATUS      current
    DESCRIPTION 
        "This attribute provides the CCAP Core's CIN interface MTU
         and is read as the value of the following L2TPv3 AVP as 
         received by the device during session setup:
         
         DEPI Downstream PW          UEPI Upstream PW
         DEPI Local MTU AVP (ICRQ)   UEPI Local MTU AVP (ICRQ)."
    ::= { docsRphyCcapL2tpSessionInfoEntry 15 }

docsRphyCcapL2tpSessionInfoIncludeDOCSISMsgs OBJECT-TYPE
    SYNTAX      TruthValue
    MAX-ACCESS  read-only
    STATUS      current
    DESCRIPTION 
        "This attribute returns true if the CCAP Core includes 
         DOCSIS MAP messages and other MAC Management messages 
         in the interface entry associated with this control 
         entry. The CCAP Core determines whether the interface 
         includes DOCSIS messages as part of the payload."
    ::= { docsRphyCcapL2tpSessionInfoEntry 16 }

docsRphyCcapL2tpSessionInfoErrorCode OBJECT-TYPE
    SYNTAX      INTEGER {
                         none(1),
                         invalidMACInterfaceValue(2),
                         invalidInterfaceValue(3),
                         noResourcesForInterfaceIndex(4),
                         l2tpv3Error(5),
                         ifAdminStatusSetToDown(6)
                        }
    MAX-ACCESS  read-only
    STATUS      current
    DESCRIPTION 
        "The error code raised when the session is in an error
         state. 
         'invalidMACInterfaceValue'  
           Indicates wrong assignment of the CCAP Core MAC interface
           ifIndex.
         'invalidInterfaceValue'  
           Indicates wrong assignment of the CCAP Core Downstream 
           interface ifIndex
         'noResourcesForInterfaceIfIndex' 
           Indicates the CCAP Core has no more resources to
           assign a session to this entry.
         'l2tpv3Error'
           An L2TPv3 StopCCN or CDN message was issued 
         'ifAdminStatusSetToDown'
           Indicates the ifAdminStatus was set to down and the
           session was torn down."
    ::= { docsRphyCcapL2tpSessionInfoEntry 17 }

docsRphyCcapL2tpSessionInfoCreationTime OBJECT-TYPE
    SYNTAX      TimeStamp
    MAX-ACCESS  read-only
    STATUS      current
    DESCRIPTION 
        "The attribute contains the sysUptime when the entry was 
         turned active."
    ::= { docsRphyCcapL2tpSessionInfoEntry 18 }
    
docsRphyCcapL2tpSessionInfoOperStatus OBJECT-TYPE
    SYNTAX      OperStatusType
    MAX-ACCESS  read-only
    STATUS      current
    DESCRIPTION 
        "This attribute provides the current status of the 
         pseudowire from the point of view of the specific 
         reporting entity (CCAP-Core). For static psuedowires, 
         the only values that the RPD can report are 'up' and 
         'down'. 
         These values are conveyed to the Core via the 
         RpdCircuitStatus TLV (TLV 59.1.3)." 
    ::= { docsRphyCcapL2tpSessionInfoEntry 19 }

docsRphyCcapL2tpSessionInfoLocalStatus OBJECT-TYPE
    SYNTAX      BITS {
                      other(0),
                      pwNotForwarding(1), 
                      servicePwRxFault(2), 
                      servicePwTxFault(3), 
                      psnPwRxFault(4), 
                      psnPwTxFault(5)
                     }
    MAX-ACCESS  read-only
    STATUS      current
    DESCRIPTION 
        "The attribute provides the status of the pseudowire 
         in the local node. If the 'other' bit is set, it indicates
         that an additional vendor-specific status is reported. 
         If none of the bits are set, it indicates no faults are 
         reported."
    ::= { docsRphyCcapL2tpSessionInfoEntry 20 }
    
docsRphyCcapL2tpSessionInfoLastChange OBJECT-TYPE
    SYNTAX      TimeStamp
    MAX-ACCESS  read-only
    STATUS      current
    DESCRIPTION 
        "The attribute provides the value of sysUpTime 
         when the session entered its current OperStatus 
         state from the point of view of the specific 
         reporting entity (CCAP-Core)."
    ::= { docsRphyCcapL2tpSessionInfoEntry 21 }
    
docsRphyCcapL2tpSessionInfoExtendedRemoteEndId OBJECT-TYPE
    SYNTAX      OCTET STRING  
    MAX-ACCESS  read-only
    STATUS      current
    DESCRIPTION 
        "This attribute provides an ASCII string 
         constructed with the form:
         RemoteEndId=(pp:mmm:ccc),... { repeated for multiple channels } 

         where
         pp is the zero-based port number signaled in the RemoteEndId AVP
         mmm is the channel-type Enum value from the RemoteEndId AVP 
         ccc is the channel number from the RemoteEndId AVP
         
         This attribute conveys largely the same information
         as the Description attribute. Its longer length however
         permits communication of the complete RemoteEndId 
         description, even when the length of the string exceeds 
         255 octets."
    ::= { docsRphyCcapL2tpSessionInfoEntry 22 }
    
-- ---------------------------------------------------------
-- CCAP Core L2TP Session Flow Table 
-- ---------------------------------------------------------
             
docsRphyCcapL2tpSessionFlowTable OBJECT-TYPE
    SYNTAX      SEQUENCE OF DocsRphyCcapL2tpSessionFlowEntry
    MAX-ACCESS  not-accessible
    STATUS      current
    DESCRIPTION
        "This table represents a PSP Flow of L2TP session or for 
         those sessions, which do not have PSP Flows, represents 
         entire session. In the latter case the PSP Flow Id by 
         convention is zero."
    ::= { docsRphyCcapMibObjects 2 }

docsRphyCcapL2tpSessionFlowEntry OBJECT-TYPE
    SYNTAX      DocsRphyCcapL2tpSessionFlowEntry
    MAX-ACCESS  not-accessible
    STATUS      current
    DESCRIPTION
        "The conceptual row of docsRphyCcapL2tpSessionFlowTable.
         This is an extension to 
         docsRphyCcapL2tpSessionInfoTable for the CCAP Core."
    INDEX { docsRphyCcapL2tpSessionInfoSessionIpAddrType,
            docsRphyCcapL2tpSessionInfoCcapLcceIpAddr,
            docsRphyCcapL2tpSessionInfoRpdLcceIpAddr,
            docsRphyCcapL2tpSessionInfoDirection,
            docsRphyCcapL2tpSessionInfoL2tpSessionId,
            docsRphyCcapL2tpSessionFlowPspFlowId }
    ::= { docsRphyCcapL2tpSessionFlowTable 1 }

DocsRphyCcapL2tpSessionFlowEntry ::= SEQUENCE
    {
    docsRphyCcapL2tpSessionFlowPspFlowId   Unsigned32,
    docsRphyCcapL2tpSessionFlowPhbId       Unsigned32
    }
    
docsRphyCcapL2tpSessionFlowPspFlowId OBJECT-TYPE
    SYNTAX      Unsigned32 (0..7)
    MAX-ACCESS  not-accessible
    STATUS      current
    DESCRIPTION 
        "This key attribute identifies a PSP Flow within the session. 
         For MPT sessions and for PSP sessions which do not support 
         multiple PSP Flows, this attribute is zero"
     ::= { docsRphyCcapL2tpSessionFlowEntry 1 }

docsRphyCcapL2tpSessionFlowPhbId OBJECT-TYPE
    SYNTAX      Unsigned32 (0..255)
    MAX-ACCESS  read-only
    STATUS      current
    DESCRIPTION
        "This attribute reports the Per Hop Behavior Identifier 
         that equals the 6-bit DSCP with which the CCAP Core 
         transmits downstream L2TPv3 data packets for the flow 
         or which is signaled to the RPD for insertion in upstream
         L2TPv3 data packets transmitted by the RPD."
    ::= { docsRphyCcapL2tpSessionFlowEntry 2 }
    
-- ---------------------------------------------------------
-- CCAP Core L2TP Session Statistics Table 
-- ---------------------------------------------------------
             
docsRphyCcapL2tpSessionStatsTable OBJECT-TYPE
    SYNTAX      SEQUENCE OF DocsRphyCcapL2tpSessionStatsEntry
    MAX-ACCESS  not-accessible
    STATUS      current
    DESCRIPTION
        "This table provides statistics for every session that 
         terminates at the CCAP-Core from the CCAP Core's point of 
         view. It also provides statistics about each tunnel 
         session between the RPD and each CCAP Core with which the 
         RPD is associated from the RPD's point of view."
    ::= { docsRphyCcapMibObjects 3 }

docsRphyCcapL2tpSessionStatsEntry OBJECT-TYPE
    SYNTAX      DocsRphyCcapL2tpSessionStatsEntry
    MAX-ACCESS  not-accessible
    STATUS      current
    DESCRIPTION
        "The conceptual row of docsRphyCcapL2tpSessionStatsTable.
         This table is an augmentation of 
         docsRphyCcapL2tpSessionFlowTable."
    AUGMENTS { docsRphyCcapL2tpSessionFlowEntry }
    ::= { docsRphyCcapL2tpSessionStatsTable 1 }

DocsRphyCcapL2tpSessionStatsEntry ::= SEQUENCE
    {
    docsRphyCcapL2tpSessionStatsOutOfSeqPkts        Counter32,
    docsRphyCcapL2tpSessionStatsInPkts              Counter64,
    docsRphyCcapL2tpSessionStatsInDiscards          Counter64,
    docsRphyCcapL2tpSessionStatsOutPkts             Counter64,
    docsRphyCcapL2tpSessionStatsOutErrors           Counter64
    }
    
docsRphyCcapL2tpSessionStatsOutOfSeqPkts OBJECT-TYPE
    SYNTAX      Counter32
    MAX-ACCESS  read-only
    STATUS      current
    DESCRIPTION 
        "This attribute indicates the count of session packets that
         were received out of sequence from the point of view of the
         reporting entity. It is vendor dependent the re-sequence of 
         packets. Implementations that do not re-sequence packets 
         also increase the value of ifInDiscards for the respective 
         entry."
    ::= { docsRphyCcapL2tpSessionStatsEntry 1 }
    
 docsRphyCcapL2tpSessionStatsInPkts OBJECT-TYPE
     SYNTAX      Counter64
     MAX-ACCESS  read-only
     STATUS      current
     DESCRIPTION 
         "This attribute counts the number of received packets accepted 
          for processing above the L2TPv3 protocol layer. The InPackets 
          attribute count excludes packets dropped by the L2TPv3 protocol 
          layer itself (e.g. OutOfSequencePackets and InDiscards)."
     ::= { docsRphyCcapL2tpSessionStatsEntry 2 } 
    
 docsRphyCcapL2tpSessionStatsInDiscards OBJECT-TYPE
     SYNTAX      Counter64
     MAX-ACCESS  read-only
     STATUS      current
     DESCRIPTION 
         "This attribute counts the number of received packets discarded 
          by the L2TPv3 protocol layer itself, including those discarded 
          because they were out of sequence. The InDiscards attribute 
          count includes packets unable to be forwarded to a higher layer 
          for processing (e.g. unknown L2tpv3 session Id). Interpretation 
          of what discards are counted in this attribute is 
          vendor-specific."
     ::= { docsRphyCcapL2tpSessionStatsEntry 3 } 
    
 docsRphyCcapL2tpSessionStatsOutPkts OBJECT-TYPE
     SYNTAX      Counter64
     MAX-ACCESS  read-only
     STATUS      current
     DESCRIPTION 
         "This attribute counts the number of packets conceptually 
          attempted to be transmitted from above the L2TPv3 protocol layer. 
          The OutPackets attribute counts packets discarded by the L2TPv3 
          protocol layer itself (i.e. as counted by OutErrors)."
     ::= { docsRphyCcapL2tpSessionStatsEntry 4 }    
    
 docsRphyCcapL2tpSessionStatsOutErrors OBJECT-TYPE
     SYNTAX      Counter64
     MAX-ACCESS  read-only
     STATUS      current
     DESCRIPTION 
         "This attribute counts the number of packets attempted to be 
          transmitted from above the L2TPv3 protocol layer that could not 
          be transmitted below the L2TPv3 protocol layer itself. 
          Interpretation of what errors are counted in this attribute is 
          vendor specific."
     ::= { docsRphyCcapL2tpSessionStatsEntry 5 }     
    

-- ---------------------------------------------------------
-- CCAP Core CIN Downstream Latency Table 
-- ---------------------------------------------------------
             
docsRphyCcapCinDsLatencyTable OBJECT-TYPE
    SYNTAX      SEQUENCE OF DocsRphyCcapCinDsLatencyEntry
    MAX-ACCESS  not-accessible
    STATUS      current
    DESCRIPTION
        "This table provides measurements on the latency on the CIN
         link for the session as measured by the CCAP-Core. These 
         measurements are based on the DEPI latency measurement, 
         specified in the Remote Downstream External PHY Interface
         Specification."
    ::= { docsRphyCcapMibObjects 4 }

docsRphyCcapCinDsLatencyEntry OBJECT-TYPE
    SYNTAX      DocsRphyCcapCinDsLatencyEntry
    MAX-ACCESS  not-accessible
    STATUS      current
    DESCRIPTION
        "The conceptual row of docsRphyCcapCinLatencyTable.
         A row entry is created for every session the CCAP Core 
         terminates. This table is an augmentation of 
         docsRphyCcapL2tpSessionFlowTable for the CCAP Core."
    AUGMENTS { docsRphyCcapL2tpSessionFlowEntry }
    ::= { docsRphyCcapCinDsLatencyTable 1 }

DocsRphyCcapCinDsLatencyEntry ::= SEQUENCE
    {
    docsRphyCcapCinDsLatencyLastVal           Unsigned32,
    docsRphyCcapCinDsLatencyLastValTime       TimeStamp,
    docsRphyCcapCinDsLatencyInterval          Unsigned32
    }

docsRphyCcapCinDsLatencyLastVal OBJECT-TYPE
    SYNTAX      Unsigned32
    MAX-ACCESS  read-only
    STATUS      current
    DESCRIPTION 
        "This attribute indicates the latest latency measurement
         on this session."
    ::= { docsRphyCcapCinDsLatencyEntry 1 }

docsRphyCcapCinDsLatencyLastValTime OBJECT-TYPE
    SYNTAX      TimeStamp
    MAX-ACCESS  read-only
    STATUS      current
    DESCRIPTION 
        "This attribute indicates the sysUpTime value of the last 
         time the docsRphyCcapCinLatencyPerfLastVal attribute was 
         updated."
    ::= { docsRphyCcapCinDsLatencyEntry 2 }
    
docsRphyCcapCinDsLatencyInterval OBJECT-TYPE
    SYNTAX      Unsigned32
    MAX-ACCESS  read-only
    STATUS      current
    DESCRIPTION 
        "This attribute provides the time interval used to measure
         periodically the CIN latency per DEPI session. Active 
         measurement of CIN latency applies to active DEPI sessions 
         only. This attribute is constrained to 420 seconds to 
         prevent Master Clock counter overruns. A value zero 
         indicates no CIN latency measurements are configured to 
         be performed."
    ::= { docsRphyCcapCinDsLatencyEntry 3 }
    
-- ---------------------------------------------------------
-- CCAP Core Session CIN Downstream Latency Statistics Table 
-- ---------------------------------------------------------

docsRphyCcapSessionCinDsLatencyStatsTable OBJECT-TYPE
    SYNTAX      SEQUENCE OF DocsRphyCcapSessionCinDsLatencyStatsEntry
    MAX-ACCESS  not-accessible
    STATUS      current
    DESCRIPTION
        "This table provides sequence of recent measurements of the 
         CIN latency on the network as measured by the CCAP Core. 
         When the table is full, the oldest measurement is 
         replaced with a new one. This table is based on the
         docsIfMCmtsDepiSessionCinLatencyPerfTable object defined 
         in the DOCS-IF-M-CMTS-MIB and has been extended for 
         Remote PHY.

         The CCAP Core must report at least 10 values of the most
         recent intervals for Session CinDsLatencyStats. "
    ::= { docsRphyCcapMibObjects 5 }

docsRphyCcapSessionCinDsLatencyStatsEntry OBJECT-TYPE
    SYNTAX      DocsRphyCcapSessionCinDsLatencyStatsEntry
    MAX-ACCESS  not-accessible
    STATUS      current
    DESCRIPTION
        "The conceptual row of docsRphyCcapSessionCinDsLatencyStatsTable.
         A row entry is created for every session the CCAP Core 
         terminates. This is an extension to 
         docsRphyCcapL2tpSessionFlowTable for the CCAP Core."
    INDEX { docsRphyCcapL2tpSessionInfoSessionIpAddrType,
            docsRphyCcapL2tpSessionInfoCcapLcceIpAddr,
            docsRphyCcapL2tpSessionInfoRpdLcceIpAddr,
            docsRphyCcapL2tpSessionInfoDirection,
            docsRphyCcapL2tpSessionInfoL2tpSessionId,
            docsRphyCcapL2tpSessionFlowPspFlowId,
            docsRphyCcapSessionCinDsLatencyStatsIntervalSeq }
    ::= { docsRphyCcapSessionCinDsLatencyStatsTable 1 }

DocsRphyCcapSessionCinDsLatencyStatsEntry ::= SEQUENCE
    {
    docsRphyCcapSessionCinDsLatencyStatsIntervalSeq       Unsigned32,
    docsRphyCcapSessionCinDsLatencyStatsVal               Unsigned32,
    docsRphyCcapSessionCinDsLatencyStatsValTime           TimeStamp
    }

docsRphyCcapSessionCinDsLatencyStatsIntervalSeq OBJECT-TYPE
    SYNTAX      Unsigned32
    MAX-ACCESS  not-accessible
    STATUS      current
    DESCRIPTION 
        "This attribute indicates the interval sequence where the 
         CIN latency measurement was taken. It is valid in an 
         implementation that overrides the oldest sequence number 
         entry with the most recent measurement."
    ::= { docsRphyCcapSessionCinDsLatencyStatsEntry 1 }

docsRphyCcapSessionCinDsLatencyStatsVal OBJECT-TYPE
    SYNTAX      Unsigned32
    MAX-ACCESS  read-only
    STATUS      current
    DESCRIPTION 
        "This attribute indicates the CIN latency value measured 
         for the session referenced by this entry."
    ::= { docsRphyCcapSessionCinDsLatencyStatsEntry 2 }
    
docsRphyCcapSessionCinDsLatencyStatsValTime OBJECT-TYPE
    SYNTAX      TimeStamp
    MAX-ACCESS  read-only
    STATUS      current
    DESCRIPTION 
        "This attribute provides the sysUpTime value for the last 
         time docsRphyCcapCinLatencyPerfVal was updated."
    ::= { docsRphyCcapSessionCinDsLatencyStatsEntry 3 }

-- ---------------------------------------------------------
-- CCAP Core CW Tone Status Table 
-- ---------------------------------------------------------

docsRphyCcapCwToneStatusTable OBJECT-TYPE
    SYNTAX      SEQUENCE OF DocsRphyCcapCwToneStatusEntry
    MAX-ACCESS  not-accessible
    STATUS      current
    DESCRIPTION
        "This table has one entry for each CW tone configured on a 
         downstream RF port on an RPD. The status of the tone depends
         on whether the tone has been successfully configured on that 
         parent RPD and the state of the RPD. For an OOS RPD, the RPD 
         MUST report the status of all CW tones as 'down'."
    ::= { docsRphyCcapMibObjects 6 }

docsRphyCcapCwToneStatusEntry OBJECT-TYPE
    SYNTAX      DocsRphyCcapCwToneStatusEntry
    MAX-ACCESS  not-accessible
    STATUS      current
    DESCRIPTION
        "The conceptual row of docsRphyCcapCwToneStatusTable."
    INDEX { docsRphyRpdDevInfoUniqueId,
            docsRphyCcapCwToneStatusRfPort,
            docsRphyCcapCwToneStatusFrequency
     }
    ::= { docsRphyCcapCwToneStatusTable 1 }

DocsRphyCcapCwToneStatusEntry ::= SEQUENCE
    {
    docsRphyCcapCwToneStatusRfPort                    Unsigned32,   
    docsRphyCcapCwToneStatusFrequency                 Unsigned32,  
    docsRphyCcapCwToneStatusStatus                    INTEGER
    }

docsRphyCcapCwToneStatusRfPort OBJECT-TYPE
    SYNTAX      Unsigned32 (0..255)
    MAX-ACCESS  not-accessible
    STATUS      current
    DESCRIPTION
        "This attribute identifies the RF port for the CW tone."
    ::= { docsRphyCcapCwToneStatusEntry 1 }

docsRphyCcapCwToneStatusFrequency OBJECT-TYPE
    SYNTAX      Unsigned32 (0..4294967295)
    MAX-ACCESS  not-accessible
    STATUS      current
    DESCRIPTION
        "This attribute identifies the CW tone on an RF port on 
         the RPD, as found either in the CwTonesCfg table, if present
         for this RPD, or in DefaultCwTonesCfg table. "
    ::= { docsRphyCcapCwToneStatusEntry 2 }

docsRphyCcapCwToneStatusStatus OBJECT-TYPE
    SYNTAX      INTEGER {
                         up(1),
                         down(2),
                         configFailure(3)
                       }
    MAX-ACCESS  read-only
    STATUS      current
    DESCRIPTION 
        "This attribute provides the status of the tone on the 
         parent RPD. If the RPD is not connected, or it is connected,
         but tone configuration has not been done yet, the tone status
         is 'down'. If configuration of the tone was unsuccessful, 
         either because one or more of the GCP configuration TLVs for the 
         tone resulted in an error response or no response, or because 
         more tones were configured than are supported by the parent RPD, 
         and this is one of the extra ones, the tone status is 'configFailure'. 
         If the tone configuration was successful, the tone status is 'up'."
    ::= { docsRphyCcapCwToneStatusEntry 3 }

-- ---------------------------------------------------------
-- CCAP Upstream OFDMA FDX Echo Canceller Status Table 
-- ---------------------------------------------------------

docsRphyCcapUsOfdmaFdxEcStatusTable OBJECT-TYPE
    SYNTAX      SEQUENCE OF DocsRphyCcapUsOfdmaFdxEcStatusEntry
    MAX-ACCESS  not-accessible
    STATUS      current
    DESCRIPTION
        "This table provides status information about CCAP Core's 
         support for RPD echo canceler training protocol. A CCAP 
         Core supports a row in this table for every FDX 
         OFDMA channel."
    ::= { docsRphyCcapMibObjects 7 }

docsRphyCcapUsOfdmaFdxEcStatusEntry OBJECT-TYPE
    SYNTAX      DocsRphyCcapUsOfdmaFdxEcStatusEntry
    MAX-ACCESS  not-accessible
    STATUS      current
    DESCRIPTION
        "The conceptual row of docsRphyCcapUsOfdmaFdxEcStatusTable."
    INDEX { ifIndex }
    ::= { docsRphyCcapUsOfdmaFdxEcStatusTable 1 }

DocsRphyCcapUsOfdmaFdxEcStatusEntry ::= SEQUENCE
    {
    docsRphyCcapUsOfdmaFdxEcStatusCurrentEctPeriod                 Unsigned32,   
    docsRphyCcapUsOfdmaFdxEcStatusCurrentEctoDuration              Unsigned32,
    docsRphyCcapUsOfdmaFdxEcStatusLastRequestEctPeriod             Unsigned32,
    docsRphyCcapUsOfdmaFdxEcStatusLastRequestEctoDuration          Unsigned32,
    docsRphyCcapUsOfdmaFdxEcStatusNumTxEctos                       Counter64,
    docsRphyCcapUsOfdmaFdxEcStatusNumRxEcRequestBlocks             Counter64,
    docsRphyCcapUsOfdmaFdxEcStatusNumRxEcRequestBlocksNoConv       Counter64
    }
    
docsRphyCcapUsOfdmaFdxEcStatusCurrentEctPeriod  OBJECT-TYPE
    SYNTAX      Unsigned32 (0..65535)
    UNITS       "Milliseconds"
    MAX-ACCESS  read-only
    STATUS      current
    DESCRIPTION
        "This attribute reports the current echo cancelation 
         training period for the channel. The CCAP Core 
         reports zero if no ECTO has been scheduled yet."
    ::= { docsRphyCcapUsOfdmaFdxEcStatusEntry 1 } 

docsRphyCcapUsOfdmaFdxEcStatusCurrentEctoDuration  OBJECT-TYPE
    SYNTAX      Unsigned32 (0..65535)
    UNITS       "OFDMA Symbols"
    MAX-ACCESS  read-only
    STATUS      current
    DESCRIPTION
        "This attribute reports the current echo cancelation 
         training opportunity duration for the channel. 
         The CCAP Core reports zero if no ECTO has been 
         scheduled yet."
    ::= { docsRphyCcapUsOfdmaFdxEcStatusEntry 2 }  

docsRphyCcapUsOfdmaFdxEcStatusLastRequestEctPeriod  OBJECT-TYPE
    SYNTAX      Unsigned32 (0..65535)
    MAX-ACCESS  read-only
    STATUS      current
    DESCRIPTION
        "This attribute reports the last cancelation training period
         requested by the RPD for the channel. The CCAP Core reports
         zero if no ECT request has been received yet."
    ::= { docsRphyCcapUsOfdmaFdxEcStatusEntry 3 } 

docsRphyCcapUsOfdmaFdxEcStatusLastRequestEctoDuration  OBJECT-TYPE
    SYNTAX      Unsigned32 (0..65535)
    MAX-ACCESS  read-only
    STATUS      current
    DESCRIPTION
        "This attribute reports the last cancelation training 
         opportunity duration requested by the RPD for the channel.
         The CCAP Core reports zero if no ECT request has been 
         received yet."
    ::= { docsRphyCcapUsOfdmaFdxEcStatusEntry 4 }

docsRphyCcapUsOfdmaFdxEcStatusNumTxEctos  OBJECT-TYPE
    SYNTAX      Counter64
    MAX-ACCESS  read-only
    STATUS      current
    DESCRIPTION
        "This attribute reports the number of transmitted 
         echo canceller training opportunities for the channel."
    ::= { docsRphyCcapUsOfdmaFdxEcStatusEntry 5 }

docsRphyCcapUsOfdmaFdxEcStatusNumRxEcRequestBlocks  OBJECT-TYPE
    SYNTAX      Counter64
    MAX-ACCESS  read-only
    STATUS      current
    DESCRIPTION
        "This attribute reports the number of received echo 
         canceller request blocks for the channel."
    ::= { docsRphyCcapUsOfdmaFdxEcStatusEntry 6 }
    
docsRphyCcapUsOfdmaFdxEcStatusNumRxEcRequestBlocksNoConv  OBJECT-TYPE
    SYNTAX      Counter64
    MAX-ACCESS  read-only
    STATUS      current
    DESCRIPTION
        "This attribute reports the number of received echo canceller
         request blocks with indication of loss of EC convergence
         for the channel."
    ::= { docsRphyCcapUsOfdmaFdxEcStatusEntry 7 } 

-- ---------------------------------------------------------------------
-- CCAP Tunnel Replace Failures (TRF) Statistics
-- ---------------------------------------------------------------------

docsRphyCcapTrfStats   OBJECT IDENTIFIER ::= { docsRphyCcapMibObjects 8 } 
   
docsRphyCcapTrfStatsTunnelReplacements  OBJECT-TYPE
    SYNTAX      Counter32  
    MAX-ACCESS  read-only
    STATUS      current
    DESCRIPTION
        "This attribute counts the number of tunnels successfully 
         replaced by the CCAP Core as a result of the transmission
         of an SCCRQ containing a DEPI Replaced Tunnel ID AVP 
         identifying the tunnel to be replaced."
    REFERENCE 
        "Information Model Mapping: CM-SP-R-OSSI 
         CcapTrfStats::TunnelReplacements"
    ::= { docsRphyCcapTrfStats 1 } 

docsRphyCcapTrfStatsTunnelReplacementFailures  OBJECT-TYPE
    SYNTAX      Counter32  
    MAX-ACCESS  read-only
    STATUS      current
    DESCRIPTION
        "This attribute counts the number of tunnel replacement 
         attempts, following the transmission of an SCCRQ containing
         a DEPI Replaced Tunnel ID AVP by the CCAP Core, that failed."
    REFERENCE 
        "Information Model Mapping: CM-SP-R-OSSI 
         CcapTrfStats::TunnelReplacementFailures"
    ::= { docsRphyCcapTrfStats 2 } 

docsRphyCcapTrfStatsTunnelHandovers  OBJECT-TYPE
    SYNTAX      Counter32  
    MAX-ACCESS  read-only
    STATUS      current
    DESCRIPTION
        "This attribute counts the number of tunnels transitioned
         from Standby to InService HA state as a result of the 
         transmission of a DTU message by the CCAP Core."
    REFERENCE 
        "Information Model Mapping: CM-SP-R-OSSI 
         CcapTrfStats::TunnelHandovers"
    ::= { docsRphyCcapTrfStats 3 } 
    
-- ---------------------------------------------------------------------
--  CCAP L2TPv3 Control Connection (LCCE) Statistics
-- ---------------------------------------------------------------------

docsRphyCcapLcceStatsTable OBJECT-TYPE
    SYNTAX      SEQUENCE OF DocsRphyCcapLcceStatsEntry
    MAX-ACCESS  not-accessible
    STATUS      current
    DESCRIPTION
        "This table is supported by the CCAP Core and is used to report
         on the DEPI L2TPv3 control connection activity between the Core
         and all the RPDs with which the Core has control connections. 
         There is an entry for each pair of RPD and CCAP Core LCCEs 
         used for DEPI L2TPv3 control connections."
    ::= { docsRphyCcapMibObjects 9}

docsRphyCcapLcceStatsEntry OBJECT-TYPE
    SYNTAX     DocsRphyCcapLcceStatsEntry
    MAX-ACCESS not-accessible
    STATUS     current
    DESCRIPTION
        "The conceptual row of docsRphyCcapLcceStatsTable."
    INDEX { 
            docsRphyCcapLcceStatsLcceIpAddrType,
            docsRphyCcapLcceStatsCcapLcceIpAddr,
            docsRphyCcapLcceStatsRpdLcceIpAddr
          }
    ::= { docsRphyCcapLcceStatsTable 1 }

DocsRphyCcapLcceStatsEntry ::= SEQUENCE
    {
     docsRphyCcapLcceStatsLcceIpAddrType          InetAddressType,
     docsRphyCcapLcceStatsCcapLcceIpAddr          InetAddress,
     docsRphyCcapLcceStatsRpdLcceIpAddr           InetAddress,
     docsRphyCcapLcceStatsCoreId                  OCTET STRING,
     docsRphyCcapLcceStatsCtrlConnEst             Counter32,
     docsRphyCcapLcceStatsCtrlConnEstFailures     Counter32,
     docsRphyCcapLcceStatsCtrlConnFailures        Counter32,
     docsRphyCcapLcceStatsCurrCtrlConn            Unsigned32
    } 
    
docsRphyCcapLcceStatsLcceIpAddrType   OBJECT-TYPE
    SYNTAX      InetAddressType    
    MAX-ACCESS  not-accessible
    STATUS      current
    DESCRIPTION 
        "This key attribute indicates whether the IP address
         provided in the CcapLcceIpAddr and RpdLcceIpAddr 
         attributes are IPv4 or IPv6."
    ::= { docsRphyCcapLcceStatsEntry 1 }

docsRphyCcapLcceStatsCcapLcceIpAddr  OBJECT-TYPE
    SYNTAX      InetAddress (SIZE(4|16))
    MAX-ACCESS  not-accessible
    STATUS      current
    DESCRIPTION 
        "This key attribute provides the LCCE IP address
         on the CCAP Core detailed in the instance. "
    ::= { docsRphyCcapLcceStatsEntry 2 }

docsRphyCcapLcceStatsRpdLcceIpAddr OBJECT-TYPE
    SYNTAX      InetAddress  (SIZE(4|16))
    MAX-ACCESS  not-accessible
    STATUS      current
    DESCRIPTION 
        "This key attribute reports the RPD LCCE
         IP address detailed in the instance."
    ::= { docsRphyCcapLcceStatsEntry 3 }
    
docsRphyCcapLcceStatsCoreId OBJECT-TYPE
    SYNTAX      OCTET STRING (SIZE (6))
    MAX-ACCESS  read-only
    STATUS      current
    DESCRIPTION 
        "This attribute reports the unique identifier
         of the CCAP Core."
    REFERENCE 
        "Information Model Mapping: CM-SP-R-OSSI 
         CcapLcceStats::CoreId"
    ::= { docsRphyCcapLcceStatsEntry 4 }
    
docsRphyCcapLcceStatsCtrlConnEst OBJECT-TYPE
    SYNTAX      Counter32
    MAX-ACCESS  read-only
    STATUS      current
    DESCRIPTION 
        "This attribute counts the number of DEPI control 
         connections successfully established between the 
         RPD and CCAP Core LCCEs."
    REFERENCE 
        "Information Model Mapping: CM-SP-R-OSSI 
         CcapLcceStats::ControlConnectionsEstablished"
    ::= { docsRphyCcapLcceStatsEntry 5 }
    
docsRphyCcapLcceStatsCtrlConnEstFailures OBJECT-TYPE
    SYNTAX      Counter32
    MAX-ACCESS  read-only
    STATUS      current
    DESCRIPTION 
        "This attribute counts the number of DEPI control 
         connections that failed during establishment 
         between the RPD and CCAP Core LCCEs."
    REFERENCE 
        "Information Model Mapping: CM-SP-R-OSSI 
         CcapLcceStats::ControlConnectionEstablishmentFailures"
    ::= { docsRphyCcapLcceStatsEntry 6 }
    
docsRphyCcapLcceStatsCtrlConnFailures OBJECT-TYPE
    SYNTAX      Counter32
    MAX-ACCESS  read-only
    STATUS      current
    DESCRIPTION 
        "This attribute counts the number of DEPI control 
         connections between the RPD and CCAP Core LCCEs in
         which a failure was detected (after successful 
         connection establishment) that led to the connection
         being closed."
    REFERENCE 
        "Information Model Mapping: CM-SP-R-OSSI 
         CcapLcceStats::ControlConnectionFailures"
    ::= { docsRphyCcapLcceStatsEntry 7 }
    
docsRphyCcapLcceStatsCurrCtrlConn OBJECT-TYPE
    SYNTAX      Unsigned32  (0..65535)
    MAX-ACCESS  read-only
    STATUS      current
    DESCRIPTION 
        "This attribute counts the number of DEPI control connections 
         that are currently operational between the RPD and CCAP Core
         LCCEs (i.e connections that are in an inService or standby state).
         Connections that have been removed are not included in the count."
    REFERENCE 
        "Information Model Mapping: CM-SP-R-OSSI 
         CcapLcceStats::CurrentControlConnections"
    ::= { docsRphyCcapLcceStatsEntry 8 }
    
-- ---------------------------------------------------------------------
--  CCAP Current Control Connections
-- ---------------------------------------------------------------------

docsRphyCcapCurrCtrlConnTable OBJECT-TYPE
    SYNTAX      SEQUENCE OF DocsRphyCcapCurrCtrlConnEntry
    MAX-ACCESS  not-accessible
    STATUS      current
    DESCRIPTION
        "This object is supported by the CCAP Core and is used
         to report on the currently operational DEPI L2TPv3 
         control connections on the CCAP Core. "
    ::= { docsRphyCcapMibObjects 10}

docsRphyCcapCurrCtrlConnEntry OBJECT-TYPE
    SYNTAX     DocsRphyCcapCurrCtrlConnEntry
    MAX-ACCESS not-accessible
    STATUS     current
    DESCRIPTION
        "The conceptual row of docsRphyCcapCurrCtrlConnTable."
    INDEX { 
            docsRphyCcapCurrCtrlConnLcceIpAddrType,
            docsRphyCcapCurrCtrlConnCcapLcceIpAddr,
            docsRphyCcapCurrCtrlConnRpdLcceIpAddr,
            docsRphyCcapCurrCtrlConnCoreConnCtrlId }
    ::= { docsRphyCcapCurrCtrlConnTable 1 }

DocsRphyCcapCurrCtrlConnEntry ::= SEQUENCE
    {
     docsRphyCcapCurrCtrlConnLcceIpAddrType    InetAddressType,
     docsRphyCcapCurrCtrlConnCcapLcceIpAddr    InetAddress,
     docsRphyCcapCurrCtrlConnRpdLcceIpAddr     InetAddress,
     docsRphyCcapCurrCtrlConnCoreConnCtrlId    Unsigned32,
     docsRphyCcapCurrCtrlConnRpdConnCtrlId     Unsigned32,
     docsRphyCcapCurrCtrlConnCoreId            OCTET STRING,
     docsRphyCcapCurrCtrlConnUdpPort           InetPortNumber,
     docsRphyCcapCurrCtrlConnHaState           INTEGER,
     docsRphyCcapCurrCtrlConnSessEstFailures   Counter32,
     docsRphyCcapCurrCtrlConnSessFailed        Counter32,
     docsRphyCcapCurrCtrlConnCurrSess          Unsigned32
    } 
    
docsRphyCcapCurrCtrlConnLcceIpAddrType  OBJECT-TYPE
    SYNTAX      InetAddressType    
    MAX-ACCESS  not-accessible
    STATUS      current
    DESCRIPTION 
        "This key attribute indicates whether the IP address
         provided in the CcapLcceIpAddr and RpdLcceIpAddr 
         attributes are IPv4 or IPv6."
    ::= { docsRphyCcapCurrCtrlConnEntry 1 }

docsRphyCcapCurrCtrlConnCcapLcceIpAddr  OBJECT-TYPE
    SYNTAX      InetAddress (SIZE(4|16))
    MAX-ACCESS  not-accessible
    STATUS      current
    DESCRIPTION 
        "This key attribute provides the LCCE IP 
         address on the CCAP Core of the control 
         connection detailed in the instance."
     ::= { docsRphyCcapCurrCtrlConnEntry 2 }

docsRphyCcapCurrCtrlConnRpdLcceIpAddr OBJECT-TYPE
    SYNTAX      InetAddress  (SIZE(4|16))
    MAX-ACCESS  not-accessible
    STATUS      current
    DESCRIPTION 
        "This key attribute reports the RPD LCCE IP 
         address of the control connection detailed 
         in the instance."
    ::= { docsRphyCcapCurrCtrlConnEntry 3 }    
    
docsRphyCcapCurrCtrlConnCoreConnCtrlId OBJECT-TYPE
    SYNTAX      Unsigned32
    MAX-ACCESS  not-accessible
    STATUS      current
    DESCRIPTION 
        "This key attribute reports the Core control connection
        identifier (CCID) for this control connection."
    REFERENCE 
        "Information Model Mapping: CM-SP-R-OSSI 
         CcapCurrentControlConnections::CoreConnCtrlId"
    ::= { docsRphyCcapCurrCtrlConnEntry 4 }
    
docsRphyCcapCurrCtrlConnRpdConnCtrlId OBJECT-TYPE
    SYNTAX      Unsigned32
    MAX-ACCESS  read-only
    STATUS      current
    DESCRIPTION 
        "This attribute reports the RPD control connection 
         identifier (CCID) for this control connection."
    REFERENCE 
        "Information Model Mapping: CM-SP-R-OSSI 
         CcapCurrentControlConnections::RpdConnCtrlId"
    ::= { docsRphyCcapCurrCtrlConnEntry 5 }
    
docsRphyCcapCurrCtrlConnCoreId OBJECT-TYPE
    SYNTAX      OCTET STRING (SIZE(6))
    MAX-ACCESS  read-only
    STATUS      current
    DESCRIPTION 
        "This attribute reports the unique identifier of the CCAP
         Core with which this control connection terminates. "
    REFERENCE 
        "Information Model Mapping: CM-SP-R-OSSI 
         CcapCurrentControlConnections::CoreId"
    ::= { docsRphyCcapCurrCtrlConnEntry 6 }
    
docsRphyCcapCurrCtrlConnUdpPort OBJECT-TYPE
    SYNTAX      InetPortNumber
    MAX-ACCESS  read-only
    STATUS      current
    DESCRIPTION 
        "This attribute reports the UDP Port reported by the RPD 
         when the DEPI control connection uses L2TPv3 Header Over UDP. 
         This attribute reports a value of 0 when the control connection
         is running with the L2TPv3 Session IP Header."
    REFERENCE 
        "Information Model Mapping: CM-SP-R-OSSI 
         CcapCurrentControlConnections::UdpPort"
    ::= { docsRphyCcapCurrCtrlConnEntry 7 } 

docsRphyCcapCurrCtrlConnHaState OBJECT-TYPE
    SYNTAX      INTEGER  {
                          other(0),
                          inService(1),
                          standby(2)
                         }
    MAX-ACCESS  read-only
    STATUS      current
    DESCRIPTION 
        "This attribute indicates the current HaState of the tunnel
         for which this DEPI control connection provides the signaling. 
         If TRF is not supported by either the Core or the RPD then 
         HaState is reported as inService."
    REFERENCE 
        "Information Model Mapping: CM-SP-R-OSSI 
         CcapCurrentControlConnections::HaState"
    ::= { docsRphyCcapCurrCtrlConnEntry 8 }
    
 docsRphyCcapCurrCtrlConnSessEstFailures OBJECT-TYPE
    SYNTAX      Counter32
    MAX-ACCESS  read-only
    STATUS      current
    DESCRIPTION 
        "This attribute counts the number of DEPI sessions that 
         failed during establishment using this control connection."
    REFERENCE 
        "Information Model Mapping: CM-SP-R-OSSI 
         CcapCurrentControlConnections::SessionEstablishmentFailures"
    ::= { docsRphyCcapCurrCtrlConnEntry 9 }
    
docsRphyCcapCurrCtrlConnSessFailed OBJECT-TYPE
    SYNTAX      Counter32
    MAX-ACCESS  read-only
    STATUS      current
    DESCRIPTION 
        "This attribute counts the number of DEPI sessions in which
        a failure was detected (after successful tunnel establishment) 
        that led to the session being closed using this control connection."
    REFERENCE 
        "Information Model Mapping: CM-SP-R-OSSI 
         CcapCurrentControlConnections::SessionsFailed"
    ::= { docsRphyCcapCurrCtrlConnEntry 10 }

docsRphyCcapCurrCtrlConnCurrSess OBJECT-TYPE
    SYNTAX      Unsigned32 (0..65535)
    MAX-ACCESS  read-only
    STATUS      current
    DESCRIPTION 
        "This attribute counts the number of current DEPI sessions 
         using this control connection (i.e., sessions that are in an
         inService or standby state). Sessions that have been removed 
         are not included in the count. "
    REFERENCE 
        "Information Model Mapping: CM-SP-R-OSSI 
         CcapCurrentControlConnections::CurrentSessions"
    ::= { docsRphyCcapCurrCtrlConnEntry 11 }

-- ---------------------------------------------------------
-- CMTS CM Reg Status Table 
-- ---------------------------------------------------------
docsRphyCmtsCmRegStatusTable OBJECT-TYPE
    SYNTAX  SEQUENCE OF DocsRphyCmtsCmRegStatusEntry
    MAX-ACCESS  not-accessible
    STATUS  current
    DESCRIPTION
        "This table extends docsIf3CmtsCmRegStatusTable
         for RPHY."
    ::= { docsRphyCmtsCmStatMibObjects 1 }

docsRphyCmtsCmRegStatusEntry OBJECT-TYPE
    SYNTAX  DocsRphyCmtsCmRegStatusEntry
    MAX-ACCESS  not-accessible
    STATUS  current
    DESCRIPTION
        "The conceptual row of docsRphyCmtsCmRegStatusTable."
    INDEX   { docsIf3CmtsCmRegStatusId }
    ::= { docsRphyCmtsCmRegStatusTable 1 }

DocsRphyCmtsCmRegStatusEntry ::= SEQUENCE
    {
    docsRphyCmtsCmRegStatusRpdUniqueId        MacAddress
    }


docsRphyCmtsCmRegStatusRpdUniqueId OBJECT-TYPE
    SYNTAX      MacAddress
    MAX-ACCESS  read-only
    STATUS      current
    DESCRIPTION
        "This attribute specifies a globally unique 6-byte 
        identifier of the RPD providing service to the CM 
        specified by the docsIf3CmtsCmRegStatusId index. 
        A compliant implementation can report Null MAC 
        address if the CM is not attached through a
        Remote PHY system."
    ::= { docsRphyCmtsCmRegStatusEntry 1 }
        
-- ---------------------------------------------------------
-- CCAP RPD to CM Map Status Table 
-- ---------------------------------------------------------
docsRphyCcapRpdToCmMapStatusTable OBJECT-TYPE
    SYNTAX      SEQUENCE OF DocsRphyCcapRpdToCmMapStatusEntry
    MAX-ACCESS  not-accessible
    STATUS      current
    DESCRIPTION
        "This table defines a mapping between an RPD 
         Unique Identifier and the corresponding CCAP Core 
         assigned CM Id (CmtsCmRegStatusId). This provides 
         lookup capabilities for CMs connected to an RPD 
         (or vice versa) and the associated US and DS RF
         Ports on the RPD.
         When it is able to learn the node RF port to which
         a CM is attached to an RPN, the CCAP Core SHOULD
         report the NodeRfPortId attribute of the
         CcapRpdToCmMapStatus object for that CM.  The
         mechanism by which the CCAP Core learns the
         NodeRfPortId of a CM is not standardized. The
         NodeRfPortId attribute can be reported whether or
         not the CM connects through an RPN capable of Partial
         Spectrum operation.
         An RPN is considered to be Partial Spectrum-capable
         per direction. If it reports the NodeRfPortId
         attribute of CcapRpdToCmMapStatus for a CM from a
         Partial Spectrum-capable RPN in either direction,
         the CCAP Core omits reporting the RpdUsRfPortNum
         and RpdDsRfPortNum attribute of CcapRpdToCmMapStatus
         and instead reports the RpdUsRfPortList and
         RpdDsRfPortList attributes."
    REFERENCE 
        "Information Model Mapping: CM-SP-R-OSSI 
         CcapRpdToCmMapStatus"
    ::= { docsRphyCmtsCmStatMibObjects 2 }

docsRphyCcapRpdToCmMapStatusEntry OBJECT-TYPE
    SYNTAX  DocsRphyCcapRpdToCmMapStatusEntry
    MAX-ACCESS  not-accessible
    STATUS  current
    DESCRIPTION
        "The conceptual row of docsRphyCcapRpdToCmMapStatusTable."
    INDEX   { docsRphyRpdDevInfoUniqueId, docsIf3CmtsCmRegStatusId }
    ::= { docsRphyCcapRpdToCmMapStatusTable 1 }

DocsRphyCcapRpdToCmMapStatusEntry ::= SEQUENCE
     {
     docsRphyCcapRpdToCmMapStatusRpdUsRfPortNum  Unsigned32,
     docsRphyCcapRpdToCmMapStatusRpdDsRfPortNum  Unsigned32,
     docsRphyCcapRpdToCmMapStatusNodeRfPortId    Unsigned32,
     docsRphyCcapRpdToCmMapStatusRpdUsRfPortList Unsigned32,
     docsRphyCcapRpdToCmMapStatusRpdDsRfPortList Unsigned32
     }


docsRphyCcapRpdToCmMapStatusRpdUsRfPortNum OBJECT-TYPE
    SYNTAX      Unsigned32  (0..4294967295)
    MAX-ACCESS  read-only
    STATUS      current
    DESCRIPTION
        "This attribute identifies the upstream RF port on 
         the RPD, for the RPD attached to the CM specified 
         by the CmId index. A CCAP Core MUST omit reporting
         RpdUsRfPortNum for an upstream Partial Spectrum-
         capable RPN.  A CCAP Core can detect this condition
         from the NodePortMapUs (TLV 50.60.18.2) sub-table
         in an IRA message."
    REFERENCE 
        "Information Model Mapping: CM-SP-R-OSSI 
         CcapRpdToCmMapStatus::RpdUsRfPortNum
         Remote PHY Specification, CM-SP-R-PHY-I17-220531
         Partial Spectrum (PS) RF Ports section"
    ::= { docsRphyCcapRpdToCmMapStatusEntry 1 }
        
docsRphyCcapRpdToCmMapStatusRpdDsRfPortNum OBJECT-TYPE
    SYNTAX      Unsigned32  (0..4294967295)
    MAX-ACCESS  read-only
    STATUS      current
    DESCRIPTION
        "This attribute identifies the downstream RF port on 
         the RPD, for the RPD attached to the CM specified 
         by the CmId index. A CCAP Core MUST omit reporting
         RpdDsRfPortNum for a downstream Partial Spectrum-
         capable RPN. A CCAP Core can detect this condition
         from the NodePortMapDs (TLV 50.60.18.1) sub-table
         in an IRA message."
    REFERENCE 
        "Information Model Mapping: CM-SP-R-OSSI 
         CcapRpdToCmMapStatus::RpdDsRfPortNum
         Remote PHY Specification, CM-SP-R-PHY-I17-220531
         Partial Spectrum (PS) RF Ports section"
    ::= { docsRphyCcapRpdToCmMapStatusEntry 2 }

    docsRphyCcapRpdToCmMapStatusNodeRfPortId OBJECT-TYPE
    SYNTAX      Unsigned32  (0..255)
    MAX-ACCESS  read-only
    STATUS      current
    DESCRIPTION
        "This attribute provides a Node RF Port identifier
        for an RPN."
    REFERENCE 
        "Information Model Mapping: CM-SP-R-OSSI 
         CcapRpdToCmMapStatus::NodeRfPortId
         Remote PHY Specification, CM-SP-R-PHY-I17-220531
         Partial Spectrum (PS) RF Ports section"
    ::= { docsRphyCcapRpdToCmMapStatusEntry 3 }

    docsRphyCcapRpdToCmMapStatusRpdUsRfPortList OBJECT-TYPE
    SYNTAX      Unsigned32  (0..255)
    MAX-ACCESS  read-only
    STATUS      current
    DESCRIPTION
        "This attribute is a list of either Full Spectrum or
         Partial Spectrum UsRfPort indexes with channels in
         the CM's TCS."
    REFERENCE 
        "Information Model Mapping: CM-SP-R-OSSI 
         CcapRpdToCmMapStatus::RpdUsRfPortList
         Remote PHY Specification, CM-SP-R-PHY-I17-220531
         Partial Spectrum (PS) RF Ports section"
    ::= { docsRphyCcapRpdToCmMapStatusEntry 4 }

    docsRphyCcapRpdToCmMapStatusRpdDsRfPortList OBJECT-TYPE
    SYNTAX      Unsigned32  (0..255)
    MAX-ACCESS  read-only
    STATUS      current
    DESCRIPTION
        "This attribute is a list of either Full Spectrum or
         Partial Spectrum DsRfPort indexes with channels in
         the CM's RCS."
    REFERENCE 
        "Information Model Mapping: CM-SP-R-OSSI 
         CcapRpdToCmMapStatus::RpdDsRfPortList
         Remote PHY Specification, CM-SP-R-PHY-I17-220531
         Partial Spectrum (PS) RF Ports section"
    ::= { docsRphyCcapRpdToCmMapStatusEntry 5 }

-- ---------------------------------------------------------
-- Conformance definitions 
-- ---------------------------------------------------------

docsRphyCompliance MODULE-COMPLIANCE 
     STATUS current 
     DESCRIPTION 
          "The compliance statement for RPD management features."


MODULE -- docsRphyMib
          
-- conditionally mandatory groups


GROUP docsRphyRpdGroup 
    DESCRIPTION
        "Group of objects applicable to RPDs only.
         These objects are implemented on the CCAP Core
         but are derived from the RPD via the GCP protocol."
         
         
GROUP docsRphyCcapCoreGroup 
    DESCRIPTION
        "Group of objects applicable to CCAP Core only."

GROUP docsRphyCmtsCmStatGroup
    DESCRIPTION
        "Group of objects implemented to support CMTS Status in CCAP Core." 
    
OBJECT docsRphyRpdDevIdCurrSwImageServerType
    SYNTAX InetAddressType { ipv4(1), ipv6(2) }
    DESCRIPTION
      "An implementation is only required to support IPv4
       and IPv6 addresses."

OBJECT  docsRphyRpdDevCoresConnectedAddressType   
    SYNTAX InetAddressType { ipv4(1), ipv6(2) }
    DESCRIPTION
      "An implementation is only required to support IPv4
       and IPv6 addresses."
       

OBJECT docsRphyRpdDevOob551UsChanStatusNcIpAddrType
    SYNTAX InetAddressType { ipv4(1), ipv6(2) }
    DESCRIPTION
      "An implementation is only required to support IPv4
       and IPv6 addresses."

OBJECT docsRphyRpdDevOob551UsChanStatusArpdSrcIpAddrType
    SYNTAX InetAddressType { ipv4(1), ipv6(2) }
    DESCRIPTION
      "An implementation is only required to support IPv4
       and IPv6 addresses."
       
OBJECT docsRphyRpdDevExtSwImageSupportSwImageServerType
    SYNTAX InetAddressType { ipv4(1), ipv6(2) }
    DESCRIPTION
      "An implementation is only required to support IPv4
       and IPv6 addresses."
       
OBJECT docsRphyRpdDevCandidateBackupCoresBackupCoreAddrType
    SYNTAX InetAddressType { ipv4(1), ipv6(2) }
    DESCRIPTION
      "An implementation is only required to support IPv4
       and IPv6 addresses."
       

       
-- conditionally optional groups


::= { docsRphyCompliances 1}

docsRphyDeprecatedCompliance MODULE-COMPLIANCE
   STATUS      deprecated
   DESCRIPTION
        "The compliance statement for deprecated RPHY objects."
    MODULE -- this MODULE
    GROUP docsRphyRpdDeprecatedGroup
    DESCRIPTION
        "This group contains RPHY RPD objects which are deprecated
         from the MIB as of the current release."
::= { docsRphyCompliances 2 }


docsRphyRpdGroup OBJECT-GROUP
        OBJECTS {
         docsRphyRpdDevInfoSysUpTime,
         docsRphyRpdDevInfoNumCrashFilesAvail,
         docsRphyRpdDevInfoPrincipalCoreStatus,
         docsRphyRpdDevIdVendorName,     
         docsRphyRpdDevIdVendorId,            
         docsRphyRpdDevIdModelNum,            
         docsRphyRpdDevIdSerialNum,           
         docsRphyRpdDevIdDeviceAlias,         
         docsRphyRpdDevIdDeviceDescr,
         docsRphyRpdDevIdHwRev,         
         docsRphyRpdDevIdCurrSwVer,           
         docsRphyRpdDevIdBootRomVer,
         docsRphyRpdDevIdUsBurstRcvrVendorId,
         docsRphyRpdDevIdUsBurstRcvrModelNum,
         docsRphyRpdDevIdUsBurstRcvrDrivVer,
         docsRphyRpdDevIdUsBurstRcvrSerialNum,
         docsRphyRpdDevIdRcpProtocolVer,
         docsRphyRpdDevIdRcpSchemaVer,
         docsRphyRpdDevIdCurrSwImageLastUpdate,                
         docsRphyRpdDevIdCurrSwImageName,
         docsRphyRpdDevIdCurrSwImageServerType,         
         docsRphyRpdDevIdCurrSwImageServerAddress,
         docsRphyRpdDevIdCurrSwImageIndex,
         docsRphyRpdDevIdVspSelector,
         docsRphyRpdDevLocationDescr,          
         docsRphyRpdDevLocationLatitude,           
         docsRphyRpdDevLocationLongitude,
          
         docsRphyRpdDevCoresConnectedCoreId, 
         docsRphyRpdDevCoresConnectedAddressType,         
         docsRphyRpdDevCoresConnectedAddress,         
         docsRphyRpdDevCoresConnectedIsPrincipal,         
         docsRphyRpdDevCoresConnectedName,
         docsRphyRpdDevCoresConnectedVendorId,
         docsRphyRpdDevCoresConnectedCoreMode,
         docsRphyRpdDevCoresConnectedInitConfigComplete,
         docsRphyRpdDevCoresConnectedCoreFunction,
         docsRphyRpdDevCoresConnectedAuxCoreRpdState,
         docsRphyRpdDevCoresConnectedResourceSetIndex,
         docsRphyRpdDevCoresConnectedGcpBackupConnectionConfig,
         docsRphyRpdDevCoresConnectedGcpConnectionStatus,
         docsRphyRpdDevCoresConnectedGcpBackupCoreStatus,
         docsRphyRpdDevCoresConnectedAuthenticationStatus,         

         docsRphyRpdDevCapabNumDsPorts,             
         docsRphyRpdDevCapabNumUsPorts,             
         docsRphyRpdDevCapabNumTenGeNsPorts,            
         docsRphyRpdDevCapabNumOneGeNsPorts,          
         docsRphyRpdDevCapabNumDsScQamChans,          
         docsRphyRpdDevCapabNumDsOfdmChans,         
         docsRphyRpdDevCapabNumUsScQamChans,          
         docsRphyRpdDevCapabNumUsOfdmaChans,          
         docsRphyRpdDevCapabNumDsOob55d1Chans,          
         docsRphyRpdDevCapabNumUsOob55d1Chans,          
         docsRphyRpdDevCapabNumDsOob55d2Modules,          
         docsRphyRpdDevCapabNumUsOob55d2Demods,          
         docsRphyRpdDevCapabNumNdfChans,          
         docsRphyRpdDevCapabNumNdrChans,     
         docsRphyRpdDevCapabNumDsPspFlowsPerChan,       
         docsRphyRpdDevCapabNumUsPspFlowsPerChan,       
         docsRphyRpdDevCapabNumAsynchVideoChans,        
         docsRphyRpdDevCapabNumCwToneGens,          
         docsRphyRpdDevCapabLowestCwToneFreq,           
         docsRphyRpdDevCapabHighestCwToneFreq,          
         docsRphyRpdDevCapabMaxPwrDedCwTone,           
         docsRphyRpdDevCapabQamAsPilot,
         docsRphyRpdDevCapabSupportsUdpEncap,
         docsRphyRpdDevCapabSupportsFlowTags,
         docsRphyRpdDevCapabSupportsFreqTilt,
         docsRphyRpdDevCapabMaxTiltValue,
         docsRphyRpdDevCapabBufferDepthMonAlertSupp,
         docsRphyRpdDevCapabBufferDepthCfgSupp,
         docsRphyRpdDevCapabRpdUcdProcTime,
         docsRphyRpdDevCapabRpdUcdChgNullGrtTime,
         docsRphyRpdDevCapabMultiSectionTimingMerRep,
         docsRphyRpdDevCapabMinPwrDedCwTone, 
         docsRphyRpdDevCapabMaxPwrQamCwTone,
         docsRphyRpdDevCapabMinPwrQamCwTone,
         docsRphyRpdDevCapabSupportsOpticalNodeRf, 
         docsRphyRpdDevCapabMaxDsFrequency, 
         docsRphyRpdDevCapabMinDsFrequency,
         docsRphyRpdDevCapabMaxBasePwr, 
         docsRphyRpdDevCapabMinTiltValue, 
         docsRphyRpdDevCapabMinPwrAdjustScQam, 
         docsRphyRpdDevCapabMaxPwrAdjustScQam, 
         docsRphyRpdDevCapabMinPwrAdjustOfdm, 
         docsRphyRpdDevCapabMaxPwrAdjustOfdm,
         docsRphyRpdDevCapabMinBaseUsPowerTarLevel,
         docsRphyRpdDevCapabMaxBaseUsPowerTarLevel,
         docsRphyRpdDevCapabMinTarRxPowerAdjustScqam,
         docsRphyRpdDevCapabMaxTarRxPowerAdjustScqam,
         docsRphyRpdDevCapabMinTarRxPowerAdjustOfdma,
         docsRphyRpdDevCapabMaxTarRxPowerAdjustOfdma,
         docsRphyRpdDevCapabMinTarRxPowerAdjustNdr,
         docsRphyRpdDevCapabMaxTarRxPowerAdjustNdr,
         docsRphyRpdDevCapabMaxDsPspSegCount,
         docsRphyRpdDevCapabDirectDsFlowQueueMapping,
         docsRphyRpdDevCapabDsSchedulerPhbIdList,
         docsRphyRpdDevCapabRpdPendingEvRepQueueSize,
         docsRphyRpdDevCapabRpdLocalEventLogSize,
         docsRphyRpdDevCapabSupportsUsProfileQuery,
         docsRphyRpdDevCapabSupportsFlowTagIncrement,
         docsRphyRpdDevCapabMinBasePwr,
         docsRphyRpdDevCapabNumCoresSupported,
         docsRphyRpdDevCapabMaxDsOob55d1Frequency,
         docsRphyRpdDevCapabSupportsDsOob55d2SecFreq,
         docsRphyRpdDevCapabMaxDsOob55d2Frequency,
         docsRphyRpdDevCapabReportsOfdmConfigChangeCounts,
         
         docsRphyRpdDevChanReachabilityEndChanIndex,   
                   
         docsRphyRpdDevDsUsRfPortAllocScQamChans,         
         docsRphyRpdDevDsUsRfPortAllocOfdmChans,          
         docsRphyRpdDevDsUsRfPortAllocOob551Chans,            
         docsRphyRpdDevDsUsRfPortAllocNdChans,
         docsRphyRpdDevDsUsRfPortAllocBdrs,
         docsRphyRpdDevDsUsRfPortAllocConfiguredBcgs,
            
         docsRphyRpdDevL2tpSessionInfoCoreId,                   
         docsRphyRpdDevL2tpSessionInfoConnCtrlID,            
         docsRphyRpdDevL2tpSessionInfoUdpPort,           
         docsRphyRpdDevL2tpSessionInfoDescr,             
         docsRphyRpdDevL2tpSessionInfoSessionType,           
         docsRphyRpdDevL2tpSessionInfoSessionSubType,        
         docsRphyRpdDevL2tpSessionInfoMaxPayload,            
         docsRphyRpdDevL2tpSessionInfoPathPayload,           
         docsRphyRpdDevL2tpSessionInfoRpdIfMtu, 
         docsRphyRpdDevL2tpSessionInfoCoreIfMtu,         
         docsRphyRpdDevL2tpSessionInfoErrorCode,         
         docsRphyRpdDevL2tpSessionInfoCreationTime,          
         docsRphyRpdDevL2tpSessionInfoOperStatus,            
         docsRphyRpdDevL2tpSessionInfoLocalStatus,           
         docsRphyRpdDevL2tpSessionInfoLastChange,
         docsRphyRpdDevL2tpSessionInfoExtendedRemoteEndId,
            
         docsRphyRpdDevL2tpSessionStatsOutOfSeqPkts,  
         docsRphyRpdDevL2tpSessionStatsInPkts,
         docsRphyRpdDevL2tpSessionStatsInDiscards,
         docsRphyRpdDevL2tpSessionStatsOutPkts,
         docsRphyRpdDevL2tpSessionStatsOutErrors,
         docsRphyRpdDevL2tpSessionStatsCounterDiscontinuityTime,
            
         docsRphyRpdDevDiagStatusProbableCause,
         docsRphyRpdDevDiagStatusAdditionalText,
         docsRphyRpdDevDiagStatusSeverityLevel,
            
         docsRphyRpdDevDepiMcastSessionRpdLcceIpAddr,
         docsRphyRpdDevDepiMcastSessionCcapLcceIpAddr,
         docsRphyRpdDevDepiMcastSessionJoinTime,
            
         docsRphyRpdDevEventLogFirstTime,
         docsRphyRpdDevEventLogLastTime,
         docsRphyRpdDevEventLogCounts,
         docsRphyRpdDevEventLogLevel,
         docsRphyRpdDevEventLogId,
         docsRphyRpdDevEventLogText,
            
         docsRphyRpdDevOob551UsChanStatusNcIpAddrType,
         docsRphyRpdDevOob551UsChanStatusNcIpAddr,
         docsRphyRpdDevOob551UsChanStatusArpdSrcIpAddrType,
         docsRphyRpdDevOob551UsChanStatusArpdSrcIpAddr,
         docsRphyRpdDevOob551UsChanStatusPerfectCellsRcvd,
         docsRphyRpdDevOob551UsChanStatusCorrectedCellsRcvd,
         docsRphyRpdDevOob551UsChanStatusUncorrectableCellsRcvd,
         docsRphyRpdDevOob551UsChanStatusTotalCellsRcvd,
         docsRphyRpdDevOob551UsChanStatusPwrLevel,
         docsRphyRpdDevOob551UsChanStatusMaxPwrLevel,
         docsRphyRpdDevOob551UsChanStatusMinPwrLevel,
         docsRphyRpdDevOob551UsChanStatusCounterDiscontinuityTime,
         docsRphyRpdDevOob551UsChanStatusOperStatus,
            
         docsRphyRpdDevCrashDataFileStatusFilename,
         docsRphyRpdDevCrashDataFileStatusFileStatus,
            
         docsRphyRpdDevUsSignalQualityRxMer,
         docsRphyRpdDevUsSignalQualityRxMerSamples,
         docsRphyRpdDevUsSignalQualityUnerroreds,
         docsRphyRpdDevUsSignalQualityCorrecteds,
         docsRphyRpdDevUsSignalQualityUncorrectables,

         docsRphyRpdDevHostResSysDate,

         docsRphyRpdDevHostResStorType,
         docsRphyRpdDevHostResStorAllocationUnits,
         docsRphyRpdDevHostResStorAllocationFailures,
         docsRphyRpdDevHostResStorSize,
         docsRphyRpdDevHostResStorUsed,
         docsRphyRpdDevHostResStorDescr,

         docsRphyRpdDevHostResSwRunType,
         docsRphyRpdDevHostResSwRunStatus,
         docsRphyRpdDevHostResSwRunPerfCpu,
         docsRphyRpdDevHostResSwRunPerfMem,
         docsRphyRpdDevHostResSwRunName,

         docsRphyRpdDevStaticPwCapMaxFwdStaticPws,
         docsRphyRpdDevStaticPwCapMaxRetStaticPws,
         docsRphyRpdDevStaticPwCapSupportsStaticMptDepiPw,
         docsRphyRpdDevStaticPwCapSupportsStaticMpt55d1RetPw,
         docsRphyRpdDevStaticPwCapSupportsStaticPspNdfPw,
         docsRphyRpdDevStaticPwCapSupportsStaticPspNdrPw,
         docsRphyRpdDevStaticPwCapMaxUcastFwdStaticPws,
         docsRphyRpdDevStaticPwCapSupportsStaticPspNdfUcastPw,
         docsRphyRpdDevStaticPwCapSupportsStaticPspPnmPw,        
         docsRphyRpdDevStaticPwCapSupportsStaticPspSpecmanPw,
         docsRphyRpdDevStaticPwCapSupportsDepiPspMultichanPw,
         docsRphyRpdDevStaticPwCapSupportsUepiPws,
         docsRphyRpdDevStaticPwCapSupportsDtpPw,         

         docsRphyRpdDevExtSwImageSupportSwImageLastUpdate,
         docsRphyRpdDevExtSwImageSupportSwImageName,
         docsRphyRpdDevExtSwImageSupportSwImageDescr,
         docsRphyRpdDevExtSwImageSupportSwImageServerType,
         docsRphyRpdDevExtSwImageSupportSwImageServerAddress,

         docsRphyRpdDevSwImageCapNumSwImages,
         docsRphyRpdDevSwImageCapImageUpgradability,

         docsRphyRpdDevGcpCapGcpKaResponseTime,

         docsRphyRpdDevOfdmCfgCapReqOfdmaImDurationCfg,
         docsRphyRpdDevOfdmCfgCapSupportedPilotPatterns,
         docsRphyRpdDevOfdmCfgCapNumDsOfdmProfiles,
         docsRphyRpdDevOfdmCfgCapOptionalOfdmModulations,
         docsRphyRpdDevOfdmCfgCapOptionalOfdmaModulations,

         docsRphyRpdDevCoreRedundancyCapSupportsRedundancy,

         docsRphyRpdDevResetCapSupportsReset,
         docsRphyRpdDevResetCapResetHistorySize,

         docsRphyRpdDevFdxCapSupportsFdx,
         docsRphyRpdDevFdxCapSupportsZblInsertion,
         docsRphyRpdDevFdxCapZblInsMsgLeadTime,

         docsRphyRpdDevRdtiCapNumPtpPortsPerEnetPort,
         docsRphyRpdDevRdtiCapSupportsSyncE,
         docsRphyRpdDevRdtiCapSupportsG8275d1,
         docsRphyRpdDevRdtiCapSupportsDtpPseudowire,

         docsRphyRpdDevDsCapScQamInterleaverSupport,
         docsRphyRpdDevDsCapMaxDocsisScQamChannels,
         docsRphyRpdDevDsCapMaxMultipleScQamPspSessions,
         docsRphyRpdDevDsCapMaxNumBdrs,
         docsRphyRpdDevDsCapMaxNumBcgs,
         docsRphyRpdDevDsCapSupportsDsScQamModulationQam128,
         docsRphyRpdDevDsCapSupportsTiltMinimumFrequency,

         docsRphyRpdDevSpecCaptureCapNumSacs,

         docsRphyRpdDevSacCapSacDescription,
         docsRphyRpdDevSacCapMaxCaptureSpan,
         docsRphyRpdDevSacCapMinCaptureFreq,
         docsRphyRpdDevSacCapMaxCaptureFreq,
         docsRphyRpdDevSacCapSuppTriggerModes,
         docsRphyRpdDevSacCapSuppOutputFormats,
         docsRphyRpdDevSacCapSuppWindowFormats,
         docsRphyRpdDevSacCapSuppAveraging,
         docsRphyRpdDevSacCapSuppAggrMethods,
         docsRphyRpdDevSacCapSuppSpecQual,
         docsRphyRpdDevSacCapMaxNumBins,
         docsRphyRpdDevSacCapMinNumBins,
         docsRphyRpdDevSacCapMinRepeatPeriod,
         docsRphyRpdDevSacCapSuppTrigChanTypes,
         docsRphyRpdDevSacCapPwType,
         docsRphyRpdDevSacCapLowestCapturePort,
         docsRphyRpdDevSacCapHighestCapturePort,
         docsRphyRpdDevSacCapSuppScanCapture,
         docsRphyRpdDevSacCapMinScanRepeatPeriod,
         docsRphyRpdDevTelemetryCapSupportsGnmiStreaming,
         docsRphyRpdDevTelemetryCapNumClientsSupported,

         docsRphyRpdDevNodePortMapDsCapGainControlIndex,

         docsRphyRpdDevNodePortMapUsCapGainControlIndex,

         docsRphyRpdDevCandidateBackupCoresBackupCoreAddrType,
         docsRphyRpdDevCandidateBackupCoresBackupCoreAddr,

         docsRphyRpdDevShelfInfoRpdSlot,

         docsRphyRpdDevPmapCapMaxNumPmaples,
         docsRphyRpdDevPmapCapProbePowerControl,
         docsRphyRpdDevPmapCapSupportedPilotPatterns,

         docsRphyRpdDevEchoCanCapEctMethod,
         docsRphyRpdDevEchoCanCapMaxEctChannels,
         docsRphyRpdDevEchoCanCapMinEctPeriod,
         docsRphyRpdDevEchoCanCapErdDuration,

         docsRphyRpdDevRfmCapSupportsRfmMgmt,
         docsRphyRpdDevRfmCapNumNodeRfPorts,
         docsRphyRpdDevRfmCapSupportsDsCfgRfmGain,
         docsRphyRpdDevRfmCapMinDsCfgRfmGain, 
         docsRphyRpdDevRfmCapMaxDsCfgRfmGain,    
         docsRphyRpdDevRfmCapSupportsUsCfgRfmGain,
         docsRphyRpdDevRfmCapMinUsCfgRfmGain,       
         docsRphyRpdDevRfmCapMaxUsCfgRfmGain,            
         docsRphyRpdDevRfmCapSupportsRfmDsTiltConfig,  
         docsRphyRpdDevRfmCapMinRfmDsTilt,          
         docsRphyRpdDevRfmCapMaxRfmDsTilt, 
         docsRphyRpdDevRfmCapMaxDsPowerGainFunctions,
         docsRphyRpdDevRfmCapMaxUsPowerGainFunctions,  
         docsRphyRpdDevRfmCapMaxDsTiltCtrlFunctions,         
         docsRphyRpdDevRfmCapMinRfmDsFreq,
         docsRphyRpdDevRfmCapMaxRfmDsFreq,

         docsRphyRpdDevNodeRfPortCapNodeRfPortVendorDesc,
         docsRphyRpdDevNodeRfPortCapRpdUsRfPortMap,
         docsRphyRpdDevNodeRfPortCapRpdDsRfPortMap,
         docsRphyRpdDevNodeRfPortCapRfmUsGainCtrlIndex,
         docsRphyRpdDevNodeRfPortCapRfmDsGainCtrlIndex,
         docsRphyRpdDevNodeRfPortCapRfmDsTiltCtrlIndex,
         docsRphyRpdDevNodeRfPortCapNodeRfPortOpLabel,
         
         docsRphyRpdDevResetHistoryResetTimestamp,
         docsRphyRpdDevResetHistoryType,
         docsRphyRpdDevResetHistoryReason,
         docsRphyRpdDevResetHistoryEventIdRef,
         docsRphyRpdDevResetHistoryEventDescription,
         docsRphyRpdDevResetHistoryRecoveryTime,
         docsRphyRpdDevResetHistoryPrincipalOpTimestamp,
         
         docsRphyRpdDevChanBcastGroupStatusGroupMember,
         
         docsRphyRpdDevUsCapMaxUsFrequency,
         docsRphyRpdDevUsCapMinUsFrequency,
         docsRphyRpdDevUsCapMaxUnicastSids,
         
         docsRphyRpdDevPmtdudCapSupportsIcmpBasedPmtud,
         docsRphyRpdDevPmtdudCapSupportsPacketizationBasedPmtud, 
         
         docsRphyRpdDevPnmCapSupportedPnmTests,
         
         docsRphyRpdDevUpcCapMinNumSymbols25Khz,
         docsRphyRpdDevUpcCapMaxNumSymbols25Khz,
         docsRphyRpdDevUpcCapMinNumSymbols50Khz,
         docsRphyRpdDevUpcCapMaxNumSymbols50Khz,
         docsRphyRpdDevUpcCapSupportsStaggeredPies,
         docsRphyRpdDevUpcCapSupportsDedicatedPwUpcRxMer,
         docsRphyRpdDevUpcCapSupportsFreqDomainSamples,
         
         docsRphyRpdDevInitCapPerCoreInitTimers,
         docsRphyRpdDevInitCapStagingConfigInitTimers,
         
         docsRphyRpdDevUsPowerCapMinTarRxPowerAdjust55d2,
         docsRphyRpdDevUsPowerCapMaxTarRxPowerAdjust55d2,
         
         docsRphyRpdDevTrfStatsTunnelReplacements,
         docsRphyRpdDevTrfStatsTunnelReplacementFailures,
         docsRphyRpdDevTrfStatsTunnelHandovers,
         docsRphyRpdDevTrfStatsTunnelHandoverFailures,
         
         docsRphyRpdDevLcceStatsCtrlConnEst,
         docsRphyRpdDevLcceStatsCtrlConnEstFailures,
         docsRphyRpdDevLcceStatsCtrlConnFailures,
         docsRphyRpdDevLcceStatsCurrCtrlConn,
         
         docsRphyRpdDevCurrCtrlConnCoreConnCtrlId,
         docsRphyRpdDevCurrCtrlConnCoreId,
         docsRphyRpdDevCurrCtrlConnUdpPort,
         docsRphyRpdDevCurrCtrlConnHaState,
         docsRphyRpdDevCurrCtrlConnSessEstFailures,
         docsRphyRpdDevCurrCtrlConnSessFailed,
         docsRphyRpdDevCurrCtrlConnCurrSess,         

         docsRphyRpdIfPhysEntityDescr,          
         docsRphyRpdIfPhysEntityVendorType,     
         docsRphyRpdIfPhysEntityContainedIn,    
         docsRphyRpdIfPhysEntityClass,          
         docsRphyRpdIfPhysEntityParentRelPos,   
         docsRphyRpdIfPhysEntityName,           
         docsRphyRpdIfPhysEntityHardwareRev,    
         docsRphyRpdIfPhysEntityFirmwareRev,    
         docsRphyRpdIfPhysEntitySoftwareRev,    
         docsRphyRpdIfPhysEntitySerialNum,      
         docsRphyRpdIfPhysEntityMfgName,        
         docsRphyRpdIfPhysEntityModelName,      
         docsRphyRpdIfPhysEntityAlias,          
         docsRphyRpdIfPhysEntityAssetID,        
         docsRphyRpdIfPhysEntityIsFRU,          
         docsRphyRpdIfPhysEntityMfgDate,        
         docsRphyRpdIfPhysEntityUris,           
         docsRphyRpdIfPhysEntityUUID,
            
         docsRphyRpdIfPhysEntSensorType,            
         docsRphyRpdIfPhysEntSensorScale,           
         docsRphyRpdIfPhysEntSensorPrecision,       
         docsRphyRpdIfPhysEntSensorValue,           
         docsRphyRpdIfPhysEntSensorOperStatus,      
         docsRphyRpdIfPhysEntSensorUnitsDisplay,    
         docsRphyRpdIfPhysEntSensorValueTimeStamp,  
         docsRphyRpdIfPhysEntSensorValueUpdateRate,
                        
         docsRphyRpdIfEnetDescr,             
         docsRphyRpdIfEnetName,              
         docsRphyRpdIfEnetAlias,             
         docsRphyRpdIfEnetType,              
         docsRphyRpdIfEnetMtu,                           
         docsRphyRpdIfEnetPhysAddress,           
         docsRphyRpdIfEnetAdminStatus,           
         docsRphyRpdIfEnetOperStatus,            
         docsRphyRpdIfEnetLastChange,            
         docsRphyRpdIfEnetLinkUpDownTrapEnable,  
         docsRphyRpdIfEnetHighSpeed,         
         docsRphyRpdIfEnetPromiscuousMode,      
         docsRphyRpdIfEnetConnectorPresent,
         docsRphyRpdIfEnetNetworkAuthStatus,

         docsRphyRpdIfEnetStatsInOctets,            
         docsRphyRpdIfEnetStatsOutOctets,           
         docsRphyRpdIfEnetStatsInFrames,            
         docsRphyRpdIfEnetStatsOutFrames,               
         docsRphyRpdIfEnetStatsInUnicastFrames,     
         docsRphyRpdIfEnetStatsOutUnicastFrames,         
         docsRphyRpdIfEnetStatsInMulticastFrames,   
         docsRphyRpdIfEnetStatsOutMulticastFrames,        
         docsRphyRpdIfEnetStatsInBroadcastFrames,   
         docsRphyRpdIfEnetStatsOutBroadcastFrames,  
         docsRphyRpdIfEnetStatsInDiscards,          
         docsRphyRpdIfEnetStatsOutDiscards,         
         docsRphyRpdIfEnetStatsInErrors,            
         docsRphyRpdIfEnetStatsOutErrors,           
         docsRphyRpdIfEnetStatsInUnknownProtos,     
         docsRphyRpdIfEnetStatsCounterDiscontinuityTime, 
            
         docsRphyRpdIfRpdEnetToCoreEntityMapEntityIndex,
            
         docsRphyRpdIfCoreToRpdMapRpdRfChanType,
         docsRphyRpdIfCoreToRpdMapRpdRfChanIndex,
            
         docsRphyRpdIfRpdToCoreMapCoreIfIndex,

         docsRphyRpdIfEnetSfpPlusStatusStatus,
         docsRphyRpdIfEnetSfpPlusStatusIdentifier,
         docsRphyRpdIfEnetSfpPlusStatusExtendedIdentifier,
         docsRphyRpdIfEnetSfpPlusStatusConnectorType,
         docsRphyRpdIfEnetSfpPlusStatusTransceiverComplianceCodes,
         docsRphyRpdIfEnetSfpPlusStatusTransceiverComplianceCode36,
         docsRphyRpdIfEnetSfpPlusStatusEncoding,
         docsRphyRpdIfEnetSfpPlusStatusBitRateNominal,
         docsRphyRpdIfEnetSfpPlusStatusRateIdentifier,
         docsRphyRpdIfEnetSfpPlusStatusLengthKm,
         docsRphyRpdIfEnetSfpPlusStatusLength100M,
         docsRphyRpdIfEnetSfpPlusStatusLength50Mi10M,
         docsRphyRpdIfEnetSfpPlusStatusLength62Pt5Mi10M,
         docsRphyRpdIfEnetSfpPlusStatusLengthCopperM,
         docsRphyRpdIfEnetSfpPlusStatusLength50MiOm3,
         docsRphyRpdIfEnetSfpPlusStatusVendorName,
         docsRphyRpdIfEnetSfpPlusStatusVendorOui,
         docsRphyRpdIfEnetSfpPlusStatusVendorPartNum,
         docsRphyRpdIfEnetSfpPlusStatusVendorSerialNum,
         docsRphyRpdIfEnetSfpPlusStatusVendorRev,
         docsRphyRpdIfEnetSfpPlusStatusLaserWavelength,
         docsRphyRpdIfEnetSfpPlusStatusOptions,
         docsRphyRpdIfEnetSfpPlusStatusBitRateMax,
         docsRphyRpdIfEnetSfpPlusStatusBitRateMin,
         docsRphyRpdIfEnetSfpPlusStatusVendorDate,
         docsRphyRpdIfEnetSfpPlusStatusVendorSpecificLotCode,
         docsRphyRpdIfEnetSfpPlusStatusDiagMonitorType,
         docsRphyRpdIfEnetSfpPlusStatusEnhancedOptions,
         docsRphyRpdIfEnetSfpPlusStatusSff8472Compliance,
         docsRphyRpdIfEnetSfpPlusStatusVendorSpecificData,
         docsRphyRpdIfEnetSfpPlusStatusMeasuredTxOutputPwr,
         docsRphyRpdIfEnetSfpPlusStatusMeasuredRxInputPwr,
         docsRphyRpdIfEnetSfpPlusStatusDigitalDiagA2Info,
         docsRphyRpdIfEnetSfpPlusStatusMeasuredTxBiasCurrent,
         docsRphyRpdIfEnetSfpPlusStatusMeasuredTemperature,
         docsRphyRpdIfEnetSfpPlusStatusMeasuredSupplyVoltage,

         docsRphyRpdIfEnetSyncEPortStatusSignalQualified,
         docsRphyRpdIfEnetSyncEPortStatusReceivedSsm,
         
         docsRphyRpdIfRfmStatusReportedDsGain,
         docsRphyRpdIfRfmStatusReportedDsGainStatus,
         docsRphyRpdIfRfmStatusReportedUsGain,
         docsRphyRpdIfRfmStatusReportedUsGainStatus,
         docsRphyRpdIfRfmStatusReportedRfmDsTilt,
         docsRphyRpdIfRfmStatusReportedRfmDsTiltStatus,
         docsRphyRpdIfRfmStatusDsOutputPower,
         docsRphyRpdIfRfmStatusUsExpectedRxPower,
         docsRphyRpdIfRfmStatusTotalDsTilt,
            
         docsRphyRpdIpv4GrpDefaultTTL,                        
         docsRphyRpdIpv4GrpInterfaceTableLastChange,
                     
         docsRphyRpdIpv6GrpIpDefaultHopLimit,        
         docsRphyRpdIpv6GrpInterfaceTableLastChange, 
         docsRphyRpdIpv6GrpIfStatsTableLastChange,     
                    
         docsRphyRpdIpv4InterfaceEnableStatus,
         docsRphyRpdIpv4InterfaceRetransmitTime,
               
         docsRphyRpdIpv6InterfaceIdentifier,
         docsRphyRpdIpv6InterfaceEnableStatus,   
         docsRphyRpdIpv6InterfaceReachableTime,
         docsRphyRpdIpv6InterfaceRetransmitTime,        
            
         docsRphyRpdIpIfStatsInReceives,          
         docsRphyRpdIpIfStatsInOctets,            
         docsRphyRpdIpIfStatsInHdrErrors,         
         docsRphyRpdIpIfStatsInNoRoutes,          
         docsRphyRpdIpIfStatsInAddrErrors,       
         docsRphyRpdIpIfStatsInUnknownProtos,     
         docsRphyRpdIpIfStatsInTruncatedPkts,          
         docsRphyRpdIpIfStatsInDiscards,          
         docsRphyRpdIpIfStatsInDelivers,            
         docsRphyRpdIpIfStatsOutRequests,             
         docsRphyRpdIpIfStatsOutDiscards,              
         docsRphyRpdIpIfStatsOutTransmits,        
         docsRphyRpdIpIfStatsOutOctets,           
         docsRphyRpdIpIfStatsInMcastPkts,          
         docsRphyRpdIpIfStatsInMcastOctets,         
         docsRphyRpdIpIfStatsOutMcastPkts,        
         docsRphyRpdIpIfStatsOutMcastOctets,           
         docsRphyRpdIpIfStatsDiscontinuityTime,   
         docsRphyRpdIpIfStatsRefreshRate,         
                     
         docsRphyRpdIpAddressEnetPortIndex,    
         docsRphyRpdIpAddressPrefixLen,
         docsRphyRpdIpAddressType,
         docsRphyRpdIpAddressOrigin,    
         docsRphyRpdIpAddressStatus,
         docsRphyRpdIpAddressCreated,   
         docsRphyRpdIpAddressLastChanged,          
            
         docsRphyRpdIpNetToPhysicalPhysAddress, 
         docsRphyRpdIpNetToPhysicalLastUpdated,
         docsRphyRpdIpNetToPhysicalType,        
         docsRphyRpdIpNetToPhysicalState,            
            
         docsRphyRpdIpDefaultRouterLifetime, 
         docsRphyRpdIpDefaultRouterPreference,
            
         docsRphyRpdIpIcmpMsgStatsInPkts, 
         docsRphyRpdIpIcmpMsgStatsOutPkts

        }
    STATUS      current
    DESCRIPTION
        "Group of objects implemented in CCAP Cores which
         represent RPD managed objects derived via the GCP 
         protocol."
              
    ::= { docsRphyGroups 1 }

docsRphyCcapCoreGroup OBJECT-GROUP
        OBJECTS {      
         docsRphyCcapL2tpSessionInfoCoreId,            
         docsRphyCcapL2tpSessionInfoConnCtrlID,            
         docsRphyCcapL2tpSessionInfoUdpPort,           
         docsRphyCcapL2tpSessionInfoDescr,             
         docsRphyCcapL2tpSessionInfoSessionType,           
         docsRphyCcapL2tpSessionInfoSessionSubType,        
         docsRphyCcapL2tpSessionInfoMaxPayload,            
         docsRphyCcapL2tpSessionInfoPathPayload, 
         docsRphyCcapL2tpSessionInfoRpdIfMtu,             
         docsRphyCcapL2tpSessionInfoCoreIfMtu,         
         docsRphyCcapL2tpSessionInfoIncludeDOCSISMsgs,     
         docsRphyCcapL2tpSessionInfoErrorCode,         
         docsRphyCcapL2tpSessionInfoCreationTime,          
         docsRphyCcapL2tpSessionInfoOperStatus,            
         docsRphyCcapL2tpSessionInfoLocalStatus,           
         docsRphyCcapL2tpSessionInfoLastChange,
         docsRphyCcapL2tpSessionInfoExtendedRemoteEndId,
            
         docsRphyCcapL2tpSessionFlowPhbId,
            
         docsRphyCcapL2tpSessionStatsOutOfSeqPkts,
         docsRphyCcapL2tpSessionStatsInPkts,
         docsRphyCcapL2tpSessionStatsInDiscards,
         docsRphyCcapL2tpSessionStatsOutPkts,
         docsRphyCcapL2tpSessionStatsOutErrors,
            
         docsRphyCcapCinDsLatencyLastVal,           
         docsRphyCcapCinDsLatencyLastValTime,       
         docsRphyCcapCinDsLatencyInterval,
            
         docsRphyCcapSessionCinDsLatencyStatsVal,           
         docsRphyCcapSessionCinDsLatencyStatsValTime,

         docsRphyCcapCwToneStatusStatus,

         docsRphyCcapUsOfdmaFdxEcStatusCurrentEctPeriod,   
         docsRphyCcapUsOfdmaFdxEcStatusCurrentEctoDuration,
         docsRphyCcapUsOfdmaFdxEcStatusLastRequestEctPeriod,
         docsRphyCcapUsOfdmaFdxEcStatusLastRequestEctoDuration,
         docsRphyCcapUsOfdmaFdxEcStatusNumTxEctos,
         docsRphyCcapUsOfdmaFdxEcStatusNumRxEcRequestBlocks,
         docsRphyCcapUsOfdmaFdxEcStatusNumRxEcRequestBlocksNoConv,

         docsRphyCcapTrfStatsTunnelReplacements,
         docsRphyCcapTrfStatsTunnelReplacementFailures,
         docsRphyCcapTrfStatsTunnelHandovers,
                 
         docsRphyCcapLcceStatsCoreId,
         docsRphyCcapLcceStatsCtrlConnEst,
         docsRphyCcapLcceStatsCtrlConnEstFailures,
         docsRphyCcapLcceStatsCtrlConnFailures,
         docsRphyCcapLcceStatsCurrCtrlConn,

         docsRphyCcapCurrCtrlConnRpdConnCtrlId,
         docsRphyCcapCurrCtrlConnCoreId,
         docsRphyCcapCurrCtrlConnUdpPort,
         docsRphyCcapCurrCtrlConnHaState,
         docsRphyCcapCurrCtrlConnSessEstFailures,
         docsRphyCcapCurrCtrlConnSessFailed,
         docsRphyCcapCurrCtrlConnCurrSess          
         
        }
    STATUS      current
    DESCRIPTION
        "Group of objects implemented in CCAP Cores."
    ::= { docsRphyGroups 2 }

--OID docsRphyGroups 3 is DEPRECATED
        

docsRphyCmtsCmStatGroup OBJECT-GROUP
        OBJECTS {
         docsRphyCmtsCmRegStatusRpdUniqueId,

         docsRphyCcapRpdToCmMapStatusRpdUsRfPortNum,
         docsRphyCcapRpdToCmMapStatusRpdDsRfPortNum,
         docsRphyCcapRpdToCmMapStatusNodeRfPortId,
         docsRphyCcapRpdToCmMapStatusRpdUsRfPortList,
         docsRphyCcapRpdToCmMapStatusRpdDsRfPortList
        }
    STATUS      current
    DESCRIPTION
        "Group of objects implemented to support CMTS Status in CCAP Core."
    ::= { docsRphyGroups 4 }

docsRphyRpdDeprecatedGroup OBJECT-GROUP
    OBJECTS {
            docsRphyRpdDevCapabVspSelector,
            docsRphyRpdIfEnetStatsInUnicastOctets,
            docsRphyRpdIfEnetStatsOutUnicastOctets,
            docsRphyRpdIfEnetStatsInMulticastOctets,
            docsRphyRpdIfEnetStatsOutMulticastOctets,
            docsRphyRpdIfEnetStatsInBroadcastOctets,
            docsRphyRpdIfEnetStatsOutBroadcastOctets,
            docsRphyRpdDevCoresConnectedAuxCoreGcpConnectionStatus
     }
    STATUS      deprecated
    DESCRIPTION
         "Deprecated RPHY RPD objects group"
    ::= { docsRphyGroups 5 }
    
    
        END
